-- -*- SNMP -*- mode for Emacs                                                                                                 
      XIV-MIB DEFINITIONS ::= BEGIN                                                                                                  
                                                                                                                                     
      IMPORTS                                                                                                                        
          MODULE-IDENTITY, OBJECT-TYPE,                                                                                              
              NOTIFICATION-TYPE,                                                                                                     
              Gauge32, Integer32   FROM SNMPv2-SMI                                                                                   
      		ucdavis FROM UCD-SNMP-MIB                                                                                                      
          OBJECT-GROUP, NOTIFICATION-GROUP,                                                                                          
             MODULE-COMPLIANCE    FROM SNMPv2-CONF                                                                                  
                                                                                                                                    
         TEXTUAL-CONVENTION, DisplayString                                                                                          
                                  FROM SNMPv2-TC;                                                                                   
                                                                                                                                    
     xivMIB MODULE-IDENTITY                                                                                                         
         LAST-UPDATED "200910010000Z"                                                                                               
         ORGANIZATION "IBM"                                                                                                         
         CONTACT-INFO "IBM"                                                                                                         
         DESCRIPTION                                                                                                                
                 "The MIB module to describe objects for IBM XIV Storage System"                                                    
                                                                                                                                    
         REVISION      "200910010000Z"                                                                                              
         DESCRIPTION                                                                                                                
                 "v10.1 revision."                                                                                                  
         ::= { ucdavis 77 }                                                                                                         
                                                                                                                                    
     xivMachine OBJECT IDENTIFIER ::= { xivMIB 1 }                                                                                  
                                                                                                                                    
     xivStatus OBJECT IDENTIFIER ::= { xivMachine 1 }                                                                               
                                                                                                                                    
     xivCompliance MODULE-COMPLIANCE                                                                                                
         STATUS  current                                                                                                            
         DESCRIPTION                                                                                                                
                 "The compliance statement for SNMPv2 IBM XIV Storage System entities."                                             
                                                                                                                                    
         MODULE  -- this module                                                                                                     
             MANDATORY-GROUPS { xivStatusGroup, xivInterfacesGroup, xivEventsGroup,                                                 
     	xivEventTrapGroup, xivEventTrapNotificationGroup }                                                                             
         ::= { xivMIB 100 }                                                                                                         
                                                                                                                                    
     xivStatusGroup OBJECT-GROUP                                                                                                    
         OBJECTS { xivMachineStatus, xivFreeSpaceSoft, xivFreeSpaceHard, xivFailedDisks, xivUtilizationSoft, xivUtilizationHard }   
         STATUS  current                                                                                                            
         DESCRIPTION                                                                                                                
                 "A collection of objects providing information on the                                                              
                  IBM XIV Storage System."                                                                                          
         ::= { xivStatus 100 }                                                                                                      
                                                                                                                                    
                                                                                                                                    
     xivGlobalStatus OBJECT IDENTIFIER ::= { xivStatus 1 }                                                                          
                                                                                                                                    
     xivInterfaces   OBJECT IDENTIFIER ::= { xivStatus 2 }                                                                          
                                                                                                                                    
     xivInterfacesGroup OBJECT-GROUP                                                                                                
         OBJECTS { xivIfStatus, xivIfIOPS }                                                                                         
         STATUS  current                                                                                                            
         DESCRIPTION                                                                                                                
                 "A collection of objects providing information on the                                                              
                  interfaces of the IBM XIV Storage System."                                                                        
         ::= { xivInterfaces 100 }                                                                                                  
                                                                                                                                    
                                                                                                                                    
     -- InterfaceIndex contains the semantics of ifIndex and should be used                                                         
     -- for any objects defined in other MIB modules that need these semantics.                                                     
                                                                                                                                    
     InterfaceIndex ::= TEXTUAL-CONVENTION                                                                                          
         DISPLAY-HINT "d"                                                                                                           
         STATUS       current                                                                                                       
         DESCRIPTION                                                                                                                
                 "A unique value, greater than zero, for each interface or                                                          
                 interface sub-layer in the managed system.  It is                                                                  
                 recommended that values are assigned contiguously starting                                                         
                 from 1.  The value for each interface sub-layer must remain                                                        
                 constant at least from one re-initialization of the entity's                                                       
                 network management system to the next re-initialization."                                                          
         SYNTAX       Integer32 (1..10000)                                                                                          
                                                                                                                                    
     -- the Interfaces table                                                                                                        
                                                                                                                                    
     -- The Interfaces table contains information on the entity's                                                                   
                                                                                                                                    
     -- interfaces.                                                                                                                 
                                                                                                                                    
                                                                                                                                    
     xivIfTable OBJECT-TYPE                                                                                                         
         SYNTAX      SEQUENCE OF XivIfEntry                                                                                         
         MAX-ACCESS  not-accessible                                                                                                 
         STATUS      current                                                                                                        
         DESCRIPTION                                                                                                                
                 "A list of interface entries"                                                                                      
         ::= { xivInterfaces 1 }                                                                                                    
                                                                                                                                    
     xivIfEntry OBJECT-TYPE                                                                                                         
         SYNTAX      XivIfEntry                                                                                                     
         MAX-ACCESS  not-accessible                                                                                                 
         STATUS      current                                                                                                        
         DESCRIPTION                                                                                                                
                 "An entry containing management information applicable to a                                                        
                 particular interface."                                                                                             
        INDEX   { xivIfIndex }                                                                                                     
        ::= { xivIfTable 1 }                                                                                                       
                                                                                                                                   
    XivIfEntry ::=                                                                                                                 
        SEQUENCE {                                                                                                                 
            xivIfIndex              InterfaceIndex,                                                                                
            xivIfIOPS               Gauge32,                                                                                       
            xivIfStatus             OCTET STRING                                                                                   
        }                                                                                                                          
                                                                                                                                   
    xivIfIndex OBJECT-TYPE                                                                                                         
        SYNTAX      InterfaceIndex                                                                                                 
        MAX-ACCESS  not-accessible                                                                                                 
        STATUS      current                                                                                                        
        DESCRIPTION                                                                                                                
                "A unique value for each interface."                                                                               
        ::= { xivIfEntry 1 }                                                                                                       
                                                                                                                                   
    xivIfIOPS OBJECT-TYPE                                                                                                          
        SYNTAX      Gauge32                                                                                                        
        MAX-ACCESS  read-only                                                                                                      
        STATUS      current                                                                                                        
        DESCRIPTION                                                                                                                
                "The interface's current load in I/Os per second."                                                                 
        ::= { xivIfEntry 2 }                                                                                                       
                                                                                                                                   
    xivIfStatus OBJECT-TYPE                                                                                                        
        SYNTAX      OCTET STRING (SIZE (1..64))                                                                                    
        MAX-ACCESS  read-only                                                                                                      
        STATUS      current                                                                                                        
        DESCRIPTION                                                                                                                
                "The current operational state of the interface."                                                                  
        ::= { xivIfEntry 3 }                                                                                                       
                                                                                                                                   
    xivUtilizationSoft OBJECT-TYPE                                                                                                 
        SYNTAX	Gauge32                                                                                                              
        MAX-ACCESS	read-only                                                                                                        
        STATUS	current                                                                                                              
        DESCRIPTION                                                                                                                
                "The system's current capacity utilization in percents."                                                           
        ::= { xivGlobalStatus 3 }                                                                                                  
                                                                                                                                   
    xivUtilizationHard OBJECT-TYPE                                                                                                 
        SYNTAX	Gauge32                                                                                                              
        MAX-ACCESS	read-only                                                                                                        
        STATUS	current                                                                                                              
        DESCRIPTION                                                                                                                
                "The system's current capacity utilization in percents."                                                           
        ::= { xivGlobalStatus 4 }                                                                                                  
                                                                                                                                   
    xivFreeSpaceSoft OBJECT-TYPE                                                                                                   
        SYNTAX	Integer32                                                                                                            
        MAX-ACCESS	read-only                                                                                                        
        STATUS	current                                                                                                              
        DESCRIPTION                                                                                                                
                "The system's current free capacity in GB."                                                                        
        ::= { xivGlobalStatus 5 }                                                                                                  
                                                                                                                                   
    xivFreeSpaceHard OBJECT-TYPE                                                                                                   
        SYNTAX	Integer32                                                                                                            
        MAX-ACCESS	read-only                                                                                                        
        STATUS	current                                                                                                              
        DESCRIPTION                                                                                                                
                "The system's current free capacity in GB."                                                                        
        ::= { xivGlobalStatus 6 }                                                                                                  
                                                                                                                                   
    xivFailedDisks OBJECT-TYPE                                                                                                     
        SYNTAX	Integer32                                                                                                            
        MAX-ACCESS	read-only                                                                                                        
        STATUS	current                                                                                                              
        DESCRIPTION                                                                                                                
                "The number of failed disks in the system."                                                                        
        ::= { xivGlobalStatus 2 }                                                                                                  
                                                                                                                                   
    xivMachineStatus OBJECT-TYPE                                                                                                   
        SYNTAX      OCTET STRING (SIZE (1..64))                                                                                    
        MAX-ACCESS  read-only                                                                                                      
        STATUS      current                                                                                                        
        DESCRIPTION                                                                                                                
                "The current operational state of the system."                                                                     
        ::= { xivGlobalStatus 1 }                                                                                                  
                                                                                                                                   
    -- -------------------------------------                                                                                       
                                                                                                                                   
    xivEventTrapInfo OBJECT IDENTIFIER ::= { xivMachine 2 }                                                                        
                                                                                                                                   
    xivEventTrapGroup OBJECT-GROUP                                                                                                 
        OBJECTS { xivEventCode, xivEventTime, xivEventDescription,                                                                 
                  xivEventSeverity, xivEventTroubleshooting }                                                                      
        STATUS  current                                                                                                            
        DESCRIPTION                                                                                                                
                "A collection of objects providing information on the                                                              
                 events of the IBM XIV Storage System."                                                                            
        ::= { xivEventTrapInfo 100 }                                                                                               
                                                                                                                                   
    xivEventTrapNotificationGroup NOTIFICATION-GROUP                                                                               
        NOTIFICATIONS { xivTrap }                                                                                                  
        STATUS  current                                                                                                            
        DESCRIPTION                                                                                                                
                "A collection of objects providing information on the                                                              
                 notification of events of the IBM XIV Storage System."                                                            
        ::= { xivEventTrapInfo 101 }                                                                                               
                                                                                                                                   
    xivEventTrap OBJECT IDENTIFIER ::= { xivEventTrapInfo 0 }                                                                      
                                                                                                                                   
    xivTrap NOTIFICATION-TYPE                                                                                                      
        STATUS current                                                                                                             
        DESCRIPTION "An event notification"                                                                                        
        ::= { xivEventTrap 1 }                                                                                                     
                                                                                                                                   
    -- -------------------------------------                                                                                       
                                                                                                                                   
    xivEvents OBJECT IDENTIFIER ::= { xivMachine 3 }                                                                               
                                                                                                                                   
    xivEventsGroup OBJECT-GROUP                                                                                                    
        OBJECTS { xivEventCode, xivEventTime, xivEventDescription,                                                                 
                  xivEventSeverity, xivEventTroubleshooting }                                                                      
        STATUS  current                                                                                                            
        DESCRIPTION                                                                                                                
                "A collection of objects providing information on the                                                              
                 events of the IBM XIV Storage System."                                                                            
        ::= { xivEvents 100 }                                                                                                      
                                                                                                                                   
                                                                                                                                   
    -- the event table, which contains information on the entity's events                                                          
                                                                                                                                   
    xivEventTable OBJECT-TYPE                                                                                                      
        SYNTAX      SEQUENCE OF XivEventEntry                                                                                      
        MAX-ACCESS  not-accessible                                                                                                 
        STATUS      current                                                                                                        
        DESCRIPTION                                                                                                                
                "A list of event entries"                                                                                          
        ::= { xivEvents 1 }                                                                                                        
                                                                                                                                   
    xivEventEntry OBJECT-TYPE                                                                                                      
        SYNTAX      XivEventEntry                                                                                                  
        MAX-ACCESS  not-accessible                                                                                                 
        STATUS      current                                                                                                        
        DESCRIPTION                                                                                                                
                "An entry containing management information applicable to a                                                        
                particular event."                                                                                                 
        INDEX   { xivEventIndex }                                                                                                  
        ::= { xivEventTable 1 }                                                                                                    
                                                                                                                                   
    XivEventEntry ::=                                                                                                              
        SEQUENCE {                                                                                                                 
            xivEventIndex           Integer32,                                                                                     
            xivEventCode            DisplayString,                                                                                 
            xivEventTime            DisplayString,                                                                                 
            xivEventDescription     DisplayString,                                                                                 
            xivEventSeverity        INTEGER,                                                                                       
            xivEventTroubleshooting DisplayString                                                                                  
        }                                                                                                                          
                                                                                                                                   
    xivEventIndex OBJECT-TYPE                                                                                                      
        SYNTAX      Integer32 (1..1000000)                                                                                         
        MAX-ACCESS  not-accessible                                                                                                 
        STATUS      current                                                                                                        
        DESCRIPTION                                                                                                                
                "A unique value for each event."                                                                                   
        ::= { xivEventEntry 1 }                                                                                                    
                                                                                                                                   
    xivEventCode OBJECT-TYPE                                                                                                       
        SYNTAX      DisplayString (SIZE (1..64))                                                                                   
        MAX-ACCESS  read-only                                                                                                      
        STATUS      current                                                                                                        
        DESCRIPTION                                                                                                                
                "The code of the event."                                                                                           
        ::= { xivEventEntry 2 }                                                                                                    
                                                                                                                                   
    xivEventTime OBJECT-TYPE                                                                                                       
        SYNTAX      DisplayString (SIZE (1..64))                                                                                   
        MAX-ACCESS  read-only                                                                                                      
        STATUS      current                                                                                                        
        DESCRIPTION                                                                                                                
                "The time of the event."                                                                                           
        ::= { xivEventEntry 3 }                                                                                                    
                                                                                                                                   
    xivEventDescription OBJECT-TYPE                                                                                                
        SYNTAX      DisplayString                                                                                                  
        MAX-ACCESS  read-only                                                                                                      
        STATUS      current                                                                                                        
        DESCRIPTION                                                                                                                
                "The detailed description of the event."                                                                           
        ::= { xivEventEntry 4 }                                                                                                    
                                                                                                                                   
    -- changed to 1 based --                                                                                                       
    xivEventSeverity OBJECT-TYPE                                                                                                   
        SYNTAX  INTEGER {                                                                                                          
            informational(1),                                                                                                      
    		warning(2),                                                                                                                    
    		minor(3),                                                                                                                      
    		major(4),                                                                                                                      
    		critical(5)                                                                                                                    
                }                                                                                                                  
        MAX-ACCESS  read-only                                                                                                      
        STATUS      current                                                                                                        
        DESCRIPTION                                                                                                                
                "The severity of the event."                                                                                       
        ::= { xivEventEntry 5 }                                                                                                    
                                                                                                                                   
    xivEventTroubleshooting OBJECT-TYPE                                                                                            
        SYNTAX      DisplayString                                                                                                  
        MAX-ACCESS  read-only                                                                                                      
        STATUS      current                                                                                                        
        DESCRIPTION                                                                                                                
                "Trouble shooting when the event occurs."                                                                          
        ::= { xivEventEntry 6 }                                                                                                    
                                                                                                                                   
    END
