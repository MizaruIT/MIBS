-- Ericsson Television Limited Standard MIB disclaimer
-- ###################################################
-- SNMP MIBs for Ericsson Television Limited products are developed 
-- primarily for use by Ericsson Television Limited control solutions.
-- Where MIBs are provided to a third party or other non-Ericsson 
-- Television Limited person, for the purposes of their development 
-- of a non-Ericsson Television Limited control or monitoring solution, 
-- they are provided free of charge, and without obligation on the
-- part of Ericsson Television Limited to offer priority support, or
-- changes to suit the third party.
--
-- $Date: 2010-02-19 10:55:07 +0000 (Fri, 19 Feb 2010) $
-- $Revision: 194 $
--
-- ###########################################################################
-- ##  THIS FILE IS NOT TO BE DISTRIBUTED OUTSIDE Ericsson Television Limited
-- ##
-- ##  For usage see the standard practice document SP-0006-SNMP.doc
-- ##
-- ###########################################################################

ETV-AccessControl-MIB DEFINITIONS ::= BEGIN

IMPORTS
   general
     FROM ETV-Base-MIB
   DisplayString
     FROM SNMPv2-TC      
   OBJECT-TYPE, MODULE-IDENTITY
      FROM SNMPv2-SMI;

controlSystem MODULE-IDENTITY
   LAST-UPDATED "1002191052Z"
   ORGANIZATION "Ericsson Television Limited"
   CONTACT-INFO "Customer Services
                 Tel:   +44 (0) 23 8048 4455
                 Fax:   +44 (0) 23 8048 4467
                 Email: tvsupportemea@ericsson.com
                 Web:   http://www.ericsson.com/television"
   DESCRIPTION  "Access Control MIB for Ericsson Television Limited devices."
   
   REVISION "1002191052Z"
   DESCRIPTION "Updated Imported OID names and module definition name"

   REVISION "1002021211Z"
   DESCRIPTION "Updated contact information"

   REVISION "0909240825Z"
   DESCRIPTION "Updated for better complicance to SNMP V2 specs"
   
::= { general 16 }

rwUserName OBJECT-TYPE
   SYNTAX	   DisplayString (SIZE (8..64))
   MAX-ACCESS  read-write
   STATUS	   current
   DESCRIPTION
		 "User name for control system read-write access. 64 characters max."
   ::= { controlSystem 1 }

rwPassword OBJECT-TYPE
   SYNTAX	   DisplayString (SIZE (8..64))
   MAX-ACCESS  read-write
   STATUS	   current
   DESCRIPTION
		 "Password for control system read-write access. 64 characters max."
   ::= { controlSystem 2 }

roUserName OBJECT-TYPE
   SYNTAX	   DisplayString (SIZE (8..64))
   MAX-ACCESS  read-write
   STATUS	   current
   DESCRIPTION
		 "User name for control system read-only access. 64 characters max."
   ::= { controlSystem 3 }

roPassword OBJECT-TYPE
   SYNTAX	   DisplayString (SIZE (8..64))
   MAX-ACCESS  read-write
   STATUS	   current
   DESCRIPTION
		 "Password for control system read-only access. 64 characters max."
   ::= { controlSystem 4 }

END
