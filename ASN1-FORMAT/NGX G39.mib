--  Title:    NGX_G39.MIB 
--  Version:  v3.9
-- 
--  Copyright @ 2000-2003 DPS Inc. All Rights Reserved 
-- 
--  This MIB defines supplemental objects for the NGDdx points and controls.
-- 
-- 

DPS-MIB-NGX-G39 DEFINITIONS ::= BEGIN 

IMPORTS 
	dpsRTU 
		FROM DPS-MIB-V38;

dpsRTUp6001Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 1 is set." 
	::=  6001

dpsRTUp7001Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 1 clears." 
	::=  7001

dpsRTUp6002Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 2 is set." 
	::=  6002

dpsRTUp7002Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 2 clears." 
	::=  7002

dpsRTUp6003Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 3 is set." 
	::=  6003

dpsRTUp7003Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 3 clears." 
	::=  7003

dpsRTUp6004Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 4 is set." 
	::=  6004

dpsRTUp7004Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 4 clears." 
	::=  7004

dpsRTUp6005Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 5 is set." 
	::=  6005

dpsRTUp7005Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 5 clears." 
	::=  7005

dpsRTUp6006Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 6 is set." 
	::=  6006

dpsRTUp7006Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 6 clears." 
	::=  7006

dpsRTUp6007Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 7 is set." 
	::=  6007

dpsRTUp7007Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 7 clears." 
	::=  7007

dpsRTUp6008Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 8 is set." 
	::=  6008

dpsRTUp7008Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 8 clears." 
	::=  7008

dpsRTUp6009Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 9 is set." 
	::=  6009

dpsRTUp7009Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 9 clears." 
	::=  7009

dpsRTUp6010Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 10 is set." 
	::=  6010

dpsRTUp7010Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 10 clears." 
	::=  7010

dpsRTUp6011Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 11 is set." 
	::=  6011

dpsRTUp7011Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 11 clears." 
	::=  7011

dpsRTUp6012Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 12 is set." 
	::=  6012

dpsRTUp7012Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 12 clears." 
	::=  7012

dpsRTUp6013Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 13 is set." 
	::=  6013

dpsRTUp7013Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 13 clears." 
	::=  7013

dpsRTUp6014Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 14 is set." 
	::=  6014

dpsRTUp7014Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 14 clears." 
	::=  7014

dpsRTUp6015Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 15 is set." 
	::=  6015

dpsRTUp7015Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 15 clears." 
	::=  7015

dpsRTUp6016Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 16 is set." 
	::=  6016

dpsRTUp7016Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 16 clears." 
	::=  7016

dpsRTUp6017Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 17 is set." 
	::=  6017

dpsRTUp7017Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 17 clears." 
	::=  7017

dpsRTUp6018Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 18 is set." 
	::=  6018

dpsRTUp7018Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 18 clears." 
	::=  7018

dpsRTUp6019Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 19 is set." 
	::=  6019

dpsRTUp7019Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 19 clears." 
	::=  7019

dpsRTUp6020Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 20 is set." 
	::=  6020

dpsRTUp7020Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 20 clears." 
	::=  7020

dpsRTUp6021Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 21 is set." 
	::=  6021

dpsRTUp7021Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 21 clears." 
	::=  7021

dpsRTUp6022Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 22 is set." 
	::=  6022

dpsRTUp7022Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 22 clears." 
	::=  7022

dpsRTUp6023Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 23 is set." 
	::=  6023

dpsRTUp7023Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 23 clears." 
	::=  7023

dpsRTUp6024Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 24 is set." 
	::=  6024

dpsRTUp7024Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 24 clears." 
	::=  7024

dpsRTUp6025Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 25 is set." 
	::=  6025

dpsRTUp7025Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 25 clears." 
	::=  7025

dpsRTUp6026Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 26 is set." 
	::=  6026

dpsRTUp7026Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 26 clears." 
	::=  7026

dpsRTUp6027Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 27 is set." 
	::=  6027

dpsRTUp7027Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 27 clears." 
	::=  7027

dpsRTUp6028Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 28 is set." 
	::=  6028

dpsRTUp7028Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 28 clears." 
	::=  7028

dpsRTUp6029Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 29 is set." 
	::=  6029

dpsRTUp7029Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 29 clears." 
	::=  7029

dpsRTUp6030Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 30 is set." 
	::=  6030

dpsRTUp7030Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 30 clears." 
	::=  7030

dpsRTUp6031Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 31 is set." 
	::=  6031

dpsRTUp7031Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 31 clears." 
	::=  7031

dpsRTUp6032Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 32 is set." 
	::=  6032

dpsRTUp7032Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 32 clears." 
	::=  7032

dpsRTUp6033Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 33 is set." 
	::=  6033

dpsRTUp7033Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 33 clears." 
	::=  7033

dpsRTUp6034Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 34 is set." 
	::=  6034

dpsRTUp7034Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 34 clears." 
	::=  7034

dpsRTUp6035Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 35 is set." 
	::=  6035

dpsRTUp7035Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 35 clears." 
	::=  7035

dpsRTUp6036Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 36 is set." 
	::=  6036

dpsRTUp7036Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 36 clears." 
	::=  7036

dpsRTUp6037Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 37 is set." 
	::=  6037

dpsRTUp7037Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 37 clears." 
	::=  7037

dpsRTUp6038Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 38 is set." 
	::=  6038

dpsRTUp7038Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 38 clears." 
	::=  7038

dpsRTUp6039Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 39 is set." 
	::=  6039

dpsRTUp7039Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 39 clears." 
	::=  7039

dpsRTUp6040Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 40 is set." 
	::=  6040

dpsRTUp7040Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 40 clears." 
	::=  7040

dpsRTUp6041Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 41 is set." 
	::=  6041

dpsRTUp7041Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 41 clears." 
	::=  7041

dpsRTUp6042Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 42 is set." 
	::=  6042

dpsRTUp7042Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 42 clears." 
	::=  7042

dpsRTUp6043Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 43 is set." 
	::=  6043

dpsRTUp7043Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 43 clears." 
	::=  7043

dpsRTUp6044Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 44 is set." 
	::=  6044

dpsRTUp7044Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 44 clears." 
	::=  7044

dpsRTUp6045Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 45 is set." 
	::=  6045

dpsRTUp7045Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 45 clears." 
	::=  7045

dpsRTUp6046Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 46 is set." 
	::=  6046

dpsRTUp7046Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 46 clears." 
	::=  7046

dpsRTUp6047Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 47 is set." 
	::=  6047

dpsRTUp7047Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 47 clears." 
	::=  7047

dpsRTUp6048Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 48 is set." 
	::=  6048

dpsRTUp7048Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx1 point 48 clears." 
	::=  7048

dpsRTUp6129Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 1 is set." 
	::=  6129

dpsRTUp7129Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 1 clears." 
	::=  7129

dpsRTUp6130Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 2 is set." 
	::=  6130

dpsRTUp7130Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 2 clears." 
	::=  7130

dpsRTUp6131Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 3 is set." 
	::=  6131

dpsRTUp7131Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 3 clears." 
	::=  7131

dpsRTUp6132Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 4 is set." 
	::=  6132

dpsRTUp7132Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 4 clears." 
	::=  7132

dpsRTUp6133Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 5 is set." 
	::=  6133

dpsRTUp7133Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 5 clears." 
	::=  7133

dpsRTUp6134Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 6 is set." 
	::=  6134

dpsRTUp7134Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 6 clears." 
	::=  7134

dpsRTUp6135Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 7 is set." 
	::=  6135

dpsRTUp7135Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 7 clears." 
	::=  7135

dpsRTUp6136Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 8 is set." 
	::=  6136

dpsRTUp7136Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 8 clears." 
	::=  7136

dpsRTUp6137Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 9 is set." 
	::=  6137

dpsRTUp7137Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 9 clears." 
	::=  7137

dpsRTUp6138Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 10 is set." 
	::=  6138

dpsRTUp7138Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 10 clears." 
	::=  7138

dpsRTUp6139Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 11 is set." 
	::=  6139

dpsRTUp7139Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 11 clears." 
	::=  7139

dpsRTUp6140Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 12 is set." 
	::=  6140

dpsRTUp7140Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 12 clears." 
	::=  7140

dpsRTUp6141Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 13 is set." 
	::=  6141

dpsRTUp7141Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 13 clears." 
	::=  7141

dpsRTUp6142Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 14 is set." 
	::=  6142

dpsRTUp7142Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 14 clears." 
	::=  7142

dpsRTUp6143Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 15 is set." 
	::=  6143

dpsRTUp7143Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 15 clears." 
	::=  7143

dpsRTUp6144Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 16 is set." 
	::=  6144

dpsRTUp7144Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 16 clears." 
	::=  7144

dpsRTUp6145Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 17 is set." 
	::=  6145

dpsRTUp7145Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 17 clears." 
	::=  7145

dpsRTUp6146Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 18 is set." 
	::=  6146

dpsRTUp7146Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 18 clears." 
	::=  7146

dpsRTUp6147Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 19 is set." 
	::=  6147

dpsRTUp7147Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 19 clears." 
	::=  7147

dpsRTUp6148Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 20 is set." 
	::=  6148

dpsRTUp7148Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 20 clears." 
	::=  7148

dpsRTUp6149Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 21 is set." 
	::=  6149

dpsRTUp7149Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 21 clears." 
	::=  7149

dpsRTUp6150Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 22 is set." 
	::=  6150

dpsRTUp7150Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 22 clears." 
	::=  7150

dpsRTUp6151Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 23 is set." 
	::=  6151

dpsRTUp7151Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 23 clears." 
	::=  7151

dpsRTUp6152Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 24 is set." 
	::=  6152

dpsRTUp7152Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 24 clears." 
	::=  7152

dpsRTUp6153Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 25 is set." 
	::=  6153

dpsRTUp7153Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 25 clears." 
	::=  7153

dpsRTUp6154Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 26 is set." 
	::=  6154

dpsRTUp7154Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 26 clears." 
	::=  7154

dpsRTUp6155Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 27 is set." 
	::=  6155

dpsRTUp7155Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 27 clears." 
	::=  7155

dpsRTUp6156Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 28 is set." 
	::=  6156

dpsRTUp7156Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 28 clears." 
	::=  7156

dpsRTUp6157Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 29 is set." 
	::=  6157

dpsRTUp7157Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 29 clears." 
	::=  7157

dpsRTUp6158Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 30 is set." 
	::=  6158

dpsRTUp7158Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 30 clears." 
	::=  7158

dpsRTUp6159Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 31 is set." 
	::=  6159

dpsRTUp7159Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 31 clears." 
	::=  7159

dpsRTUp6160Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 32 is set." 
	::=  6160

dpsRTUp7160Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 32 clears." 
	::=  7160

dpsRTUp6161Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 33 is set." 
	::=  6161

dpsRTUp7161Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 33 clears." 
	::=  7161

dpsRTUp6162Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 34 is set." 
	::=  6162

dpsRTUp7162Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 34 clears." 
	::=  7162

dpsRTUp6163Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 35 is set." 
	::=  6163

dpsRTUp7163Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 35 clears." 
	::=  7163

dpsRTUp6164Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 36 is set." 
	::=  6164

dpsRTUp7164Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 36 clears." 
	::=  7164

dpsRTUp6165Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 37 is set." 
	::=  6165

dpsRTUp7165Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 37 clears." 
	::=  7165

dpsRTUp6166Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 38 is set." 
	::=  6166

dpsRTUp7166Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 38 clears." 
	::=  7166

dpsRTUp6167Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 39 is set." 
	::=  6167

dpsRTUp7167Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 39 clears." 
	::=  7167

dpsRTUp6168Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 40 is set." 
	::=  6168

dpsRTUp7168Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 40 clears." 
	::=  7168

dpsRTUp6169Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 41 is set." 
	::=  6169

dpsRTUp7169Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 41 clears." 
	::=  7169

dpsRTUp6170Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 42 is set." 
	::=  6170

dpsRTUp7170Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 42 clears." 
	::=  7170

dpsRTUp6171Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 43 is set." 
	::=  6171

dpsRTUp7171Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 43 clears." 
	::=  7171

dpsRTUp6172Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 44 is set." 
	::=  6172

dpsRTUp7172Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 44 clears." 
	::=  7172

dpsRTUp6173Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 45 is set." 
	::=  6173

dpsRTUp7173Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 45 clears." 
	::=  7173

dpsRTUp6174Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 46 is set." 
	::=  6174

dpsRTUp7174Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 46 clears." 
	::=  7174

dpsRTUp6175Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 47 is set." 
	::=  6175

dpsRTUp7175Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 47 clears." 
	::=  7175

dpsRTUp6176Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 48 is set." 
	::=  6176

dpsRTUp7176Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx2 point 48 clears." 
	::=  7176

dpsRTUp6257Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 1 is set." 
	::=  6257

dpsRTUp7257Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 1 clears." 
	::=  7257

dpsRTUp6258Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 2 is set." 
	::=  6258

dpsRTUp7258Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 2 clears." 
	::=  7258

dpsRTUp6259Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 3 is set." 
	::=  6259

dpsRTUp7259Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 3 clears." 
	::=  7259

dpsRTUp6260Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 4 is set." 
	::=  6260

dpsRTUp7260Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 4 clears." 
	::=  7260

dpsRTUp6261Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 5 is set." 
	::=  6261

dpsRTUp7261Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 5 clears." 
	::=  7261

dpsRTUp6262Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 6 is set." 
	::=  6262

dpsRTUp7262Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 6 clears." 
	::=  7262

dpsRTUp6263Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 7 is set." 
	::=  6263

dpsRTUp7263Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 7 clears." 
	::=  7263

dpsRTUp6264Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 8 is set." 
	::=  6264

dpsRTUp7264Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 8 clears." 
	::=  7264

dpsRTUp6265Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 9 is set." 
	::=  6265

dpsRTUp7265Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 9 clears." 
	::=  7265

dpsRTUp6266Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 10 is set." 
	::=  6266

dpsRTUp7266Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 10 clears." 
	::=  7266

dpsRTUp6267Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 11 is set." 
	::=  6267

dpsRTUp7267Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 11 clears." 
	::=  7267

dpsRTUp6268Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 12 is set." 
	::=  6268

dpsRTUp7268Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 12 clears." 
	::=  7268

dpsRTUp6269Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 13 is set." 
	::=  6269

dpsRTUp7269Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 13 clears." 
	::=  7269

dpsRTUp6270Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 14 is set." 
	::=  6270

dpsRTUp7270Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 14 clears." 
	::=  7270

dpsRTUp6271Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 15 is set." 
	::=  6271

dpsRTUp7271Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 15 clears." 
	::=  7271

dpsRTUp6272Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 16 is set." 
	::=  6272

dpsRTUp7272Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 16 clears." 
	::=  7272

dpsRTUp6273Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 17 is set." 
	::=  6273

dpsRTUp7273Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 17 clears." 
	::=  7273

dpsRTUp6274Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 18 is set." 
	::=  6274

dpsRTUp7274Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 18 clears." 
	::=  7274

dpsRTUp6275Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 19 is set." 
	::=  6275

dpsRTUp7275Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 19 clears." 
	::=  7275

dpsRTUp6276Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 20 is set." 
	::=  6276

dpsRTUp7276Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 20 clears." 
	::=  7276

dpsRTUp6277Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 21 is set." 
	::=  6277

dpsRTUp7277Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 21 clears." 
	::=  7277

dpsRTUp6278Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 22 is set." 
	::=  6278

dpsRTUp7278Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 22 clears." 
	::=  7278

dpsRTUp6279Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 23 is set." 
	::=  6279

dpsRTUp7279Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 23 clears." 
	::=  7279

dpsRTUp6280Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 24 is set." 
	::=  6280

dpsRTUp7280Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 24 clears." 
	::=  7280

dpsRTUp6281Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 25 is set." 
	::=  6281

dpsRTUp7281Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 25 clears." 
	::=  7281

dpsRTUp6282Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 26 is set." 
	::=  6282

dpsRTUp7282Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 26 clears." 
	::=  7282

dpsRTUp6283Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 27 is set." 
	::=  6283

dpsRTUp7283Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 27 clears." 
	::=  7283

dpsRTUp6284Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 28 is set." 
	::=  6284

dpsRTUp7284Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 28 clears." 
	::=  7284

dpsRTUp6285Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 29 is set." 
	::=  6285

dpsRTUp7285Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 29 clears." 
	::=  7285

dpsRTUp6286Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 30 is set." 
	::=  6286

dpsRTUp7286Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 30 clears." 
	::=  7286

dpsRTUp6287Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 31 is set." 
	::=  6287

dpsRTUp7287Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 31 clears." 
	::=  7287

dpsRTUp6288Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 32 is set." 
	::=  6288

dpsRTUp7288Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 32 clears." 
	::=  7288

dpsRTUp6289Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 33 is set." 
	::=  6289

dpsRTUp7289Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 33 clears." 
	::=  7289

dpsRTUp6290Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 34 is set." 
	::=  6290

dpsRTUp7290Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 34 clears." 
	::=  7290

dpsRTUp6291Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 35 is set." 
	::=  6291

dpsRTUp7291Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 35 clears." 
	::=  7291

dpsRTUp6292Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 36 is set." 
	::=  6292

dpsRTUp7292Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 36 clears." 
	::=  7292

dpsRTUp6293Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 37 is set." 
	::=  6293

dpsRTUp7293Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 37 clears." 
	::=  7293

dpsRTUp6294Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 38 is set." 
	::=  6294

dpsRTUp7294Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 38 clears." 
	::=  7294

dpsRTUp6295Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 39 is set." 
	::=  6295

dpsRTUp7295Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 39 clears." 
	::=  7295

dpsRTUp6296Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 40 is set." 
	::=  6296

dpsRTUp7296Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 40 clears." 
	::=  7296

dpsRTUp6297Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 41 is set." 
	::=  6297

dpsRTUp7297Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 41 clears." 
	::=  7297

dpsRTUp6298Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 42 is set." 
	::=  6298

dpsRTUp7298Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 42 clears." 
	::=  7298

dpsRTUp6299Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 43 is set." 
	::=  6299

dpsRTUp7299Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 43 clears." 
	::=  7299

dpsRTUp6300Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 44 is set." 
	::=  6300

dpsRTUp7300Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 44 clears." 
	::=  7300

dpsRTUp6301Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 45 is set." 
	::=  6301

dpsRTUp7301Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 45 clears." 
	::=  7301

dpsRTUp6302Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 46 is set." 
	::=  6302

dpsRTUp7302Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 46 clears." 
	::=  7302

dpsRTUp6303Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 47 is set." 
	::=  6303

dpsRTUp7303Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 47 clears." 
	::=  7303

dpsRTUp6304Set TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 48 is set." 
	::=  6304

dpsRTUp7304Clr TRAP-TYPE 
	ENTERPRISE	dpsRTU
	VARIABLES {	sysDescr, sysLocation, dpsRTUDateTime, 
					dpsRTUAPort, dpsRTUCAddress, dpsRTUADisplay, dpsRTUAPoint, 
					dpsRTUAPntDesc, dpsRTUAState } 
	DESCRIPTION "Generated when NGDdx3 point 48 clears." 
	::=  7304

dpsRTUp6065Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 1 is latched."
	::=  6065

dpsRTUp7065Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 1 is released."
	::=  7065

dpsRTUp6066Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 2 is latched."
	::=  6066

dpsRTUp7066Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 2 is released."
	::=  7066

dpsRTUp6067Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 3 is latched."
	::=  6067

dpsRTUp7067Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 3 is released."
	::=  7067

dpsRTUp6068Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 4 is latched."
	::=  6068

dpsRTUp7068Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 4 is released."
	::=  7068

dpsRTUp6069Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 5 is latched."
	::=  6069

dpsRTUp7069Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 5 is released."
	::=  7069

dpsRTUp6070Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 6 is latched."
	::=  6070

dpsRTUp7070Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 6 is released."
	::=  7070

dpsRTUp6071Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 7 is latched."
	::=  6071

dpsRTUp7071Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 7 is released."
	::=  7071

dpsRTUp6072Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 8 is latched."
	::=  6072

dpsRTUp7072Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx1 control 8 is released."
	::=  7072

dpsRTUp6193Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 1 is latched."
	::=  6193

dpsRTUp7193Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 1 is released."
	::=  7193

dpsRTUp6194Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 2 is latched."
	::=  6194

dpsRTUp7194Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 2 is released."
	::=  7194

dpsRTUp6195Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 3 is latched."
	::=  6195

dpsRTUp7195Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 3 is released."
	::=  7195

dpsRTUp6196Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 4 is latched."
	::=  6196

dpsRTUp7196Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 4 is released."
	::=  7196

dpsRTUp6197Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 5 is latched."
	::=  6197

dpsRTUp7197Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 5 is released."
	::=  7197

dpsRTUp6198Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 6 is latched."
	::=  6198

dpsRTUp7198Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 6 is released."
	::=  7198

dpsRTUp6199Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 7 is latched."
	::=  6199

dpsRTUp7199Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 7 is released."
	::=  7199

dpsRTUp6200Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 8 is latched."
	::=  6200

dpsRTUp7200Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx2 control 8 is released."
	::=  7200

dpsRTUp6321Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 1 is latched."
	::=  6321

dpsRTUp7321Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 1 is released."
	::=  7321

dpsRTUp6322Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 2 is latched."
	::=  6322

dpsRTUp7322Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 2 is released."
	::=  7322

dpsRTUp6323Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 3 is latched."
	::=  6323

dpsRTUp7323Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 3 is released."
	::=  7323

dpsRTUp6324Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 4 is latched."
	::=  6324

dpsRTUp7324Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 4 is released."
	::=  7324

dpsRTUp6325Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 5 is latched."
	::=  6325

dpsRTUp7325Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 5 is released."
	::=  7325

dpsRTUp6326Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 6 is latched."
	::=  6326

dpsRTUp7326Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 6 is released."
	::=  7326

dpsRTUp6327Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 7 is latched."
	::=  6327

dpsRTUp7327Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 7 is released."
	::=  7327

dpsRTUp6328Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 8 is latched."
	::=  6328

dpsRTUp7328Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when NGDdx3 control 8 is released."
	::=  7328

END
