HUAWEI-VLAN-IF-MIB DEFINITIONS ::= BEGIN

		IMPORTS 
			huaweiMgmt			
				FROM HUAWEI-MIB			
			ifIndex			
				FROM IF-MIB			
			TimeTicks, IpAddress, Unsigned32, OBJECT-TYPE, MODULE-IDENTITY, 
			OBJECT-IDENTITY			
				FROM SNMPv2-SMI			
			TruthValue, RowStatus, TEXTUAL-CONVENTION			
				FROM SNMPv2-TC;
	
	
		hwVlan MODULE-IDENTITY
			LAST-UPDATED "200211290900Z"
			ORGANIZATION
				"HAUWEI MIB Standard community
 				 "
			CONTACT-INFO
				"
				ADDR：HUAWEI TECHNOLOGY CO.,LTD,SHEZHEN CHINA
				Tel： 86-755-26540808
				"
			DESCRIPTION
				"
				V2.00		
				reunification version based on the  Fix-Net MIBs baseline by the MIB Standard community.
						
				固网所有标准MIB统一基线化，为便于管理统一升级为2.0版本发布。
				"
			::= { huaweiMgmt 6 }
		
	

	
		VlanIndex ::= TEXTUAL-CONVENTION
			STATUS current
			DESCRIPTION
				"A value used to index per-VLAN tables: values of 0 and
				4095 are not permitted; if the value is between 1 and
				4094 inclusive, it represents an IEEE 802.1Q VLAN-ID with
				global scope within a given bridged domain (see VlanId
				textual convention).  If the value is greater than 4095
				then it represents a VLAN with scope local to the
				particular agent, i.e. one without a global VLAN-ID
				assigned to it. Such VLANs are outside the scope of
				IEEE 802.1Q but it is convenient to be able to manage them
				in the same way using this MIB."
			SYNTAX Unsigned32
			
		SnmpAdminString ::= TEXTUAL-CONVENTION
			DISPLAY-HINT
				"255a"
			STATUS current
			DESCRIPTION
				"An octet string containing administrative
				information, preferably in human-readable form.
				
				To facilitate internationalization, this
				information is represented using the ISO/IEC
				IS 10646-1 character set, encoded as an octet
				string using the UTF-8 transformation format
				described in [RFC2279].
				
				Since additional code points are added by
				amendments to the 10646 standard from time
				to time, implementations must be prepared to
				encounter any code point from 0x00000000 to
				0x7fffffff.  Byte sequences that do not
				correspond to the valid UTF-8 encoding of a
				code point or are outside this range are
				prohibited.
				
				The use of control codes should be avoided.
				
				When it is necessary to represent a newline,
				the control code sequence CR LF should be used.
				
				The use of leading or trailing white space should
				be avoided.
				
				For code points not directly supported by user
				interface hardware or software, an alternative
				means of entry and display, such as hexadecimal,
				may be provided.
				
				For information encoded in 7-bit US-ASCII,
				the UTF-8 encoding is identical to the
				US-ASCII encoding.
				
				UTF-8 may require multiple bytes to represent a
				single character / code point; thus the length
				of this object in octets may be different from
				the number of characters encoded.  Similarly,
				size constraints refer to the number of encoded
				octets, not the number of characters represented
				by an encoding.
				
				Note that when this TC is used for an object that
				is used or envisioned to be used as an index, then
				a SIZE restriction MUST be specified so that the
				number of sub-identifiers for any object instance
				does not exceed the limit of 128, as defined by
				[RFC1905].
				
				Note that the size of an SnmpAdminString object is
				measured in octets, not characters.
				"
			SYNTAX OCTET STRING (SIZE (0..255))
			
		PortList ::= TEXTUAL-CONVENTION
			STATUS current
			DESCRIPTION
				"Each octet within this value specifies a set of eight
				ports, with the first octet specifying ports 1 through
				8, the second octet specifying ports 9 through 16, etc.
				Within each octet, the most significant bit represents
				the lowest numbered port, and the least significant bit
				represents the highest numbered port.  Thus, each port
				of the bridge is represented by a single bit within the
				value of this object.  If that bit has a value of '1'
				then that port is included in the set of ports; the port
				is not included if its bit has a value of '0'."
			SYNTAX OCTET STRING
			
	

	
		hwVlanMngObject OBJECT-IDENTITY
			STATUS current
			DESCRIPTION
				"Vlan Object
				
				Vlan管理对象."
			::= { hwVlan 1 }
		
	
		hwVlanInterfaceTable OBJECT-TYPE
			SYNTAX SEQUENCE OF HwVlanInterfaceEntry
			MAX-ACCESS not-accessible
			STATUS current
			DESCRIPTION
				" vlan interface table
				
				虚接口配置表  "
			::= { hwVlanMngObject 2 }
		
		hwVlanInterfaceEntry OBJECT-TYPE
			SYNTAX HwVlanInterfaceEntry
			MAX-ACCESS not-accessible
			STATUS current
			DESCRIPTION
				"vlan interface entry
				
				 虚接口配置表实体  "
			INDEX { hwVlanInterfaceID }
			::= { hwVlanInterfaceTable 1 }
		
		HwVlanInterfaceEntry ::=
			SEQUENCE { 
				hwVlanInterfaceID
					INTEGER,
				hwVlanID
					INTEGER,
				hwVlanIpAddress
					IpAddress,
				hwVlanIpAddressMask
					IpAddress,
				hwVlanInterfaceAdminStatus
					INTEGER,
				hwVlanInterfaceFrameType
					INTEGER,
				hwInterfaceRowStatus
					RowStatus
			 }

		hwVlanInterfaceID OBJECT-TYPE
			SYNTAX INTEGER
			MAX-ACCESS read-only
			STATUS current
			DESCRIPTION
				"vlan interface id
				
				 VLAN虚接口索引 "
			::= { hwVlanInterfaceEntry 1 }
		
		hwVlanID OBJECT-TYPE
			SYNTAX INTEGER
			MAX-ACCESS read-only
			STATUS current
			DESCRIPTION
				"vlan id
				
				 VLANID "
			::= { hwVlanInterfaceEntry 2 }
		
		hwVlanIpAddress OBJECT-TYPE
			SYNTAX IpAddress
			MAX-ACCESS read-write
			STATUS current
			DESCRIPTION
				"vlan ip address
				
				 接口IP地址 "
			::= { hwVlanInterfaceEntry 3 }
		
		hwVlanIpAddressMask OBJECT-TYPE
			SYNTAX IpAddress
			MAX-ACCESS read-write
			STATUS current
			DESCRIPTION
				"vlan ip mask address
				
				 接口IP地址掩码 "
			::= { hwVlanInterfaceEntry 4 }
		
		hwVlanInterfaceAdminStatus OBJECT-TYPE
			SYNTAX INTEGER
				{
				up(1),
				down(2)
				}
			MAX-ACCESS read-write
			STATUS current
			DESCRIPTION
				"vlan interface admin status
				
				 VLAN虚接口的状态 "
			::= { hwVlanInterfaceEntry 5 }
		
		hwVlanInterfaceFrameType OBJECT-TYPE
			SYNTAX INTEGER
				{
				ethernetii(1),
				ethernetsnap(2),
				ethernet8022(3),
				ethernet8023(4)
				}
			MAX-ACCESS read-write
			STATUS current
			DESCRIPTION
				"vlan interface frame type
				
				 VLAN虚接口可以接受的帧类型 "
			::= { hwVlanInterfaceEntry 6 }
		
		hwInterfaceRowStatus OBJECT-TYPE
			SYNTAX RowStatus
			MAX-ACCESS read-create
			STATUS current
			DESCRIPTION
				" row admin status
				
				操作状态 "
			::= { hwVlanInterfaceEntry 7 }
		
		hwVlanInterfaceSubIpAddrTable OBJECT-TYPE
			SYNTAX SEQUENCE OF HwVlanInterfaceSubIpAddrEntry
			MAX-ACCESS not-accessible
			STATUS current
			DESCRIPTION
				" vlan interfacesubipaddr table
				
				虚接口从IP地址配置表  "
			::= { hwVlanMngObject 9 }
		
		hwVlanInterfaceSubIpAddrEntry OBJECT-TYPE
			SYNTAX HwVlanInterfaceSubIpAddrEntry
			MAX-ACCESS not-accessible
			STATUS current
			DESCRIPTION
				"vlan interfacesubipaddr entry
				
				 虚接口配置表实体  "
			INDEX { hwVlanInterfaceIDWithSub, hwVlanSubIpAddress, hwVlanSubIpAddressMask}
			::= { hwVlanInterfaceSubIpAddrTable 1 }
		
		HwVlanInterfaceSubIpAddrEntry ::=
			SEQUENCE { 
				hwVlanInterfaceIDWithSub
				  	  INTEGER,
				hwVlanSubIpAddress
					IpAddress,
				hwVlanSubIpAddressMask
					IpAddress,
				hwInterfaceSubIpAddrRowStatus
					RowStatus
			 }
		
		hwVlanInterfaceIDWithSub OBJECT-TYPE
			SYNTAX INTEGER
			MAX-ACCESS read-only
			STATUS current
			DESCRIPTION
				"vlan interface id
				
				 VLAN虚接口索引 "
			::= { hwVlanInterfaceSubIpAddrEntry 1 }		
		
		hwVlanSubIpAddress OBJECT-TYPE
			SYNTAX IpAddress
			MAX-ACCESS read-only
			STATUS current
			DESCRIPTION
				"vlan sub ip address
				
				 接口从IP地址 "
			::= { hwVlanInterfaceSubIpAddrEntry 2 }
		
		hwVlanSubIpAddressMask OBJECT-TYPE
			SYNTAX IpAddress
			MAX-ACCESS read-only
			STATUS current
			DESCRIPTION
				"vlan sub ip mask address
				
				 接口从IP地址掩码 "
			::= { hwVlanInterfaceSubIpAddrEntry 3 }
	
		hwInterfaceSubIpAddrRowStatus OBJECT-TYPE
			SYNTAX RowStatus
			MAX-ACCESS read-create
			STATUS current
			DESCRIPTION
				" row admin status
				
				操作状态 "
			::= { hwVlanInterfaceSubIpAddrEntry 4 }
			
	END
