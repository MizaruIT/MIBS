--
-- OPTIX-SDH-PER-MIB.mib
-- MIB generated by MG-SOFT Visual MIB Builder Version 3.0 Build 253
-- Thursday, June 29, 2006 at 14:57:04
--

	OPTIX-SDH-PER-MIB DEFINITIONS ::= BEGIN
 
		IMPORTS
			optixCommonSdh			
				FROM OPTIX-OID-MIB			
			SdhPerformanceEventType			
				FROM OPTIX-SDH-TC-MIB			
			OBJECT-GROUP, MODULE-COMPLIANCE			
				FROM SNMPv2-CONF			
			mgmt, Gauge32, OBJECT-TYPE, MODULE-IDENTITY			
				FROM SNMPv2-SMI			
			DateAndTime			
				FROM SNMPv2-TC;
	
	
		optixPerformance MODULE-IDENTITY 
			LAST-UPDATED "200604141635Z"		-- April 14, 2006 at 16:35 GMT
			ORGANIZATION 
				"Huawei Technologies co.,Ltd."
			CONTACT-INFO 
				"R&D Building
				Huawei Technologies Co., Ltd.
				Bantian, Longgang District 
				Shenzhen, P. R. China
				http://www.huawei.com
				Zip:518129
				E-mail:support@huawei.com"
			DESCRIPTION 
				"This module MIB describes the Optix Perfomance."
			REVISION "200604151158Z"		-- April 15, 2006 at 11:58 GMT
			DESCRIPTION
				"The initial revision of this MIB module."
			::= { optixCommonSdh 20 }
		
	
--
-- Type definitions
--
	
		RowStatus ::= INTEGER
			{
			active(1),
			notInService(2),
			notReady(3),
			createAndGo(4),
			createAndWait(5),
			destroy(6)
			}
		
	
--
-- Node definitions
--
	
--  -------------------------------------------------------------------------
-- Node Object Identity
-- -------------------------------------------------------------------------
		-- 1.3.6.1.4.1.2011.2.25.3.10.20.10
		perMonitorTime OBJECT IDENTIFIER ::= { optixPerformance 10 }
		
--  Event report event(REP)
		-- 1.3.6.1.4.1.2011.2.25.3.10.20.10.10
		per15mMonitorTime OBJECT IDENTIFIER ::= { perMonitorTime 10 }
		
-- -------------------------------------------------------------------------
-- Date and time of PM 15 minutes(or one day) period beginning( or end)
-- -------------------------------------------------------------------------
		-- 1.3.6.1.4.1.2011.2.25.3.10.20.10.10.10
		per15mMonitorStartTime OBJECT-TYPE
			SYNTAX DateAndTime
			MAX-ACCESS read-write
			STATUS current
			DESCRIPTION
				"Start date and time of 15 minutes PM period.When system enter 
				the per15mMonitorStartTime,15 minutes PM starts.the 
				per15mMonitorStartTime should not ealier than current date and time,
				specially,when it is equal to 1990-00-00 00:00:00,15 minutes PM 
				starts immediately.reset the per15mMonitorStartTime will terminate
				current 15 minutes PM period.When system enter the per15mMonitorEndTime,
				the per15mMonitorStartTime will be reset to zero."
			::= { per15mMonitorTime 10 }
		
		-- 1.3.6.1.4.1.2011.2.25.3.10.20.10.10.20
		per15mMonitorEndTime OBJECT-TYPE
			SYNTAX DateAndTime
			MAX-ACCESS read-write
			STATUS current
			DESCRIPTION
				"End date and time of 15 minutes PM period.you need set the 
				per15mMonitorStartTime before set the per15mMonitorEndTime,and 
				per15mMonitorStartTime should earlier than the 
				per15mMonitorEndTime,specially,when the  per15mMonitorEndTime 
				is equal to 1990-00-00 00:00:00,15 minutes PM ends immediately.
				When system enter the per15mMonitorEndTime,the 
				per15mMonitorEndTime will be reset to zero."
			::= { per15mMonitorTime 20 }
		
--  date and time of 15 minutes PM period
		-- 1.3.6.1.4.1.2011.2.25.3.10.20.10.20
		per24hMonitorTime OBJECT IDENTIFIER ::= { perMonitorTime 20 }
		
		-- 1.3.6.1.4.1.2011.2.25.3.10.20.10.20.10
		per24hMonitorStartTime OBJECT-TYPE
			SYNTAX DateAndTime
			MAX-ACCESS read-write
			STATUS current
			DESCRIPTION
				"Start date and time of one day PM period.When system enter 
				the per24hMonitorStartTime,one day PM starts.the 
				per24hMonitorStartTime should not ealier than current date and time,
				specially,when it is equal to 1990-00-00 00:00:00,one day PM 
				starts immediately.reset the per24hMonitorStartTime will terminate
				current one day PM period.When system enter the per24hMonitorEndTime,
				the per24hMonitorStartTime will be reset to zero."
			::= { per24hMonitorTime 10 }
		
		-- 1.3.6.1.4.1.2011.2.25.3.10.20.10.20.20
		per24hMonitorEndTime OBJECT-TYPE
			SYNTAX DateAndTime
			MAX-ACCESS read-write
			STATUS current
			DESCRIPTION
				"End date and time of one day PM period.you need set the 
				per24hMonitorStartTime before set the per24hMonitorEndTime,and 
				per24hMonitorStartTime should earlier than the 
				per24hMonitorEndTime,specially,when the  per24hMonitorEndTime 
				is equal to 1990-00-00 00:00:00,one day PM ends immediately.
				When system enter the per24hMonitorEndTime,the 
				per24hMonitorEndTime will be reset to zero."
			::= { per24hMonitorTime 20 }
		
--  Performance monitor date and time
		-- 1.3.6.1.4.1.2011.2.25.3.10.20.20
		perMonitorData OBJECT IDENTIFIER ::= { optixPerformance 20 }
		
--  date and time of one day PM period
		-- 1.3.6.1.4.1.2011.2.25.3.10.20.20.10
		per15mMonitoring OBJECT IDENTIFIER ::= { perMonitorData 10 }
		
--  -------------------------------------------------------------------------
-- 15 minutes PM period current data table
-- 
-- -------------------------------------------------------------------------
		-- 1.3.6.1.4.1.2011.2.25.3.10.20.20.10.10
		per15mCurrentDataTable OBJECT-TYPE
			SYNTAX SEQUENCE OF Per15mCurrentDataEntry
			MAX-ACCESS not-accessible
			STATUS current
			DESCRIPTION
				"15 minutes PM period current data table"
			::= { per15mMonitoring 10 }
		
		-- 1.3.6.1.4.1.2011.2.25.3.10.20.20.10.10.1
		per15mCurrentDataEntry OBJECT-TYPE
			SYNTAX Per15mCurrentDataEntry
			MAX-ACCESS not-accessible
			STATUS current
			DESCRIPTION
				"15 minutes PM period current data entry"
			INDEX { per15mCurrentDataBoardNo, per15mCurrentDataOpticalPort, per15mCurrentDataPathNumber, per15mCurrentDataEventID }
			::= { per15mCurrentDataTable 1 }
		
		Per15mCurrentDataEntry ::=
			SEQUENCE { 
				per15mCurrentDataBoardNo
					Gauge32,
				per15mCurrentDataOpticalPort
					Gauge32,
				per15mCurrentDataPathNumber
					Gauge32,
				per15mCurrentDataEventID
					SdhPerformanceEventType,
				per15mCurrentDataStartTime
					DateAndTime,
				per15mCurrentDataValue
					Gauge32,
				per15mCurrentDataReset
					INTEGER
			 }

		-- 1.3.6.1.4.1.2011.2.25.3.10.20.20.10.10.1.1
		per15mCurrentDataBoardNo OBJECT-TYPE
			SYNTAX Gauge32
			MAX-ACCESS read-only
			STATUS current
			DESCRIPTION
				"Card No.:between 1 and 20"
			::= { per15mCurrentDataEntry 1 }
		
		-- 1.3.6.1.4.1.2011.2.25.3.10.20.20.10.10.1.2
		per15mCurrentDataOpticalPort OBJECT-TYPE
			SYNTAX Gauge32
			MAX-ACCESS read-only
			STATUS current
			DESCRIPTION
				"Optical port No.:values depend on type of card"
			::= { per15mCurrentDataEntry 2 }
		
		-- 1.3.6.1.4.1.2011.2.25.3.10.20.20.10.10.1.3
		per15mCurrentDataPathNumber OBJECT-TYPE
			SYNTAX Gauge32
			MAX-ACCESS read-only
			STATUS current
			DESCRIPTION
				"Path No.:values depend on type of card"
			::= { per15mCurrentDataEntry 3 }
		
		-- 1.3.6.1.4.1.2011.2.25.3.10.20.20.10.10.1.4
		per15mCurrentDataEventID OBJECT-TYPE
			SYNTAX SdhPerformanceEventType
			MAX-ACCESS read-only
			STATUS current
			DESCRIPTION
				"Event ID:values depend on type of card"
			::= { per15mCurrentDataEntry 4 }
		
		-- 1.3.6.1.4.1.2011.2.25.3.10.20.20.10.10.1.5
		per15mCurrentDataStartTime OBJECT-TYPE
			SYNTAX DateAndTime
			MAX-ACCESS read-only
			STATUS current
			DESCRIPTION
				"start date and time: start date and time of current 15 minutes PM period."
			::= { per15mCurrentDataEntry 5 }
		
		-- 1.3.6.1.4.1.2011.2.25.3.10.20.20.10.10.1.6
		per15mCurrentDataValue OBJECT-TYPE
			SYNTAX Gauge32
			MAX-ACCESS read-only
			STATUS current
			DESCRIPTION
				"Current data value: value of current 15 minutes PM period register.the units
				of value vary as the PM event,fo example,the unit of RSUAS is 'second',while 
				the unit of RSBBE is 'count'."
			::= { per15mCurrentDataEntry 6 }
		
		-- 1.3.6.1.4.1.2011.2.25.3.10.20.20.10.10.1.7
		per15mCurrentDataReset OBJECT-TYPE
			SYNTAX INTEGER { reset(1) }
			MAX-ACCESS read-write
			STATUS current
			DESCRIPTION
				"Current data reset: reset value of current 15 minutes PM period register to zero."
			::= { per15mCurrentDataEntry 7 }
		
--  -------------------------------------------------------------------------
-- 15 minutes PM period historic data table
-- 
-- -------------------------------------------------------------------------
		-- 1.3.6.1.4.1.2011.2.25.3.10.20.20.10.20
		per15mHistoryDataTable OBJECT-TYPE
			SYNTAX SEQUENCE OF Per15mHistoryDataEntry
			MAX-ACCESS not-accessible
			STATUS current
			DESCRIPTION
				"15 minutes PM period historic data table"
			::= { per15mMonitoring 20 }
		
		-- 1.3.6.1.4.1.2011.2.25.3.10.20.20.10.20.1
		per15mHistoryDataEntry OBJECT-TYPE
			SYNTAX Per15mHistoryDataEntry
			MAX-ACCESS not-accessible
			STATUS current
			DESCRIPTION
				"15 minutes PM period historic data entry"
			INDEX { per15mHistoryDataBoardNo, per15mHistoryDataOpticalPort, per15mHistoryDataPathNumber, per15mHistoryDataEventID, per15mHistoryDataStartTime
				 }
			::= { per15mHistoryDataTable 1 }
		
		Per15mHistoryDataEntry ::=
			SEQUENCE { 
				per15mHistoryDataBoardNo
					Gauge32,
				per15mHistoryDataOpticalPort
					Gauge32,
				per15mHistoryDataPathNumber
					Gauge32,
				per15mHistoryDataEventID
					SdhPerformanceEventType,
				per15mHistoryDataStartTime
					DateAndTime,
				per15mHistoryDataValue
					Gauge32,
				per15mHistoryDataReset
					INTEGER
			 }

		-- 1.3.6.1.4.1.2011.2.25.3.10.20.20.10.20.1.1
		per15mHistoryDataBoardNo OBJECT-TYPE
			SYNTAX Gauge32
			MAX-ACCESS read-only
			STATUS current
			DESCRIPTION
				"Card No.:between 1 and 20"
			::= { per15mHistoryDataEntry 1 }
		
		-- 1.3.6.1.4.1.2011.2.25.3.10.20.20.10.20.1.2
		per15mHistoryDataOpticalPort OBJECT-TYPE
			SYNTAX Gauge32
			MAX-ACCESS read-only
			STATUS current
			DESCRIPTION
				"Optical port No.:values depend on type of card"
			::= { per15mHistoryDataEntry 2 }
		
		-- 1.3.6.1.4.1.2011.2.25.3.10.20.20.10.20.1.3
		per15mHistoryDataPathNumber OBJECT-TYPE
			SYNTAX Gauge32
			MAX-ACCESS read-only
			STATUS current
			DESCRIPTION
				"Path No.:values depend on type of card"
			::= { per15mHistoryDataEntry 3 }
		
		-- 1.3.6.1.4.1.2011.2.25.3.10.20.20.10.20.1.4
		per15mHistoryDataEventID OBJECT-TYPE
			SYNTAX SdhPerformanceEventType
			MAX-ACCESS read-only
			STATUS current
			DESCRIPTION
				"Event ID:values depend on type of card"
			::= { per15mHistoryDataEntry 4 }
		
		-- 1.3.6.1.4.1.2011.2.25.3.10.20.20.10.20.1.5
		per15mHistoryDataStartTime OBJECT-TYPE
			SYNTAX DateAndTime
			MAX-ACCESS read-only
			STATUS current
			DESCRIPTION
				"start date and time: start date and time of special 15 minutes PM period."
			::= { per15mHistoryDataEntry 5 }
		
		-- 1.3.6.1.4.1.2011.2.25.3.10.20.20.10.20.1.6
		per15mHistoryDataValue OBJECT-TYPE
			SYNTAX Gauge32
			MAX-ACCESS read-only
			STATUS current
			DESCRIPTION
				"Historic data value: value of special 15 minutes PM period register.the units
				of value vary as the PM event,fo example,the unit of RSUAS is 'second',while 
				the unit of RSBBE is 'count'."
			::= { per15mHistoryDataEntry 6 }
		
		-- 1.3.6.1.4.1.2011.2.25.3.10.20.20.10.20.1.7
		per15mHistoryDataReset OBJECT-TYPE
			SYNTAX INTEGER { reset(1) }
			MAX-ACCESS read-write
			STATUS current
			DESCRIPTION
				"Historic data reset: reset value of special 15 minutes PM period register to zero."
			::= { per15mHistoryDataEntry 7 }
		
--  15 minutes PM
		-- 1.3.6.1.4.1.2011.2.25.3.10.20.20.20
		per24hMonitoring OBJECT IDENTIFIER ::= { perMonitorData 20 }
		
--  -------------------------------------------------------------------------
-- one day PM period historic data table
-- 
-- -------------------------------------------------------------------------
		-- 1.3.6.1.4.1.2011.2.25.3.10.20.20.20.20
		per24hHistoryDataTable OBJECT-TYPE
			SYNTAX SEQUENCE OF Per24hHistoryDataEntry
			MAX-ACCESS not-accessible
			STATUS current
			DESCRIPTION
				"one day PM period historic data table"
			::= { per24hMonitoring 20 }
		
		-- 1.3.6.1.4.1.2011.2.25.3.10.20.20.20.20.1
		per24hHistoryDataEntry OBJECT-TYPE
			SYNTAX Per24hHistoryDataEntry
			MAX-ACCESS not-accessible
			STATUS current
			DESCRIPTION
				"one day PM period historic data entry"
			INDEX { per24hHistoryDataBoardNo, per24hHistoryDataOpticalPort, per24hHistoryDataPathNumber, per24hHistoryDataEventID, per24hHistoryDataStartTime
				 }
			::= { per24hHistoryDataTable 1 }
		
		Per24hHistoryDataEntry ::=
			SEQUENCE { 
				per24hHistoryDataBoardNo
					Gauge32,
				per24hHistoryDataOpticalPort
					Gauge32,
				per24hHistoryDataPathNumber
					Gauge32,
				per24hHistoryDataEventID
					SdhPerformanceEventType,
				per24hHistoryDataStartTime
					DateAndTime,
				per24hHistoryDataValue
					Gauge32,
				per24hHistoryDataReset
					INTEGER
			 }

		-- 1.3.6.1.4.1.2011.2.25.3.10.20.20.20.20.1.1
		per24hHistoryDataBoardNo OBJECT-TYPE
			SYNTAX Gauge32
			MAX-ACCESS read-only
			STATUS current
			DESCRIPTION
				"Card No.:between 1 and 20"
			::= { per24hHistoryDataEntry 1 }
		
		-- 1.3.6.1.4.1.2011.2.25.3.10.20.20.20.20.1.2
		per24hHistoryDataOpticalPort OBJECT-TYPE
			SYNTAX Gauge32
			MAX-ACCESS read-only
			STATUS current
			DESCRIPTION
				"Optical port No.:values depend on type of card"
			::= { per24hHistoryDataEntry 2 }
		
		-- 1.3.6.1.4.1.2011.2.25.3.10.20.20.20.20.1.3
		per24hHistoryDataPathNumber OBJECT-TYPE
			SYNTAX Gauge32
			MAX-ACCESS read-only
			STATUS current
			DESCRIPTION
				"Path No.:values depend on type of card"
			::= { per24hHistoryDataEntry 3 }
		
		-- 1.3.6.1.4.1.2011.2.25.3.10.20.20.20.20.1.4
		per24hHistoryDataEventID OBJECT-TYPE
			SYNTAX SdhPerformanceEventType
			MAX-ACCESS read-only
			STATUS current
			DESCRIPTION
				"Event ID:values depend on type of card"
			::= { per24hHistoryDataEntry 4 }
		
		-- 1.3.6.1.4.1.2011.2.25.3.10.20.20.20.20.1.5
		per24hHistoryDataStartTime OBJECT-TYPE
			SYNTAX DateAndTime
			MAX-ACCESS read-only
			STATUS current
			DESCRIPTION
				"start date and time: start date and time of special one day PM period."
			::= { per24hHistoryDataEntry 5 }
		
		-- 1.3.6.1.4.1.2011.2.25.3.10.20.20.20.20.1.6
		per24hHistoryDataValue OBJECT-TYPE
			SYNTAX Gauge32
			MAX-ACCESS read-only
			STATUS current
			DESCRIPTION
				"Historic data value: value of special one day PM period register.the units
				of value vary as the PM event,fo example,the unit of RSUAS is 'second',while 
				the unit of RSBBE is 'count'."
			::= { per24hHistoryDataEntry 6 }
		
		-- 1.3.6.1.4.1.2011.2.25.3.10.20.20.20.20.1.7
		per24hHistoryDataReset OBJECT-TYPE
			SYNTAX INTEGER { reset(1) }
			MAX-ACCESS read-write
			STATUS current
			DESCRIPTION
				"Historic data reset: reset value of special one day PM period register to zero."
			::= { per24hHistoryDataEntry 7 }
		
--  -------------------------------------------------------------------------
-- one day PM period current data table
-- 
-- -------------------------------------------------------------------------
		-- 1.3.6.1.4.1.2011.2.25.3.10.20.20.20.10
		per24hCurrentDataTable OBJECT-TYPE
			SYNTAX SEQUENCE OF Per24hCurrentDataEntry
			MAX-ACCESS not-accessible
			STATUS current
			DESCRIPTION
				"one day PM period current data table"
			::= { per24hMonitoring 10 }
		
		-- 1.3.6.1.4.1.2011.2.25.3.10.20.20.20.10.1
		per24hCurrentDataEntry OBJECT-TYPE
			SYNTAX Per24hCurrentDataEntry
			MAX-ACCESS not-accessible
			STATUS current
			DESCRIPTION
				"one day PM period current data entry"
			INDEX { per24hCurrentDataBoardNo, per24hCurrentDataOpticalPort, per24hCurrentDataPathNumber, per24hCurrentDataEventID }
			::= { per24hCurrentDataTable 1 }
		
		Per24hCurrentDataEntry ::=
			SEQUENCE { 
				per24hCurrentDataBoardNo
					Gauge32,
				per24hCurrentDataOpticalPort
					Gauge32,
				per24hCurrentDataPathNumber
					Gauge32,
				per24hCurrentDataEventID
					SdhPerformanceEventType,
				per24hCurrentDataStartTime
					DateAndTime,
				per24hCurrentDataValue
					Gauge32,
				per24hCurrentDataReset
					INTEGER
			 }

		-- 1.3.6.1.4.1.2011.2.25.3.10.20.20.20.10.1.1
		per24hCurrentDataBoardNo OBJECT-TYPE
			SYNTAX Gauge32
			MAX-ACCESS read-only
			STATUS current
			DESCRIPTION
				"Card No.:between 1 and 20"
			::= { per24hCurrentDataEntry 1 }
		
		-- 1.3.6.1.4.1.2011.2.25.3.10.20.20.20.10.1.2
		per24hCurrentDataOpticalPort OBJECT-TYPE
			SYNTAX Gauge32
			MAX-ACCESS read-only
			STATUS current
			DESCRIPTION
				"Optical port No.:values depend on type of card"
			::= { per24hCurrentDataEntry 2 }
		
		-- 1.3.6.1.4.1.2011.2.25.3.10.20.20.20.10.1.3
		per24hCurrentDataPathNumber OBJECT-TYPE
			SYNTAX Gauge32
			MAX-ACCESS read-only
			STATUS current
			DESCRIPTION
				"Path No.:values depend on type of card"
			::= { per24hCurrentDataEntry 3 }
		
		-- 1.3.6.1.4.1.2011.2.25.3.10.20.20.20.10.1.4
		per24hCurrentDataEventID OBJECT-TYPE
			SYNTAX SdhPerformanceEventType
			MAX-ACCESS read-only
			STATUS current
			DESCRIPTION
				"Event ID:values depend on type of card"
			::= { per24hCurrentDataEntry 4 }
		
		-- 1.3.6.1.4.1.2011.2.25.3.10.20.20.20.10.1.5
		per24hCurrentDataStartTime OBJECT-TYPE
			SYNTAX DateAndTime
			MAX-ACCESS read-only
			STATUS current
			DESCRIPTION
				"start date and time: start date and time of current one day PM period."
			::= { per24hCurrentDataEntry 5 }
		
		-- 1.3.6.1.4.1.2011.2.25.3.10.20.20.20.10.1.6
		per24hCurrentDataValue OBJECT-TYPE
			SYNTAX Gauge32
			MAX-ACCESS read-only
			STATUS current
			DESCRIPTION
				"Current data value: value of current one day PM period register.the units
				of value vary as the PM event,fo example,the unit of RSUAS is 'second',while 
				the unit of RSBBE is 'count'."
			::= { per24hCurrentDataEntry 6 }
		
		-- 1.3.6.1.4.1.2011.2.25.3.10.20.20.20.10.1.7
		per24hCurrentDataReset OBJECT-TYPE
			SYNTAX INTEGER { reset(1) }
			MAX-ACCESS read-write
			STATUS current
			DESCRIPTION
				"Current data reset: reset value of current one day PM period register to zero."
			::= { per24hCurrentDataEntry 7 }
		
--  Performance monitor data
		-- 1.3.6.1.4.1.2011.2.25.3.10.20.30
		perThreshold OBJECT IDENTIFIER ::= { optixPerformance 30 }
		
--  one day PM
		-- 1.3.6.1.4.1.2011.2.25.3.10.20.30.10
		per15mThreshold OBJECT IDENTIFIER ::= { perThreshold 10 }
		
--  -------------------------------------------------------------------------
-- 15 minutes PM period threshold table
-- 
-- -------------------------------------------------------------------------
		-- 1.3.6.1.4.1.2011.2.25.3.10.20.30.10.10
		per15mThresholdTable OBJECT-TYPE
			SYNTAX SEQUENCE OF Per15mThresholdEntry
			MAX-ACCESS not-accessible
			STATUS current
			DESCRIPTION
				"15 minutes PM period threshold table"
			::= { per15mThreshold 10 }
		
		-- 1.3.6.1.4.1.2011.2.25.3.10.20.30.10.10.1
		per15mThresholdEntry OBJECT-TYPE
			SYNTAX Per15mThresholdEntry
			MAX-ACCESS not-accessible
			STATUS current
			DESCRIPTION
				"15 minutes PM period threshold entry"
			INDEX { per15mThresholdBoardNo, per15mThresholdOpticalPort, per15mThresholdPathNumber, per15mThresholdEventID }
			::= { per15mThresholdTable 1 }
		
		Per15mThresholdEntry ::=
			SEQUENCE { 
				per15mThresholdBoardNo
					Gauge32,
				per15mThresholdOpticalPort
					Gauge32,
				per15mThresholdPathNumber
					Gauge32,
				per15mThresholdEventID
					SdhPerformanceEventType,
				per15mThresholdHighValue
					Gauge32,
				per15mThresholdLowValue
					Gauge32,
				per15mThresholdReset
					INTEGER
			 }

		-- 1.3.6.1.4.1.2011.2.25.3.10.20.30.10.10.1.1
		per15mThresholdBoardNo OBJECT-TYPE
			SYNTAX Gauge32
			MAX-ACCESS read-only
			STATUS current
			DESCRIPTION
				"Card No.:between 1 and 20"
			::= { per15mThresholdEntry 1 }
		
		-- 1.3.6.1.4.1.2011.2.25.3.10.20.30.10.10.1.2
		per15mThresholdOpticalPort OBJECT-TYPE
			SYNTAX Gauge32
			MAX-ACCESS read-only
			STATUS current
			DESCRIPTION
				"Optical port No.:values depend on type of card"
			::= { per15mThresholdEntry 2 }
		
		-- 1.3.6.1.4.1.2011.2.25.3.10.20.30.10.10.1.3
		per15mThresholdPathNumber OBJECT-TYPE
			SYNTAX Gauge32
			MAX-ACCESS read-only
			STATUS current
			DESCRIPTION
				"Path No.:values depend on type of card"
			::= { per15mThresholdEntry 3 }
		
		-- 1.3.6.1.4.1.2011.2.25.3.10.20.30.10.10.1.4
		per15mThresholdEventID OBJECT-TYPE
			SYNTAX SdhPerformanceEventType
			MAX-ACCESS read-only
			STATUS current
			DESCRIPTION
				"Event ID:values depend on type of card"
			::= { per15mThresholdEntry 4 }
		
		-- 1.3.6.1.4.1.2011.2.25.3.10.20.30.10.10.1.5
		per15mThresholdHighValue OBJECT-TYPE
			SYNTAX Gauge32
			MAX-ACCESS read-write
			STATUS current
			DESCRIPTION
				"High threshold value: some parameters have two thresholds,such as RSBBE, 
				while others have single threshold,such as RSSES."
			::= { per15mThresholdEntry 5 }
		
		-- 1.3.6.1.4.1.2011.2.25.3.10.20.30.10.10.1.6
		per15mThresholdLowValue OBJECT-TYPE
			SYNTAX Gauge32
			MAX-ACCESS read-write
			STATUS current
			DESCRIPTION
				"Low threshold value: specially,some parameters have single threshold, 
				so their Low threshold should always be zero."
			::= { per15mThresholdEntry 6 }
		
		-- 1.3.6.1.4.1.2011.2.25.3.10.20.30.10.10.1.7
		per15mThresholdReset OBJECT-TYPE
			SYNTAX INTEGER { reset(1) }
			MAX-ACCESS read-write
			STATUS current
			DESCRIPTION
				"Threshold reset: reset both high threshold and low threshold(if has)."
			::= { per15mThresholdEntry 7 }
		
--  threshold of 15 minutes PM period
		-- 1.3.6.1.4.1.2011.2.25.3.10.20.30.20
		per24hThreshold OBJECT IDENTIFIER ::= { perThreshold 20 }
		
--  -------------------------------------------------------------------------
-- one day PM period threshold table
-- 
-- -------------------------------------------------------------------------
		-- 1.3.6.1.4.1.2011.2.25.3.10.20.30.20.10
		per24hThresholdTable OBJECT-TYPE
			SYNTAX SEQUENCE OF Per24hThresholdEntry
			MAX-ACCESS not-accessible
			STATUS current
			DESCRIPTION
				"one day PM period threshold table"
			::= { per24hThreshold 10 }
		
		-- 1.3.6.1.4.1.2011.2.25.3.10.20.30.20.10.1
		per24hThresholdEntry OBJECT-TYPE
			SYNTAX Per24hThresholdEntry
			MAX-ACCESS not-accessible
			STATUS current
			DESCRIPTION
				"one day PM period threshold entry"
			INDEX { per24hThresholdBoardNo, per24hThresholdOpticalPort, per24hThresholdPathNumber, per24hThresholdEventID }
			::= { per24hThresholdTable 1 }
		
		Per24hThresholdEntry ::=
			SEQUENCE { 
				per24hThresholdReset
					INTEGER,
				per24hThresholdValue
					Gauge32,
				per24hThresholdEventID
					SdhPerformanceEventType,
				per24hThresholdPathNumber
					Gauge32,
				per24hThresholdOpticalPort
					Gauge32,
				per24hThresholdBoardNo
					Gauge32
			 }

		-- 1.3.6.1.4.1.2011.2.25.3.10.20.30.20.10.1.6
		per24hThresholdReset OBJECT-TYPE
			SYNTAX INTEGER { reset(1) }
			MAX-ACCESS read-write
			STATUS current
			DESCRIPTION
				"Threshold reset: reset threshold."
			::= { per24hThresholdEntry 6 }
		
		-- 1.3.6.1.4.1.2011.2.25.3.10.20.30.20.10.1.5
		per24hThresholdValue OBJECT-TYPE
			SYNTAX Gauge32
			MAX-ACCESS read-write
			STATUS current
			DESCRIPTION
				"Threshold value: all parameters have only one threshold value for one day PM period."
			::= { per24hThresholdEntry 5 }
		
		-- 1.3.6.1.4.1.2011.2.25.3.10.20.30.20.10.1.4
		per24hThresholdEventID OBJECT-TYPE
			SYNTAX SdhPerformanceEventType
			MAX-ACCESS read-only
			STATUS current
			DESCRIPTION
				"Event ID:values depend on type of card"
			::= { per24hThresholdEntry 4 }
		
		-- 1.3.6.1.4.1.2011.2.25.3.10.20.30.20.10.1.3
		per24hThresholdPathNumber OBJECT-TYPE
			SYNTAX Gauge32
			MAX-ACCESS read-only
			STATUS current
			DESCRIPTION
				"Path No.:values depend on type of card"
			::= { per24hThresholdEntry 3 }
		
		-- 1.3.6.1.4.1.2011.2.25.3.10.20.30.20.10.1.2
		per24hThresholdOpticalPort OBJECT-TYPE
			SYNTAX Gauge32
			MAX-ACCESS read-only
			STATUS current
			DESCRIPTION
				"Optical port No.:values depend on type of card"
			::= { per24hThresholdEntry 2 }
		
		-- 1.3.6.1.4.1.2011.2.25.3.10.20.30.20.10.1.1
		per24hThresholdBoardNo OBJECT-TYPE
			SYNTAX Gauge32
			MAX-ACCESS read-only
			STATUS current
			DESCRIPTION
				"Card No.:between 1 and 20"
			::= { per24hThresholdEntry 1 }
		
--  Performance threshold
		-- 1.3.6.1.4.1.2011.2.25.3.10.20.40
		perStatus OBJECT IDENTIFIER ::= { optixPerformance 40 }
		
--  threshold of one day PM period
		-- 1.3.6.1.4.1.2011.2.25.3.10.20.40.10
		perStatusControl OBJECT IDENTIFIER ::= { perStatus 10 }
		
--  PM threshold crossing status
		-- 1.3.6.1.4.1.2011.2.25.3.10.20.40.10.10
		per15mStatusControl OBJECT IDENTIFIER ::= { perStatusControl 10 }
		
--  -------------------------------------------------------------------------
-- 15 minutes PM period monitor status table
-- 
-- -------------------------------------------------------------------------
		-- 1.3.6.1.4.1.2011.2.25.3.10.20.40.10.10.10
		per15mMonitorStatusTable OBJECT-TYPE
			SYNTAX SEQUENCE OF Per15mMonitorStatusEntry
			MAX-ACCESS not-accessible
			STATUS current
			DESCRIPTION
				"15 minutes PM period monitor status table."
			::= { per15mStatusControl 10 }
		
		-- 1.3.6.1.4.1.2011.2.25.3.10.20.40.10.10.10.1
		per15mMonitorStatusEntry OBJECT-TYPE
			SYNTAX Per15mMonitorStatusEntry
			MAX-ACCESS not-accessible
			STATUS current
			DESCRIPTION
				"15 minutes PM period monitor status entry."
			INDEX { per15mMonitorStatusBoardNo, per15mMonitorStatusOpticalPort, per15mMonitorStatusPathNumber, per15mMonitorStatusEventID }
			::= { per15mMonitorStatusTable 1 }
		
		Per15mMonitorStatusEntry ::=
			SEQUENCE { 
				per15mMonitorStatusBoardNo
					Gauge32,
				per15mMonitorStatusOpticalPort
					Gauge32,
				per15mMonitorStatusPathNumber
					Gauge32,
				per15mMonitorStatusEventID
					SdhPerformanceEventType,
				per15mMonitorStatus
					INTEGER
			 }

		-- 1.3.6.1.4.1.2011.2.25.3.10.20.40.10.10.10.1.1
		per15mMonitorStatusBoardNo OBJECT-TYPE
			SYNTAX Gauge32
			MAX-ACCESS read-only
			STATUS current
			DESCRIPTION
				"Card No.:between 1 and 20"
			::= { per15mMonitorStatusEntry 1 }
		
		-- 1.3.6.1.4.1.2011.2.25.3.10.20.40.10.10.10.1.2
		per15mMonitorStatusOpticalPort OBJECT-TYPE
			SYNTAX Gauge32
			MAX-ACCESS read-only
			STATUS current
			DESCRIPTION
				"Optical port No.:values depend on type of card"
			::= { per15mMonitorStatusEntry 2 }
		
		-- 1.3.6.1.4.1.2011.2.25.3.10.20.40.10.10.10.1.3
		per15mMonitorStatusPathNumber OBJECT-TYPE
			SYNTAX Gauge32
			MAX-ACCESS read-only
			STATUS current
			DESCRIPTION
				"Path No.:values depend on type of card"
			::= { per15mMonitorStatusEntry 3 }
		
		-- 1.3.6.1.4.1.2011.2.25.3.10.20.40.10.10.10.1.4
		per15mMonitorStatusEventID OBJECT-TYPE
			SYNTAX SdhPerformanceEventType
			MAX-ACCESS read-only
			STATUS current
			DESCRIPTION
				"Event ID:values depend on type of card"
			::= { per15mMonitorStatusEntry 4 }
		
		-- 1.3.6.1.4.1.2011.2.25.3.10.20.40.10.10.10.1.5
		per15mMonitorStatus OBJECT-TYPE
			SYNTAX INTEGER
				{
				disable(0),
				enable(1)
				}
			MAX-ACCESS read-write
			STATUS current
			DESCRIPTION
				"Monitor status: when monitor status is disabled,current data register is reset to 
				zero and will not increase any more until monitor status be enabled.
				The default monitor status is enable."
			::= { per15mMonitorStatusEntry 5 }
		
--  -------------------------------------------------------------------------
-- 15 minutes PM period pause status table
-- 
-- -------------------------------------------------------------------------
		-- 1.3.6.1.4.1.2011.2.25.3.10.20.40.10.10.20
		per15mPauseStatusTable OBJECT-TYPE
			SYNTAX SEQUENCE OF Per15mPauseStatusEntry
			MAX-ACCESS not-accessible
			STATUS current
			DESCRIPTION
				"15 minutes PM period pause status table."
			::= { per15mStatusControl 20 }
		
		-- 1.3.6.1.4.1.2011.2.25.3.10.20.40.10.10.20.1
		per15mPauseStatusEntry OBJECT-TYPE
			SYNTAX Per15mPauseStatusEntry
			MAX-ACCESS not-accessible
			STATUS current
			DESCRIPTION
				"15 minutes PM period pause status entry."
			INDEX { per15mPauseStatusBoardNo, per15mPauseStatusOpticalPort, per15mPauseStatusPathNumber, per15mPauseStatusEventID }
			::= { per15mPauseStatusTable 1 }
		
		Per15mPauseStatusEntry ::=
			SEQUENCE { 
				per15mPauseStatusBoardNo
					Gauge32,
				per15mPauseStatusOpticalPort
					Gauge32,
				per15mPauseStatusPathNumber
					Gauge32,
				per15mPauseStatusEventID
					SdhPerformanceEventType,
				per15mPauseStatus
					INTEGER
			 }

		-- 1.3.6.1.4.1.2011.2.25.3.10.20.40.10.10.20.1.1
		per15mPauseStatusBoardNo OBJECT-TYPE
			SYNTAX Gauge32
			MAX-ACCESS read-only
			STATUS current
			DESCRIPTION
				"Card No.:between 1 and 20"
			::= { per15mPauseStatusEntry 1 }
		
		-- 1.3.6.1.4.1.2011.2.25.3.10.20.40.10.10.20.1.2
		per15mPauseStatusOpticalPort OBJECT-TYPE
			SYNTAX Gauge32
			MAX-ACCESS read-only
			STATUS current
			DESCRIPTION
				"Optical port No.:values depend on type of card"
			::= { per15mPauseStatusEntry 2 }
		
		-- 1.3.6.1.4.1.2011.2.25.3.10.20.40.10.10.20.1.3
		per15mPauseStatusPathNumber OBJECT-TYPE
			SYNTAX Gauge32
			MAX-ACCESS read-only
			STATUS current
			DESCRIPTION
				"Path No.:values depend on type of card"
			::= { per15mPauseStatusEntry 3 }
		
		-- 1.3.6.1.4.1.2011.2.25.3.10.20.40.10.10.20.1.4
		per15mPauseStatusEventID OBJECT-TYPE
			SYNTAX SdhPerformanceEventType
			MAX-ACCESS read-only
			STATUS current
			DESCRIPTION
				"Event ID:values depend on type of card"
			::= { per15mPauseStatusEntry 4 }
		
		-- 1.3.6.1.4.1.2011.2.25.3.10.20.40.10.10.20.1.5
		per15mPauseStatus OBJECT-TYPE
			SYNTAX INTEGER
				{
				disable(0),
				enable(1)
				}
			MAX-ACCESS read-write
			STATUS current
			DESCRIPTION
				"Pause status: when pause status is disabled,current data register 
				will not increase (but will reset to zero)any more until pause 
				status be enabled.The default monitor status is disable."
			::= { per15mPauseStatusEntry 5 }
		
--  -------------------------------------------------------------------------
-- 15 minutes PM period threshold status table
-- 
-- -------------------------------------------------------------------------
		-- 1.3.6.1.4.1.2011.2.25.3.10.20.40.10.10.30
		per15mThresholdStatusTable OBJECT-TYPE
			SYNTAX SEQUENCE OF Per15mThresholdStatusEntry
			MAX-ACCESS not-accessible
			STATUS current
			DESCRIPTION
				"15 minutes PM period threshold status table"
			::= { per15mStatusControl 30 }
		
		-- 1.3.6.1.4.1.2011.2.25.3.10.20.40.10.10.30.1
		per15mThresholdStatusEntry OBJECT-TYPE
			SYNTAX Per15mThresholdStatusEntry
			MAX-ACCESS not-accessible
			STATUS current
			DESCRIPTION
				"15 minutes PM period threshold status entry"
			INDEX { per15mThresholdStatusBoardNo, per15mThresholdStatusOpticalPort, per15mThresholdStatusPathNumber, per15mThresholdStatusEventID }
			::= { per15mThresholdStatusTable 1 }
		
		Per15mThresholdStatusEntry ::=
			SEQUENCE { 
				per15mThresholdStatusBoardNo
					Gauge32,
				per15mThresholdStatusOpticalPort
					Gauge32,
				per15mThresholdStatusPathNumber
					Gauge32,
				per15mThresholdStatusEventID
					SdhPerformanceEventType,
				per15mThresholdStatus
					INTEGER
			 }

		-- 1.3.6.1.4.1.2011.2.25.3.10.20.40.10.10.30.1.1
		per15mThresholdStatusBoardNo OBJECT-TYPE
			SYNTAX Gauge32
			MAX-ACCESS read-only
			STATUS current
			DESCRIPTION
				"Card No.:between 1 and 20"
			::= { per15mThresholdStatusEntry 1 }
		
		-- 1.3.6.1.4.1.2011.2.25.3.10.20.40.10.10.30.1.2
		per15mThresholdStatusOpticalPort OBJECT-TYPE
			SYNTAX Gauge32
			MAX-ACCESS read-only
			STATUS current
			DESCRIPTION
				"Optical port No.:values depend on type of card"
			::= { per15mThresholdStatusEntry 2 }
		
		-- 1.3.6.1.4.1.2011.2.25.3.10.20.40.10.10.30.1.3
		per15mThresholdStatusPathNumber OBJECT-TYPE
			SYNTAX Gauge32
			MAX-ACCESS read-only
			STATUS current
			DESCRIPTION
				"Path No.:values depend on type of card"
			::= { per15mThresholdStatusEntry 3 }
		
		-- 1.3.6.1.4.1.2011.2.25.3.10.20.40.10.10.30.1.4
		per15mThresholdStatusEventID OBJECT-TYPE
			SYNTAX SdhPerformanceEventType
			MAX-ACCESS read-only
			STATUS current
			DESCRIPTION
				"Event ID:values depend on type of card"
			::= { per15mThresholdStatusEntry 4 }
		
		-- 1.3.6.1.4.1.2011.2.25.3.10.20.40.10.10.30.1.5
		per15mThresholdStatus OBJECT-TYPE
			SYNTAX INTEGER
				{
				disable(0),
				enable(1)
				}
			MAX-ACCESS read-write
			STATUS current
			DESCRIPTION
				"Threshold status:when threshold status is disabled,no threshold 
				crossing alert will be reported even though threshold is crossed.The
				default threshold status is enable."
			::= { per15mThresholdStatusEntry 5 }
		
--  -------------------------------------------------------------------------
-- 15 minutes PM period automatic report(REP) status table
-- 
-- -------------------------------------------------------------------------
		-- 1.3.6.1.4.1.2011.2.25.3.10.20.40.10.10.40
		per15mAutoReportStatusTable OBJECT-TYPE
			SYNTAX SEQUENCE OF Per15mAutoReportStatusEntry
			MAX-ACCESS not-accessible
			STATUS current
			DESCRIPTION
				"15 minutes PM period automatic report(REP) status table"
			::= { per15mStatusControl 40 }
		
		-- 1.3.6.1.4.1.2011.2.25.3.10.20.40.10.10.40.1
		per15mAutoReportStatusEntry OBJECT-TYPE
			SYNTAX Per15mAutoReportStatusEntry
			MAX-ACCESS not-accessible
			STATUS current
			DESCRIPTION
				"15 minutes PM period automatic report(REP) status entry"
			INDEX { per15mAutoReportStatusBoardNo, per15mAutoReportStatusOpticalPort, per15mAutoReportStatusPathNumber, per15mAutoReportStatusEventID }
			::= { per15mAutoReportStatusTable 1 }
		
		Per15mAutoReportStatusEntry ::=
			SEQUENCE { 
				per15mAutoReportStatusBoardNo
					Gauge32,
				per15mAutoReportStatusOpticalPort
					Gauge32,
				per15mAutoReportStatusPathNumber
					Gauge32,
				per15mAutoReportStatusEventID
					SdhPerformanceEventType,
				per15mAutoReportStatus
					INTEGER
			 }

		-- 1.3.6.1.4.1.2011.2.25.3.10.20.40.10.10.40.1.1
		per15mAutoReportStatusBoardNo OBJECT-TYPE
			SYNTAX Gauge32
			MAX-ACCESS read-only
			STATUS current
			DESCRIPTION
				"Card No.:between 1 and 20"
			::= { per15mAutoReportStatusEntry 1 }
		
		-- 1.3.6.1.4.1.2011.2.25.3.10.20.40.10.10.40.1.2
		per15mAutoReportStatusOpticalPort OBJECT-TYPE
			SYNTAX Gauge32
			MAX-ACCESS read-only
			STATUS current
			DESCRIPTION
				"Optical port No.:values depend on type of card"
			::= { per15mAutoReportStatusEntry 2 }
		
		-- 1.3.6.1.4.1.2011.2.25.3.10.20.40.10.10.40.1.3
		per15mAutoReportStatusPathNumber OBJECT-TYPE
			SYNTAX Gauge32
			MAX-ACCESS read-only
			STATUS current
			DESCRIPTION
				"Path No.:values depend on type of card"
			::= { per15mAutoReportStatusEntry 3 }
		
		-- 1.3.6.1.4.1.2011.2.25.3.10.20.40.10.10.40.1.4
		per15mAutoReportStatusEventID OBJECT-TYPE
			SYNTAX SdhPerformanceEventType
			MAX-ACCESS read-only
			STATUS current
			DESCRIPTION
				"Event ID:values depend on type of card"
			::= { per15mAutoReportStatusEntry 4 }
		
		-- 1.3.6.1.4.1.2011.2.25.3.10.20.40.10.10.40.1.5
		per15mAutoReportStatus OBJECT-TYPE
			SYNTAX INTEGER
				{
				disable(0),
				enable(1)
				}
			MAX-ACCESS read-write
			STATUS current
			DESCRIPTION
				"Automatic report status: if automatic report status is enabled, 
				when PM period expired, NE will report none-zero current data 
				register value to user.The default automatic report status is enable
				."
			::= { per15mAutoReportStatusEntry 5 }
		
--  PM status control of 15 minutes PM period
		-- 1.3.6.1.4.1.2011.2.25.3.10.20.40.10.20
		per24hStatusControl OBJECT IDENTIFIER ::= { perStatusControl 20 }
		
--  -------------------------------------------------------------------------
-- one day PM period monitor status table
-- 
-- -------------------------------------------------------------------------
		-- 1.3.6.1.4.1.2011.2.25.3.10.20.40.10.20.10
		per24hMonitorStatusTable OBJECT-TYPE
			SYNTAX SEQUENCE OF Per24hMonitorStatusEntry
			MAX-ACCESS not-accessible
			STATUS current
			DESCRIPTION
				"one day PM period monitor status table."
			::= { per24hStatusControl 10 }
		
		-- 1.3.6.1.4.1.2011.2.25.3.10.20.40.10.20.10.1
		per24hMonitorStatusEntry OBJECT-TYPE
			SYNTAX Per24hMonitorStatusEntry
			MAX-ACCESS not-accessible
			STATUS current
			DESCRIPTION
				"one day PM period monitor status entry."
			INDEX { per24hMonitorStatusBoardNo, per24hMonitorStatusOpticalPort, per24hMonitorStatusPathNumber, per24hMonitorStatusEventID }
			::= { per24hMonitorStatusTable 1 }
		
		Per24hMonitorStatusEntry ::=
			SEQUENCE { 
				per24hMonitorStatusBoardNo
					Gauge32,
				per24hMonitorStatusOpticalPort
					Gauge32,
				per24hMonitorStatusPathNumber
					Gauge32,
				per24hMonitorStatusEventID
					SdhPerformanceEventType,
				per24hMonitorStatus
					INTEGER
			 }

		-- 1.3.6.1.4.1.2011.2.25.3.10.20.40.10.20.10.1.1
		per24hMonitorStatusBoardNo OBJECT-TYPE
			SYNTAX Gauge32
			MAX-ACCESS read-only
			STATUS current
			DESCRIPTION
				"Card No.:between 1 and 20"
			::= { per24hMonitorStatusEntry 1 }
		
		-- 1.3.6.1.4.1.2011.2.25.3.10.20.40.10.20.10.1.2
		per24hMonitorStatusOpticalPort OBJECT-TYPE
			SYNTAX Gauge32
			MAX-ACCESS read-only
			STATUS current
			DESCRIPTION
				"Optical port No.:values depend on type of card"
			::= { per24hMonitorStatusEntry 2 }
		
		-- 1.3.6.1.4.1.2011.2.25.3.10.20.40.10.20.10.1.3
		per24hMonitorStatusPathNumber OBJECT-TYPE
			SYNTAX Gauge32
			MAX-ACCESS read-only
			STATUS current
			DESCRIPTION
				"Path No.:values depend on type of card"
			::= { per24hMonitorStatusEntry 3 }
		
		-- 1.3.6.1.4.1.2011.2.25.3.10.20.40.10.20.10.1.4
		per24hMonitorStatusEventID OBJECT-TYPE
			SYNTAX SdhPerformanceEventType
			MAX-ACCESS read-only
			STATUS current
			DESCRIPTION
				"Event ID:values depend on type of card"
			::= { per24hMonitorStatusEntry 4 }
		
		-- 1.3.6.1.4.1.2011.2.25.3.10.20.40.10.20.10.1.5
		per24hMonitorStatus OBJECT-TYPE
			SYNTAX INTEGER
				{
				disable(0),
				enable(1)
				}
			MAX-ACCESS read-write
			STATUS current
			DESCRIPTION
				"Monitor status: when monitor status is disabled,current data 
				register is reset to zero and will not increase any more until 
				monitor status be enabled.The default monitor status is enable."
			::= { per24hMonitorStatusEntry 5 }
		
--  -------------------------------------------------------------------------
-- one day PM period pause status table
-- 
-- -------------------------------------------------------------------------
		-- 1.3.6.1.4.1.2011.2.25.3.10.20.40.10.20.20
		per24hPauseStatusTable OBJECT-TYPE
			SYNTAX SEQUENCE OF Per24hPauseStatusEntry
			MAX-ACCESS not-accessible
			STATUS current
			DESCRIPTION
				"one day PM period pause status table."
			::= { per24hStatusControl 20 }
		
		-- 1.3.6.1.4.1.2011.2.25.3.10.20.40.10.20.20.1
		per24hPauseStatusEntry OBJECT-TYPE
			SYNTAX Per24hPauseStatusEntry
			MAX-ACCESS not-accessible
			STATUS current
			DESCRIPTION
				"one day PM period pause status entry."
			INDEX { per24hPauseStatusBoardNo, per24hPauseStatusOpticalPort, per24hPauseStatusPathNumber, per24hPauseStatusEventID }
			::= { per24hPauseStatusTable 1 }
		
		Per24hPauseStatusEntry ::=
			SEQUENCE { 
				per24hPauseStatusBoardNo
					Gauge32,
				per24hPauseStatusOpticalPort
					Gauge32,
				per24hPauseStatusPathNumber
					Gauge32,
				per24hPauseStatusEventID
					SdhPerformanceEventType,
				per24hPauseStatus
					INTEGER
			 }

		-- 1.3.6.1.4.1.2011.2.25.3.10.20.40.10.20.20.1.1
		per24hPauseStatusBoardNo OBJECT-TYPE
			SYNTAX Gauge32
			MAX-ACCESS read-only
			STATUS current
			DESCRIPTION
				"Card No.:between 1 and 20"
			::= { per24hPauseStatusEntry 1 }
		
		-- 1.3.6.1.4.1.2011.2.25.3.10.20.40.10.20.20.1.2
		per24hPauseStatusOpticalPort OBJECT-TYPE
			SYNTAX Gauge32
			MAX-ACCESS read-only
			STATUS current
			DESCRIPTION
				"Optical port No.:values depend on type of card"
			::= { per24hPauseStatusEntry 2 }
		
		-- 1.3.6.1.4.1.2011.2.25.3.10.20.40.10.20.20.1.3
		per24hPauseStatusPathNumber OBJECT-TYPE
			SYNTAX Gauge32
			MAX-ACCESS read-only
			STATUS current
			DESCRIPTION
				"Path No.:values depend on type of card"
			::= { per24hPauseStatusEntry 3 }
		
		-- 1.3.6.1.4.1.2011.2.25.3.10.20.40.10.20.20.1.4
		per24hPauseStatusEventID OBJECT-TYPE
			SYNTAX SdhPerformanceEventType
			MAX-ACCESS read-only
			STATUS current
			DESCRIPTION
				"Event ID:values depend on type of card"
			::= { per24hPauseStatusEntry 4 }
		
		-- 1.3.6.1.4.1.2011.2.25.3.10.20.40.10.20.20.1.5
		per24hPauseStatus OBJECT-TYPE
			SYNTAX INTEGER
				{
				disable(0),
				enable(1)
				}
			MAX-ACCESS read-write
			STATUS current
			DESCRIPTION
				"Pause status: when pause status is disabled,current data register 
				will not increase (but will reset to zero)any more until pause 
				status be enabled.The default monitor status is disable."
			::= { per24hPauseStatusEntry 5 }
		
--  -------------------------------------------------------------------------
-- one day PM period threshold status table
-- 
-- -------------------------------------------------------------------------
		-- 1.3.6.1.4.1.2011.2.25.3.10.20.40.10.20.30
		per24hThresholdStatusTable OBJECT-TYPE
			SYNTAX SEQUENCE OF Per24hThresholdStatusEntry
			MAX-ACCESS not-accessible
			STATUS current
			DESCRIPTION
				"one day PM period threshold status table."
			::= { per24hStatusControl 30 }
		
		-- 1.3.6.1.4.1.2011.2.25.3.10.20.40.10.20.30.1
		per24hThresholdStatusEntry OBJECT-TYPE
			SYNTAX Per24hThresholdStatusEntry
			MAX-ACCESS not-accessible
			STATUS current
			DESCRIPTION
				"one day PM period threshold status entry."
			INDEX { per24hThresholdStatusBoardNo, per24hThresholdStatusOpticalPort, per24hThresholdStatusPathNumber, per24hThresholdStatusEventID }
			::= { per24hThresholdStatusTable 1 }
		
		Per24hThresholdStatusEntry ::=
			SEQUENCE { 
				per24hThresholdStatusBoardNo
					Gauge32,
				per24hThresholdStatusOpticalPort
					Gauge32,
				per24hThresholdStatusPathNumber
					Gauge32,
				per24hThresholdStatusEventID
					SdhPerformanceEventType,
				per24hThresholdStatus
					INTEGER
			 }

		-- 1.3.6.1.4.1.2011.2.25.3.10.20.40.10.20.30.1.1
		per24hThresholdStatusBoardNo OBJECT-TYPE
			SYNTAX Gauge32
			MAX-ACCESS read-only
			STATUS current
			DESCRIPTION
				"Card No.:between 1 and 20"
			::= { per24hThresholdStatusEntry 1 }
		
		-- 1.3.6.1.4.1.2011.2.25.3.10.20.40.10.20.30.1.2
		per24hThresholdStatusOpticalPort OBJECT-TYPE
			SYNTAX Gauge32
			MAX-ACCESS read-only
			STATUS current
			DESCRIPTION
				"Optical port No.:values depend on type of card"
			::= { per24hThresholdStatusEntry 2 }
		
		-- 1.3.6.1.4.1.2011.2.25.3.10.20.40.10.20.30.1.3
		per24hThresholdStatusPathNumber OBJECT-TYPE
			SYNTAX Gauge32
			MAX-ACCESS read-only
			STATUS current
			DESCRIPTION
				"Path No.:values depend on type of card"
			::= { per24hThresholdStatusEntry 3 }
		
		-- 1.3.6.1.4.1.2011.2.25.3.10.20.40.10.20.30.1.4
		per24hThresholdStatusEventID OBJECT-TYPE
			SYNTAX SdhPerformanceEventType
			MAX-ACCESS read-only
			STATUS current
			DESCRIPTION
				"Event ID:values depend on type of card"
			::= { per24hThresholdStatusEntry 4 }
		
		-- 1.3.6.1.4.1.2011.2.25.3.10.20.40.10.20.30.1.5
		per24hThresholdStatus OBJECT-TYPE
			SYNTAX INTEGER
				{
				disable(0),
				enable(1)
				}
			MAX-ACCESS read-write
			STATUS current
			DESCRIPTION
				"Threshold status:when threshold status is disabled,no threshold 
				crossing alert will be reported even though threshold is crossed.The
				default threshold status is enable."
			::= { per24hThresholdStatusEntry 5 }
		
--  -------------------------------------------------------------------------
-- one day PM period automatic report(REP) status table
-- 
-- -------------------------------------------------------------------------
		-- 1.3.6.1.4.1.2011.2.25.3.10.20.40.10.20.40
		per24hAutoReportStatusTable OBJECT-TYPE
			SYNTAX SEQUENCE OF Per24hAutoReportStatusEntry
			MAX-ACCESS not-accessible
			STATUS current
			DESCRIPTION
				"one day PM period automatic report(REP) status table."
			::= { per24hStatusControl 40 }
		
		-- 1.3.6.1.4.1.2011.2.25.3.10.20.40.10.20.40.1
		per24hAutoReportStatusEntry OBJECT-TYPE
			SYNTAX Per24hAutoReportStatusEntry
			MAX-ACCESS not-accessible
			STATUS current
			DESCRIPTION
				"one day PM period automatic report(REP) status entry."
			INDEX { per24hAutoReportStatusBoardNo, per24hAutoReportStatusOpticalPort, per24hAutoReportStatusPathNumber, per24hAutoReportStatusEventID }
			::= { per24hAutoReportStatusTable 1 }
		
		Per24hAutoReportStatusEntry ::=
			SEQUENCE { 
				per24hAutoReportStatusBoardNo
					Gauge32,
				per24hAutoReportStatusOpticalPort
					Gauge32,
				per24hAutoReportStatusPathNumber
					Gauge32,
				per24hAutoReportStatusEventID
					SdhPerformanceEventType,
				per24hAutoReportStatus
					INTEGER
			 }

		-- 1.3.6.1.4.1.2011.2.25.3.10.20.40.10.20.40.1.1
		per24hAutoReportStatusBoardNo OBJECT-TYPE
			SYNTAX Gauge32
			MAX-ACCESS read-only
			STATUS current
			DESCRIPTION
				"Card No.:between 1 and 20"
			::= { per24hAutoReportStatusEntry 1 }
		
		-- 1.3.6.1.4.1.2011.2.25.3.10.20.40.10.20.40.1.2
		per24hAutoReportStatusOpticalPort OBJECT-TYPE
			SYNTAX Gauge32
			MAX-ACCESS read-only
			STATUS current
			DESCRIPTION
				"Optical port No.:values depend on type of card"
			::= { per24hAutoReportStatusEntry 2 }
		
		-- 1.3.6.1.4.1.2011.2.25.3.10.20.40.10.20.40.1.3
		per24hAutoReportStatusPathNumber OBJECT-TYPE
			SYNTAX Gauge32
			MAX-ACCESS read-only
			STATUS current
			DESCRIPTION
				"Path No.:values depend on type of card"
			::= { per24hAutoReportStatusEntry 3 }
		
		-- 1.3.6.1.4.1.2011.2.25.3.10.20.40.10.20.40.1.4
		per24hAutoReportStatusEventID OBJECT-TYPE
			SYNTAX SdhPerformanceEventType
			MAX-ACCESS read-only
			STATUS current
			DESCRIPTION
				"Event ID:values depend on type of card"
			::= { per24hAutoReportStatusEntry 4 }
		
		-- 1.3.6.1.4.1.2011.2.25.3.10.20.40.10.20.40.1.5
		per24hAutoReportStatus OBJECT-TYPE
			SYNTAX INTEGER
				{
				disable(0),
				enable(1)
				}
			MAX-ACCESS read-write
			STATUS current
			DESCRIPTION
				"Automatic report status: if automatic report status is enabled, 
				when PM period expired, NE will report none-zero current data 
				register value to user.The default automatic report status is enable
				."
			::= { per24hAutoReportStatusEntry 5 }
		
--  PM status control
		-- 1.3.6.1.4.1.2011.2.25.3.10.20.40.20
		perThresholdCrossStatus OBJECT IDENTIFIER ::= { perStatus 20 }
		
--  -------------------------------------------------------------------------
-- 15 minutes PM period threshold crossing status table
-- 
-- -------------------------------------------------------------------------
		-- 1.3.6.1.4.1.2011.2.25.3.10.20.40.20.10
		per15mThresholdCrossStatusTable OBJECT-TYPE
			SYNTAX SEQUENCE OF Per15mThresholdCrossStatusEntry
			MAX-ACCESS not-accessible
			STATUS current
			DESCRIPTION
				"15 minutes PM period threshold crossing status table."
			::= { perThresholdCrossStatus 10 }
		
		-- 1.3.6.1.4.1.2011.2.25.3.10.20.40.20.10.1
		per15mThresholdCrossStatusEntry OBJECT-TYPE
			SYNTAX Per15mThresholdCrossStatusEntry
			MAX-ACCESS not-accessible
			STATUS current
			DESCRIPTION
				"15 minutes PM period threshold crossing status entry."
			INDEX { per15mThresholdCrossStatusBoardNo, per15mThresholdCrossStatusOpticalPort, per15mThresholdCrossStatusPathNumber, per15mThresholdCrossStatusEventID }
			::= { per15mThresholdCrossStatusTable 1 }
		
		Per15mThresholdCrossStatusEntry ::=
			SEQUENCE { 
				per15mThresholdCrossStatusBoardNo
					Gauge32,
				per15mThresholdCrossStatusOpticalPort
					Gauge32,
				per15mThresholdCrossStatusPathNumber
					Gauge32,
				per15mThresholdCrossStatusEventID
					SdhPerformanceEventType,
				per15mThresholdCrossStatus
					INTEGER
			 }

		-- 1.3.6.1.4.1.2011.2.25.3.10.20.40.20.10.1.1
		per15mThresholdCrossStatusBoardNo OBJECT-TYPE
			SYNTAX Gauge32
			MAX-ACCESS read-only
			STATUS current
			DESCRIPTION
				"Card No.:between 1 and 20"
			::= { per15mThresholdCrossStatusEntry 1 }
		
		-- 1.3.6.1.4.1.2011.2.25.3.10.20.40.20.10.1.2
		per15mThresholdCrossStatusOpticalPort OBJECT-TYPE
			SYNTAX Gauge32
			MAX-ACCESS read-only
			STATUS current
			DESCRIPTION
				"Optical port No.:values depend on type of card"
			::= { per15mThresholdCrossStatusEntry 2 }
		
		-- 1.3.6.1.4.1.2011.2.25.3.10.20.40.20.10.1.3
		per15mThresholdCrossStatusPathNumber OBJECT-TYPE
			SYNTAX Gauge32
			MAX-ACCESS read-only
			STATUS current
			DESCRIPTION
				"Path No.:values depend on type of card"
			::= { per15mThresholdCrossStatusEntry 3 }
		
		-- 1.3.6.1.4.1.2011.2.25.3.10.20.40.20.10.1.4
		per15mThresholdCrossStatusEventID OBJECT-TYPE
			SYNTAX SdhPerformanceEventType
			MAX-ACCESS read-only
			STATUS current
			DESCRIPTION
				"Event ID:values depend on type of card"
			::= { per15mThresholdCrossStatusEntry 4 }
		
		-- 1.3.6.1.4.1.2011.2.25.3.10.20.40.20.10.1.5
		per15mThresholdCrossStatus OBJECT-TYPE
			SYNTAX INTEGER
				{
				normal(0),
				crossed(1)
				}
			MAX-ACCESS read-only
			STATUS current
			DESCRIPTION
				"Threshold crossing status:normal-threshold was not crossed,crossed
				-threshold was crossed."
			::= { per15mThresholdCrossStatusEntry 5 }
		
--  -------------------------------------------------------------------------
-- one day PM period threshold crossing status table
-- 
-- -------------------------------------------------------------------------
		-- 1.3.6.1.4.1.2011.2.25.3.10.20.40.20.20
		per24hThresholdCrossStatusTable OBJECT-TYPE
			SYNTAX SEQUENCE OF Per24hThresholdCrossStatusEntry
			MAX-ACCESS not-accessible
			STATUS current
			DESCRIPTION
				"one day PM period threshold crossing status table."
			::= { perThresholdCrossStatus 20 }
		
		-- 1.3.6.1.4.1.2011.2.25.3.10.20.40.20.20.1
		per24hThresholdCrossStatusEntry OBJECT-TYPE
			SYNTAX Per24hThresholdCrossStatusEntry
			MAX-ACCESS not-accessible
			STATUS current
			DESCRIPTION
				"one day PM period threshold crossing status entry."
			INDEX { per24hThresholdCrossStatusBoardNo, per24hThresholdCrossStatusOpticalPort, per24hThresholdCrossStatusPathNumber, per24hThresholdCrossStatusEventID }
			::= { per24hThresholdCrossStatusTable 1 }
		
		Per24hThresholdCrossStatusEntry ::=
			SEQUENCE { 
				per24hThresholdCrossStatus
					INTEGER,
				per24hThresholdCrossStatusEventID
					SdhPerformanceEventType,
				per24hThresholdCrossStatusPathNumber
					Gauge32,
				per24hThresholdCrossStatusOpticalPort
					Gauge32,
				per24hThresholdCrossStatusBoardNo
					Gauge32
			 }

		-- 1.3.6.1.4.1.2011.2.25.3.10.20.40.20.20.1.5
		per24hThresholdCrossStatus OBJECT-TYPE
			SYNTAX INTEGER
				{
				normal(0),
				crossed(1)
				}
			MAX-ACCESS read-only
			STATUS current
			DESCRIPTION
				"Threshold crossing status:normal-threshold was not crossed,crossed
				-threshold was crossed."
			::= { per24hThresholdCrossStatusEntry 5 }
		
		-- 1.3.6.1.4.1.2011.2.25.3.10.20.40.20.20.1.4
		per24hThresholdCrossStatusEventID OBJECT-TYPE
			SYNTAX SdhPerformanceEventType
			MAX-ACCESS read-only
			STATUS current
			DESCRIPTION
				"Event ID:values depend on type of card"
			::= { per24hThresholdCrossStatusEntry 4 }
		
		-- 1.3.6.1.4.1.2011.2.25.3.10.20.40.20.20.1.3
		per24hThresholdCrossStatusPathNumber OBJECT-TYPE
			SYNTAX Gauge32
			MAX-ACCESS read-only
			STATUS current
			DESCRIPTION
				"Path No.:values depend on type of card"
			::= { per24hThresholdCrossStatusEntry 3 }
		
		-- 1.3.6.1.4.1.2011.2.25.3.10.20.40.20.20.1.2
		per24hThresholdCrossStatusOpticalPort OBJECT-TYPE
			SYNTAX Gauge32
			MAX-ACCESS read-only
			STATUS current
			DESCRIPTION
				"Optical port No.:values depend on type of card"
			::= { per24hThresholdCrossStatusEntry 2 }
		
		-- 1.3.6.1.4.1.2011.2.25.3.10.20.40.20.20.1.1
		per24hThresholdCrossStatusBoardNo OBJECT-TYPE
			SYNTAX Gauge32
			MAX-ACCESS read-only
			STATUS current
			DESCRIPTION
				"Card No.:between 1 and 20"
			::= { per24hThresholdCrossStatusEntry 1 }
		
--  Performance status
		-- 1.3.6.1.4.1.2011.2.25.3.10.20.50
		perEvents OBJECT IDENTIFIER ::= { optixPerformance 50 }
		
--  PM status control of one day PM period
		-- 1.3.6.1.4.1.2011.2.25.3.10.20.50.10
		perUATEvent OBJECT IDENTIFIER ::= { perEvents 10 }
		
--  -------------------------------------------------------------------------
-- UAT event(REP) table
-- 
-- -------------------------------------------------------------------------
		-- 1.3.6.1.4.1.2011.2.25.3.10.20.50.10.10
		perUATEventTable OBJECT-TYPE
			SYNTAX SEQUENCE OF PerUATEventEntry
			MAX-ACCESS not-accessible
			STATUS current
			DESCRIPTION
				"UAT event table."
			::= { perUATEvent 10 }
		
		-- 1.3.6.1.4.1.2011.2.25.3.10.20.50.10.10.1
		perUATEventEntry OBJECT-TYPE
			SYNTAX PerUATEventEntry
			MAX-ACCESS not-accessible
			STATUS current
			DESCRIPTION
				"UAT event entry."
			INDEX { perUATBoardNo, perUATOpticalPort, perUATPathNumber, perUATEventID, perUATStartTime
				 }
			::= { perUATEventTable 1 }
		
		PerUATEventEntry ::=
			SEQUENCE { 
				perUATBoardNo
					Gauge32,
				perUATOpticalPort
					Gauge32,
				perUATPathNumber
					Gauge32,
				perUATEventID
					SdhPerformanceEventType,
				perUATStartTime
					DateAndTime,
				perUATEndTime
					DateAndTime
			 }

		-- 1.3.6.1.4.1.2011.2.25.3.10.20.50.10.10.1.1
		perUATBoardNo OBJECT-TYPE
			SYNTAX Gauge32
			MAX-ACCESS read-only
			STATUS current
			DESCRIPTION
				"Card No.:between 1 and 20"
			::= { perUATEventEntry 1 }
		
		-- 1.3.6.1.4.1.2011.2.25.3.10.20.50.10.10.1.2
		perUATOpticalPort OBJECT-TYPE
			SYNTAX Gauge32
			MAX-ACCESS read-only
			STATUS current
			DESCRIPTION
				"Optical port No.:values depend on type of card"
			::= { perUATEventEntry 2 }
		
		-- 1.3.6.1.4.1.2011.2.25.3.10.20.50.10.10.1.3
		perUATPathNumber OBJECT-TYPE
			SYNTAX Gauge32
			MAX-ACCESS read-only
			STATUS current
			DESCRIPTION
				"Path No.:values depend on type of card"
			::= { perUATEventEntry 3 }
		
		-- 1.3.6.1.4.1.2011.2.25.3.10.20.50.10.10.1.4
		perUATEventID OBJECT-TYPE
			SYNTAX SdhPerformanceEventType
			MAX-ACCESS read-only
			STATUS current
			DESCRIPTION
				"Event ID:values depend on type of card"
			::= { perUATEventEntry 4 }
		
		-- 1.3.6.1.4.1.2011.2.25.3.10.20.50.10.10.1.5
		perUATStartTime OBJECT-TYPE
			SYNTAX DateAndTime
			MAX-ACCESS read-only
			STATUS current
			DESCRIPTION
				"the date and time when enter UAT."
			::= { perUATEventEntry 5 }
		
		-- 1.3.6.1.4.1.2011.2.25.3.10.20.50.10.10.1.6
		perUATEndTime OBJECT-TYPE
			SYNTAX DateAndTime
			MAX-ACCESS read-only
			STATUS current
			DESCRIPTION
				"the date and time when exit UAT."
			::= { perUATEventEntry 6 }
		
--  PM UAT event
		-- 1.3.6.1.4.1.2011.2.25.3.10.20.50.20
		perCSESEvent OBJECT IDENTIFIER ::= { perEvents 20 }
		
--  -------------------------------------------------------------------------
-- CSES event(REP) table
-- 
-- -------------------------------------------------------------------------
		-- 1.3.6.1.4.1.2011.2.25.3.10.20.50.20.10
		perCSESEventTable OBJECT-TYPE
			SYNTAX SEQUENCE OF PerCSESEventEntry
			MAX-ACCESS not-accessible
			STATUS current
			DESCRIPTION
				"CSES event table."
			::= { perCSESEvent 10 }
		
		-- 1.3.6.1.4.1.2011.2.25.3.10.20.50.20.10.1
		perCSESEventEntry OBJECT-TYPE
			SYNTAX PerCSESEventEntry
			MAX-ACCESS not-accessible
			STATUS current
			DESCRIPTION
				"CSES event entry."
			INDEX { perCSESBoardNo, perCSESOpticalPort, perCSESPathNumber, perCSESEventID, perCSESStartTime
				 }
			::= { perCSESEventTable 1 }
		
		PerCSESEventEntry ::=
			SEQUENCE { 
				perCSESKeepTime
					Gauge32,
				perCSESStartTime
					DateAndTime,
				perCSESEventID
					SdhPerformanceEventType,
				perCSESPathNumber
					Gauge32,
				perCSESOpticalPort
					Gauge32,
				perCSESBoardNo
					Gauge32
			 }

		-- 1.3.6.1.4.1.2011.2.25.3.10.20.50.20.10.1.6
		perCSESKeepTime OBJECT-TYPE
			SYNTAX Gauge32
			MAX-ACCESS read-only
			STATUS current
			DESCRIPTION
				"the count of CSES continues."
			::= { perCSESEventEntry 6 }
		
		-- 1.3.6.1.4.1.2011.2.25.3.10.20.50.20.10.1.5
		perCSESStartTime OBJECT-TYPE
			SYNTAX DateAndTime
			MAX-ACCESS read-only
			STATUS current
			DESCRIPTION
				"the date and time when enter CSES."
			::= { perCSESEventEntry 5 }
		
		-- 1.3.6.1.4.1.2011.2.25.3.10.20.50.20.10.1.4
		perCSESEventID OBJECT-TYPE
			SYNTAX SdhPerformanceEventType
			MAX-ACCESS read-only
			STATUS current
			DESCRIPTION
				"Event ID:values depend on type of card"
			::= { perCSESEventEntry 4 }
		
		-- 1.3.6.1.4.1.2011.2.25.3.10.20.50.20.10.1.3
		perCSESPathNumber OBJECT-TYPE
			SYNTAX Gauge32
			MAX-ACCESS read-only
			STATUS current
			DESCRIPTION
				"Path No.:values depend on type of card"
			::= { perCSESEventEntry 3 }
		
		-- 1.3.6.1.4.1.2011.2.25.3.10.20.50.20.10.1.2
		perCSESOpticalPort OBJECT-TYPE
			SYNTAX Gauge32
			MAX-ACCESS read-only
			STATUS current
			DESCRIPTION
				"Optical port No.:values depend on type of card"
			::= { perCSESEventEntry 2 }
		
		-- 1.3.6.1.4.1.2011.2.25.3.10.20.50.20.10.1.1
		perCSESBoardNo OBJECT-TYPE
			SYNTAX Gauge32
			MAX-ACCESS read-only
			STATUS current
			DESCRIPTION
				"Card No.:between 1 and 20"
			::= { perCSESEventEntry 1 }
		
		-- 1.3.6.1.4.1.2011.2.25.3.10.20.90
		optixCommonSdhConformance OBJECT IDENTIFIER ::= { optixPerformance 90 }
		
		-- 1.3.6.1.4.1.2011.2.25.3.10.20.90.1
		optixCommonSdhGroups OBJECT IDENTIFIER ::= { optixCommonSdhConformance 1 }
		
		-- 1.3.6.1.4.1.2011.2.25.3.10.20.90.1.1
		currentObjectGroup OBJECT-GROUP
			OBJECTS { per15mMonitorEndTime, per24hMonitorEndTime, per24hMonitorStartTime, per24hHistoryDataReset, per24hHistoryDataValue, 
				per24hHistoryDataStartTime, per24hHistoryDataEventID, per24hHistoryDataPathNumber, per24hHistoryDataOpticalPort, per24hHistoryDataBoardNo, 
				per24hCurrentDataReset, per24hCurrentDataValue, per24hCurrentDataStartTime, per24hCurrentDataEventID, per24hCurrentDataPathNumber, 
				per24hCurrentDataOpticalPort, per24hCurrentDataBoardNo, per15mHistoryDataReset, per15mHistoryDataValue, per15mHistoryDataStartTime, 
				per15mHistoryDataEventID, per15mHistoryDataPathNumber, per15mHistoryDataOpticalPort, per15mHistoryDataBoardNo, per15mCurrentDataReset, 
				per15mCurrentDataValue, per15mCurrentDataStartTime, per15mCurrentDataEventID, per15mCurrentDataPathNumber, per15mCurrentDataOpticalPort, 
				per15mCurrentDataBoardNo, per24hThresholdReset, per24hThresholdValue, per24hThresholdEventID, per24hThresholdPathNumber, 
				per24hThresholdOpticalPort, per24hThresholdBoardNo, per15mThresholdReset, per15mThresholdLowValue, per15mThresholdHighValue, 
				per15mThresholdEventID, per15mThresholdPathNumber, per15mThresholdOpticalPort, per15mThresholdBoardNo, per24hThresholdCrossStatus, 
				per24hThresholdCrossStatusEventID, per24hThresholdCrossStatusPathNumber, per24hThresholdCrossStatusOpticalPort, per24hThresholdCrossStatusBoardNo, per15mThresholdCrossStatus, 
				per15mThresholdCrossStatusEventID, per15mThresholdCrossStatusPathNumber, per15mThresholdCrossStatusOpticalPort, per15mThresholdCrossStatusBoardNo, per24hAutoReportStatus, 
				per24hAutoReportStatusEventID, per24hAutoReportStatusPathNumber, per24hAutoReportStatusOpticalPort, per24hAutoReportStatusBoardNo, per24hThresholdStatus, 
				per24hThresholdStatusEventID, per24hThresholdStatusPathNumber, per24hThresholdStatusOpticalPort, per24hThresholdStatusBoardNo, per24hPauseStatus, 
				per24hPauseStatusEventID, per24hPauseStatusPathNumber, per24hPauseStatusOpticalPort, per24hPauseStatusBoardNo, per24hMonitorStatus, 
				per24hMonitorStatusEventID, per24hMonitorStatusPathNumber, per24hMonitorStatusOpticalPort, per24hMonitorStatusBoardNo, per15mAutoReportStatus, 
				per15mAutoReportStatusEventID, per15mAutoReportStatusPathNumber, per15mAutoReportStatusOpticalPort, per15mAutoReportStatusBoardNo, per15mThresholdStatus, 
				per15mThresholdStatusEventID, per15mThresholdStatusPathNumber, per15mThresholdStatusOpticalPort, per15mThresholdStatusBoardNo, per15mPauseStatus, 
				per15mPauseStatusEventID, per15mPauseStatusPathNumber, per15mPauseStatusOpticalPort, per15mPauseStatusBoardNo, per15mMonitorStatus, 
				per15mMonitorStatusEventID, per15mMonitorStatusPathNumber, per15mMonitorStatusOpticalPort, per15mMonitorStatusBoardNo, perCSESKeepTime, 
				perCSESStartTime, perCSESEventID, perCSESPathNumber, perCSESOpticalPort, perCSESBoardNo, 
				perUATEndTime, perUATStartTime, perUATEventID, perUATPathNumber, perUATOpticalPort, 
				per15mMonitorStartTime, perUATBoardNo }
			STATUS current
			DESCRIPTION 
				"Enter the description of the created OBJECT-GROUP."
			::= { optixCommonSdhGroups 1 }
		
		-- 1.3.6.1.4.1.2011.2.25.3.10.20.90.2
		optixCommonSdhCompliances OBJECT IDENTIFIER ::= { optixCommonSdhConformance 2 }
		
		-- 1.3.6.1.4.1.2011.2.25.3.10.20.90.2.1
		optixCommonSdhbasicCompliance MODULE-COMPLIANCE
			STATUS current
			DESCRIPTION 
				"Enter the description of the created MODULE-COMPLIANCE."
			MODULE -- this module
				MANDATORY-GROUPS { currentObjectGroup }
			::= { optixCommonSdhCompliances 1 }
		
	
	END

--
-- OPTIX-SDH-PER-MIB.mib
--
