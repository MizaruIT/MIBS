--  Title:    NMT2SB_V10A_V2.MIB
--  Version:  v1.0
--
--  Copyright @ 2008 DPS Inc. All Rights Reserved
--
--  This MIB defines supplemental objects for the DPS NetMediator T2S series remotes.
--
--

DPS-MIB-NMT2SB-V10A-V2 DEFINITIONS ::= BEGIN

IMPORTS
	dpsRTUv2
		FROM DPS-MIB-V38-V2;

dpsRTUv2p18001Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 1 is set"
	::= { dpsRTUv2 18001 }

dpsRTUv2p19001Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 1 is cleared"
	::= { dpsRTUv2 19001 }

dpsRTUv2p18002Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 2 is set"
	::= { dpsRTUv2 18002 }

dpsRTUv2p19002Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 2 is cleared"
	::= { dpsRTUv2 19002 }

dpsRTUv2p18003Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 3 is set"
	::= { dpsRTUv2 18003 }

dpsRTUv2p19003Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 3 is cleared"
	::= { dpsRTUv2 19003 }

dpsRTUv2p18004Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 4 is set"
	::= { dpsRTUv2 18004 }

dpsRTUv2p19004Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 4 is cleared"
	::= { dpsRTUv2 19004 }

dpsRTUv2p18005Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 5 is set"
	::= { dpsRTUv2 18005 }

dpsRTUv2p19005Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 5 is cleared"
	::= { dpsRTUv2 19005 }

dpsRTUv2p18006Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 6 is set"
	::= { dpsRTUv2 18006 }

dpsRTUv2p19006Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 6 is cleared"
	::= { dpsRTUv2 19006 }

dpsRTUv2p18007Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 7 is set"
	::= { dpsRTUv2 18007 }

dpsRTUv2p19007Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 7 is cleared"
	::= { dpsRTUv2 19007 }

dpsRTUv2p18008Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 8 is set"
	::= { dpsRTUv2 18008 }

dpsRTUv2p19008Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 8 is cleared"
	::= { dpsRTUv2 19008 }

dpsRTUv2p18009Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 9 is set"
	::= { dpsRTUv2 18009 }

dpsRTUv2p19009Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 9 is cleared"
	::= { dpsRTUv2 19009 }

dpsRTUv2p18010Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 10 is set"
	::= { dpsRTUv2 18010 }

dpsRTUv2p19010Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 10 is cleared"
	::= { dpsRTUv2 19010 }

dpsRTUv2p18011Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 11 is set"
	::= { dpsRTUv2 18011 }

dpsRTUv2p19011Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 11 is cleared"
	::= { dpsRTUv2 19011 }

dpsRTUv2p18012Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 12 is set"
	::= { dpsRTUv2 18012 }

dpsRTUv2p19012Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 12 is cleared"
	::= { dpsRTUv2 19012 }

dpsRTUv2p18013Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 13 is set"
	::= { dpsRTUv2 18013 }

dpsRTUv2p19013Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 13 is cleared"
	::= { dpsRTUv2 19013 }

dpsRTUv2p18014Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 14 is set"
	::= { dpsRTUv2 18014 }

dpsRTUv2p19014Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 14 is cleared"
	::= { dpsRTUv2 19014 }

dpsRTUv2p18015Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 15 is set"
	::= { dpsRTUv2 18015 }

dpsRTUv2p19015Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 15 is cleared"
	::= { dpsRTUv2 19015 }

dpsRTUv2p18016Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 16 is set"
	::= { dpsRTUv2 18016 }

dpsRTUv2p19016Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 16 is cleared"
	::= { dpsRTUv2 19016 }

dpsRTUv2p18017Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 17 is set"
	::= { dpsRTUv2 18017 }

dpsRTUv2p19017Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 17 is cleared"
	::= { dpsRTUv2 19017 }

dpsRTUv2p18018Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 18 is set"
	::= { dpsRTUv2 18018 }

dpsRTUv2p19018Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 18 is cleared"
	::= { dpsRTUv2 19018 }

dpsRTUv2p18019Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 19 is set"
	::= { dpsRTUv2 18019 }

dpsRTUv2p19019Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 19 is cleared"
	::= { dpsRTUv2 19019 }

dpsRTUv2p18020Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 20 is set"
	::= { dpsRTUv2 18020 }

dpsRTUv2p19020Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 20 is cleared"
	::= { dpsRTUv2 19020 }

dpsRTUv2p18021Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 21 is set"
	::= { dpsRTUv2 18021 }

dpsRTUv2p19021Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 21 is cleared"
	::= { dpsRTUv2 19021 }

dpsRTUv2p18022Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 22 is set"

	::= { dpsRTUv2 18022 }

dpsRTUv2p19022Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 22 is cleared"
	::= { dpsRTUv2 19022 }

dpsRTUv2p18023Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 23 is set"
	::= { dpsRTUv2 18023 }

dpsRTUv2p19023Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 23 is cleared"
	::= { dpsRTUv2 19023 }

dpsRTUv2p18024Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 24 is set"
	::= { dpsRTUv2 18024 }

dpsRTUv2p19024Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 24 is cleared"
	::= { dpsRTUv2 19024 }

dpsRTUv2p18025Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 25 is set"
	::= { dpsRTUv2 18025 }

dpsRTUv2p19025Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 25 is cleared"
	::= { dpsRTUv2 19025 }

dpsRTUv2p18026Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 26 is set"
	::= { dpsRTUv2 18026 }

dpsRTUv2p19026Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 26 is cleared"
	::= { dpsRTUv2 19026 }

dpsRTUv2p18027Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 27 is set"
	::= { dpsRTUv2 18027 }

dpsRTUv2p19027Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 27 is cleared"
	::= { dpsRTUv2 19027 }

dpsRTUv2p18028Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 28 is set"
	::= { dpsRTUv2 18028 }

dpsRTUv2p19028Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 28 is cleared"
	::= { dpsRTUv2 19028 }

dpsRTUv2p18029Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 29 is set"
	::= { dpsRTUv2 18029 }

dpsRTUv2p19029Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 29 is cleared"
	::= { dpsRTUv2 19029 }

dpsRTUv2p18030Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 30 is set"
	::= { dpsRTUv2 18030 }

dpsRTUv2p19030Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 30 is cleared"
	::= { dpsRTUv2 19030 }

dpsRTUv2p18031Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 31 is set"
	::= { dpsRTUv2 18031 }

dpsRTUv2p19031Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 31 is cleared"
	::= { dpsRTUv2 19031 }

dpsRTUv2p18032Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 32 is set"
	::= { dpsRTUv2 18032 }

dpsRTUv2p19032Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 32 is cleared"
	::= { dpsRTUv2 19032 }

dpsRTUv2p18033Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 33 is set"
	::= { dpsRTUv2 18033 }

dpsRTUv2p19033Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 33 is cleared"
	::= { dpsRTUv2 19033 }

dpsRTUv2p18034Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 34 is set"
	::= { dpsRTUv2 18034 }

dpsRTUv2p19034Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 34 is cleared"
	::= { dpsRTUv2 19034 }

dpsRTUv2p18035Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 35 is set"
	::= { dpsRTUv2 18035 }

dpsRTUv2p19035Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 35 is cleared"
	::= { dpsRTUv2 19035 }

dpsRTUv2p18036Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 36 is set"
	::= { dpsRTUv2 18036 }

dpsRTUv2p19036Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 36 is cleared"
	::= { dpsRTUv2 19036 }

dpsRTUv2p18037Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 37 is set"
	::= { dpsRTUv2 18037 }

dpsRTUv2p19037Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 37 is cleared"
	::= { dpsRTUv2 19037 }

dpsRTUv2p18038Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 38 is set"
	::= { dpsRTUv2 18038 }

dpsRTUv2p19038Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 38 is cleared"
	::= { dpsRTUv2 19038 }

dpsRTUv2p18039Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 39 is set"
	::= { dpsRTUv2 18039 }

dpsRTUv2p19039Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 39 is cleared"
	::= { dpsRTUv2 19039 }

dpsRTUv2p18040Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 40 is set"
	::= { dpsRTUv2 18040 }

dpsRTUv2p19040Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 40 is cleared"
	::= { dpsRTUv2 19040 }

dpsRTUv2p18041Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 41 is set"
	::= { dpsRTUv2 18041 }

dpsRTUv2p19041Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 41 is cleared"
	::= { dpsRTUv2 19041 }

dpsRTUv2p18042Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 42 is set"
	::= { dpsRTUv2 18042 }

dpsRTUv2p19042Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 42 is cleared"
	::= { dpsRTUv2 19042 }

dpsRTUv2p18043Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 43 is set"
	::= { dpsRTUv2 18043 }

dpsRTUv2p19043Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 43 is cleared"
	::= { dpsRTUv2 19043 }

dpsRTUv2p18044Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 44 is set"
	::= { dpsRTUv2 18044 }

dpsRTUv2p19044Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 44 is cleared"
	::= { dpsRTUv2 19044 }

dpsRTUv2p18045Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 45 is set"
	::= { dpsRTUv2 18045 }

dpsRTUv2p19045Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 45 is cleared"
	::= { dpsRTUv2 19045 }

dpsRTUv2p18046Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 46 is set"
	::= { dpsRTUv2 18046 }

dpsRTUv2p19046Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 46 is cleared"
	::= { dpsRTUv2 19046 }

dpsRTUv2p18047Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 47 is set"
	::= { dpsRTUv2 18047 }

dpsRTUv2p19047Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 47 is cleared"
	::= { dpsRTUv2 19047 }

dpsRTUv2p18048Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 48 is set"
	::= { dpsRTUv2 18048 }

dpsRTUv2p19048Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 48 is cleared"
	::= { dpsRTUv2 19048 }

dpsRTUv2p18049Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 49 is set"
	::= { dpsRTUv2 18049 }

dpsRTUv2p19049Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 49 is cleared"
	::= { dpsRTUv2 19049 }

dpsRTUv2p18050Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 50 is set"
	::= { dpsRTUv2 18050 }

dpsRTUv2p19050Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 50 is cleared"
	::= { dpsRTUv2 19050 }

dpsRTUv2p18051Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 51 is set"
	::= { dpsRTUv2 18051 }

dpsRTUv2p19051Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 51 is cleared"
	::= { dpsRTUv2 19051 }

dpsRTUv2p18052Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 52 is set"
	::= { dpsRTUv2 18052 }

dpsRTUv2p19052Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 52 is cleared"
	::= { dpsRTUv2 19052 }

dpsRTUv2p18053Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 53 is set"
	::= { dpsRTUv2 18053 }

dpsRTUv2p19053Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 53 is cleared"
	::= { dpsRTUv2 19053 }

dpsRTUv2p18054Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 54 is set"
	::= { dpsRTUv2 18054 }

dpsRTUv2p19054Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 54 is cleared"
	::= { dpsRTUv2 19054 }

dpsRTUv2p18055Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 55 is set"
	::= { dpsRTUv2 18055 }

dpsRTUv2p19055Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 55 is cleared"
	::= { dpsRTUv2 19055 }

dpsRTUv2p18056Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 56 is set"
	::= { dpsRTUv2 18056 }

dpsRTUv2p19056Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 56 is cleared"
	::= { dpsRTUv2 19056 }

dpsRTUv2p18057Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 57 is set"
	::= { dpsRTUv2 18057 }

dpsRTUv2p19057Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 57 is cleared"
	::= { dpsRTUv2 19057 }

dpsRTUv2p18058Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 58 is set"
	::= { dpsRTUv2 18058 }

dpsRTUv2p19058Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 58 is cleared"
	::= { dpsRTUv2 19058 }

dpsRTUv2p18059Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 59 is set"
	::= { dpsRTUv2 18059 }

dpsRTUv2p19059Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 59 is cleared"
	::= { dpsRTUv2 19059 }

dpsRTUv2p18060Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 60 is set"
	::= { dpsRTUv2 18060 }

dpsRTUv2p19060Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 60 is cleared"
	::= { dpsRTUv2 19060 }

dpsRTUv2p18061Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 61 is set"
	::= { dpsRTUv2 18061 }

dpsRTUv2p19061Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 61 is cleared"
	::= { dpsRTUv2 19061 }

dpsRTUv2p18062Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 62 is set"
	::= { dpsRTUv2 18062 }

dpsRTUv2p19062Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 62 is cleared"
	::= { dpsRTUv2 19062 }

dpsRTUv2p18063Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 63 is set"
	::= { dpsRTUv2 18063 }

dpsRTUv2p19063Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 63 is cleared"
	::= { dpsRTUv2 19063 }

dpsRTUv2p18064Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 64 is set"
	::= { dpsRTUv2 18064 }

dpsRTUv2p19064Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 1 point 64 is cleared"
	::= { dpsRTUv2 19064 }

dpsRTUv2p18065Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 1 is set"
	::= { dpsRTUv2 18065 }

dpsRTUv2p19065Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 1 is cleared"
	::= { dpsRTUv2 19065 }

dpsRTUv2p18066Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 2 is set"
	::= { dpsRTUv2 18066 }

dpsRTUv2p19066Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 2 is cleared"
	::= { dpsRTUv2 19066 }

dpsRTUv2p18067Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 3 is set"
	::= { dpsRTUv2 18067 }

dpsRTUv2p19067Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 3 is cleared"
	::= { dpsRTUv2 19067 }

dpsRTUv2p18068Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 4 is set"
	::= { dpsRTUv2 18068 }

dpsRTUv2p19068Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 4 is cleared"
	::= { dpsRTUv2 19068 }

dpsRTUv2p18069Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 5 is set"
	::= { dpsRTUv2 18069 }

dpsRTUv2p19069Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 5 is cleared"
	::= { dpsRTUv2 19069 }

dpsRTUv2p18070Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 6 is set"
	::= { dpsRTUv2 18070 }

dpsRTUv2p19070Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 6 is cleared"
	::= { dpsRTUv2 19070 }

dpsRTUv2p18071Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 7 is set"
	::= { dpsRTUv2 18071 }

dpsRTUv2p19071Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 7 is cleared"
	::= { dpsRTUv2 19071 }

dpsRTUv2p18072Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 8 is set"
	::= { dpsRTUv2 18072 }

dpsRTUv2p19072Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 8 is cleared"
	::= { dpsRTUv2 19072 }

dpsRTUv2p18073Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 9 is set"
	::= { dpsRTUv2 18073 }

dpsRTUv2p19073Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 9 is cleared"
	::= { dpsRTUv2 19073 }

dpsRTUv2p18074Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 10 is set"
	::= { dpsRTUv2 18074 }

dpsRTUv2p19074Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 10 is cleared"
	::= { dpsRTUv2 19074 }

dpsRTUv2p18075Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 11 is set"
	::= { dpsRTUv2 18075 }

dpsRTUv2p19075Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 11 is cleared"
	::= { dpsRTUv2 19075 }

dpsRTUv2p18076Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 12 is set"
	::= { dpsRTUv2 18076 }

dpsRTUv2p19076Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 12 is cleared"
	::= { dpsRTUv2 19076 }

dpsRTUv2p18077Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 13 is set"
	::= { dpsRTUv2 18077 }

dpsRTUv2p19077Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 13 is cleared"
	::= { dpsRTUv2 19077 }

dpsRTUv2p18078Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 14 is set"
	::= { dpsRTUv2 18078 }

dpsRTUv2p19078Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 14 is cleared"
	::= { dpsRTUv2 19078 }

dpsRTUv2p18079Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 15 is set"
	::= { dpsRTUv2 18079 }

dpsRTUv2p19079Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 15 is cleared"
	::= { dpsRTUv2 19079 }

dpsRTUv2p18080Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 16 is set"
	::= { dpsRTUv2 18080 }

dpsRTUv2p19080Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 16 is cleared"
	::= { dpsRTUv2 19080 }

dpsRTUv2p18081Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 17 is set"
	::= { dpsRTUv2 18081 }

dpsRTUv2p19081Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 17 is cleared"
	::= { dpsRTUv2 19081 }

dpsRTUv2p18082Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 18 is set"
	::= { dpsRTUv2 18082 }

dpsRTUv2p19082Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 18 is cleared"
	::= { dpsRTUv2 19082 }

dpsRTUv2p18083Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 19 is set"
	::= { dpsRTUv2 18083 }

dpsRTUv2p19083Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 19 is cleared"
	::= { dpsRTUv2 19083 }

dpsRTUv2p18084Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 20 is set"
	::= { dpsRTUv2 18084 }

dpsRTUv2p19084Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 20 is cleared"
	::= { dpsRTUv2 19084 }

dpsRTUv2p18085Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 21 is set"
	::= { dpsRTUv2 18085 }

dpsRTUv2p19085Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 21 is cleared"
	::= { dpsRTUv2 19085 }

dpsRTUv2p18086Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 22 is set"
	::= { dpsRTUv2 18086 }

dpsRTUv2p19086Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 22 is cleared"
	::= { dpsRTUv2 19086 }

dpsRTUv2p18087Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 23 is set"
	::= { dpsRTUv2 18087 }

dpsRTUv2p19087Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 23 is cleared"
	::= { dpsRTUv2 19087 }

dpsRTUv2p18088Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 24 is set"
	::= { dpsRTUv2 18088 }

dpsRTUv2p19088Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 24 is cleared"
	::= { dpsRTUv2 19088 }

dpsRTUv2p18089Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 25 is set"
	::= { dpsRTUv2 18089 }

dpsRTUv2p19089Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 25 is cleared"
	::= { dpsRTUv2 19089 }

dpsRTUv2p18090Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 26 is set"
	::= { dpsRTUv2 18090 }

dpsRTUv2p19090Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 26 is cleared"
	::= { dpsRTUv2 19090 }

dpsRTUv2p18091Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 27 is set"
	::= { dpsRTUv2 18091 }

dpsRTUv2p19091Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 27 is cleared"
	::= { dpsRTUv2 19091 }

dpsRTUv2p18092Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 28 is set"
	::= { dpsRTUv2 18092 }

dpsRTUv2p19092Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 28 is cleared"
	::= { dpsRTUv2 19092 }

dpsRTUv2p18093Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 29 is set"
	::= { dpsRTUv2 18093 }

dpsRTUv2p19093Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 29 is cleared"
	::= { dpsRTUv2 19093 }

dpsRTUv2p18094Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 30 is set"
	::= { dpsRTUv2 18094 }

dpsRTUv2p19094Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 30 is cleared"
	::= { dpsRTUv2 19094 }

dpsRTUv2p18095Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 31 is set"
	::= { dpsRTUv2 18095 }

dpsRTUv2p19095Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 31 is cleared"
	::= { dpsRTUv2 19095 }

dpsRTUv2p18096Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 32 is set"
	::= { dpsRTUv2 18096 }

dpsRTUv2p19096Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 32 is cleared"
	::= { dpsRTUv2 19096 }

dpsRTUv2p18097Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 33 is set"
	::= { dpsRTUv2 18097 }

dpsRTUv2p19097Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 33 is cleared"
	::= { dpsRTUv2 19097 }

dpsRTUv2p18098Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 34 is set"
	::= { dpsRTUv2 18098 }

dpsRTUv2p19098Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 34 is cleared"
	::= { dpsRTUv2 19098 }

dpsRTUv2p18099Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 35 is set"
	::= { dpsRTUv2 18099 }

dpsRTUv2p19099Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 35 is cleared"
	::= { dpsRTUv2 19099 }

dpsRTUv2p18100Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 36 is set"
	::= { dpsRTUv2 18100 }

dpsRTUv2p19100Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 36 is cleared"
	::= { dpsRTUv2 19100 }

dpsRTUv2p18101Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 37 is set"
	::= { dpsRTUv2 18101 }

dpsRTUv2p19101Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 37 is cleared"
	::= { dpsRTUv2 19101 }

dpsRTUv2p18102Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 38 is set"
	::= { dpsRTUv2 18102 }

dpsRTUv2p19102Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 38 is cleared"
	::= { dpsRTUv2 19102 }

dpsRTUv2p18103Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 39 is set"
	::= { dpsRTUv2 18103 }

dpsRTUv2p19103Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 39 is cleared"
	::= { dpsRTUv2 19103 }

dpsRTUv2p18104Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 40 is set"
	::= { dpsRTUv2 18104 }

dpsRTUv2p19104Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 40 is cleared"
	::= { dpsRTUv2 19104 }

dpsRTUv2p18105Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 41 is set"
	::= { dpsRTUv2 18105 }

dpsRTUv2p19105Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 41 is cleared"
	::= { dpsRTUv2 19105 }

dpsRTUv2p18106Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 42 is set"
	::= { dpsRTUv2 18106 }

dpsRTUv2p19106Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 42 is cleared"
	::= { dpsRTUv2 19106 }

dpsRTUv2p18107Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 43 is set"
	::= { dpsRTUv2 18107 }

dpsRTUv2p19107Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 43 is cleared"
	::= { dpsRTUv2 19107 }

dpsRTUv2p18108Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 44 is set"
	::= { dpsRTUv2 18108 }

dpsRTUv2p19108Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 44 is cleared"
	::= { dpsRTUv2 19108 }

dpsRTUv2p18109Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 45 is set"
	::= { dpsRTUv2 18109 }

dpsRTUv2p19109Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 45 is cleared"
	::= { dpsRTUv2 19109 }

dpsRTUv2p18110Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 46 is set"
	::= { dpsRTUv2 18110 }

dpsRTUv2p19110Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 46 is cleared"
	::= { dpsRTUv2 19110 }

dpsRTUv2p18111Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 47 is set"
	::= { dpsRTUv2 18111 }

dpsRTUv2p19111Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 47 is cleared"
	::= { dpsRTUv2 19111 }

dpsRTUv2p18112Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 48 is set"
	::= { dpsRTUv2 18112 }

dpsRTUv2p19112Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 48 is cleared"
	::= { dpsRTUv2 19112 }

dpsRTUv2p18113Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 49 is set"
	::= { dpsRTUv2 18113 }

dpsRTUv2p19113Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 49 is cleared"
	::= { dpsRTUv2 19113 }

dpsRTUv2p18114Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 50 is set"
	::= { dpsRTUv2 18114 }

dpsRTUv2p19114Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 50 is cleared"
	::= { dpsRTUv2 19114 }

dpsRTUv2p18115Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 51 is set"
	::= { dpsRTUv2 18115 }

dpsRTUv2p19115Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 51 is cleared"
	::= { dpsRTUv2 19115 }

dpsRTUv2p18116Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 52 is set"
	::= { dpsRTUv2 18116 }

dpsRTUv2p19116Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 52 is cleared"
	::= { dpsRTUv2 19116 }

dpsRTUv2p18117Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 53 is set"
	::= { dpsRTUv2 18117 }

dpsRTUv2p19117Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 53 is cleared"
	::= { dpsRTUv2 19117 }

dpsRTUv2p18118Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 54 is set"
	::= { dpsRTUv2 18118 }

dpsRTUv2p19118Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 54 is cleared"
	::= { dpsRTUv2 19118 }

dpsRTUv2p18119Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 55 is set"
	::= { dpsRTUv2 18119 }

dpsRTUv2p19119Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 55 is cleared"
	::= { dpsRTUv2 19119 }

dpsRTUv2p18120Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 56 is set"
	::= { dpsRTUv2 18120 }

dpsRTUv2p19120Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 56 is cleared"
	::= { dpsRTUv2 19120 }

dpsRTUv2p18121Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 57 is set"
	::= { dpsRTUv2 18121 }

dpsRTUv2p19121Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 57 is cleared"
	::= { dpsRTUv2 19121 }

dpsRTUv2p18122Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 58 is set"
	::= { dpsRTUv2 18122 }

dpsRTUv2p19122Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 58 is cleared"
	::= { dpsRTUv2 19122 }

dpsRTUv2p18123Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 59 is set"
	::= { dpsRTUv2 18123 }

dpsRTUv2p19123Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 59 is cleared"
	::= { dpsRTUv2 19123 }

dpsRTUv2p18124Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 60 is set"
	::= { dpsRTUv2 18124 }

dpsRTUv2p19124Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 60 is cleared"
	::= { dpsRTUv2 19124 }

dpsRTUv2p18125Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 61 is set"
	::= { dpsRTUv2 18125 }

dpsRTUv2p19125Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 61 is cleared"
	::= { dpsRTUv2 19125 }

dpsRTUv2p18126Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 62 is set"
	::= { dpsRTUv2 18126 }

dpsRTUv2p19126Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 62 is cleared"
	::= { dpsRTUv2 19126 }

dpsRTUv2p18127Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 63 is set"
	::= { dpsRTUv2 18127 }

dpsRTUv2p19127Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 63 is cleared"
	::= { dpsRTUv2 19127 }

dpsRTUv2p18128Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 64 is set"
	::= { dpsRTUv2 18128 }

dpsRTUv2p19128Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 2 point 64 is cleared"
	::= { dpsRTUv2 19128 }

dpsRTUv2p18129Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 1 is set"
	::= { dpsRTUv2 18129 }

dpsRTUv2p19129Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 1 is cleared"
	::= { dpsRTUv2 19129 }

dpsRTUv2p18130Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 2 is set"
	::= { dpsRTUv2 18130 }

dpsRTUv2p19130Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 2 is cleared"
	::= { dpsRTUv2 19130 }

dpsRTUv2p18131Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 3 is set"
	::= { dpsRTUv2 18131 }

dpsRTUv2p19131Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 3 is cleared"
	::= { dpsRTUv2 19131 }

dpsRTUv2p18132Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 4 is set"
	::= { dpsRTUv2 18132 }

dpsRTUv2p19132Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 4 is cleared"
	::= { dpsRTUv2 19132 }

dpsRTUv2p18133Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 5 is set"
	::= { dpsRTUv2 18133 }

dpsRTUv2p19133Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 5 is cleared"
	::= { dpsRTUv2 19133 }

dpsRTUv2p18134Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 6 is set"
	::= { dpsRTUv2 18134 }

dpsRTUv2p19134Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 6 is cleared"
	::= { dpsRTUv2 19134 }

dpsRTUv2p18135Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 7 is set"
	::= { dpsRTUv2 18135 }

dpsRTUv2p19135Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 7 is cleared"
	::= { dpsRTUv2 19135 }

dpsRTUv2p18136Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 8 is set"
	::= { dpsRTUv2 18136 }

dpsRTUv2p19136Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 8 is cleared"
	::= { dpsRTUv2 19136 }

dpsRTUv2p18137Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 9 is set"
	::= { dpsRTUv2 18137 }

dpsRTUv2p19137Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 9 is cleared"
	::= { dpsRTUv2 19137 }

dpsRTUv2p18138Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 10 is set"
	::= { dpsRTUv2 18138 }

dpsRTUv2p19138Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 10 is cleared"
	::= { dpsRTUv2 19138 }

dpsRTUv2p18139Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 11 is set"
	::= { dpsRTUv2 18139 }

dpsRTUv2p19139Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 11 is cleared"
	::= { dpsRTUv2 19139 }

dpsRTUv2p18140Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 12 is set"
	::= { dpsRTUv2 18140 }

dpsRTUv2p19140Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 12 is cleared"
	::= { dpsRTUv2 19140 }

dpsRTUv2p18141Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 13 is set"
	::= { dpsRTUv2 18141 }

dpsRTUv2p19141Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 13 is cleared"
	::= { dpsRTUv2 19141 }

dpsRTUv2p18142Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 14 is set"
	::= { dpsRTUv2 18142 }

dpsRTUv2p19142Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 14 is cleared"
	::= { dpsRTUv2 19142 }

dpsRTUv2p18143Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 15 is set"
	::= { dpsRTUv2 18143 }

dpsRTUv2p19143Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 15 is cleared"
	::= { dpsRTUv2 19143 }

dpsRTUv2p18144Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 16 is set"
	::= { dpsRTUv2 18144 }

dpsRTUv2p19144Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 16 is cleared"
	::= { dpsRTUv2 19144 }

dpsRTUv2p18145Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 17 is set"
	::= { dpsRTUv2 18145 }

dpsRTUv2p19145Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 17 is cleared"
	::= { dpsRTUv2 19145 }

dpsRTUv2p18146Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 18 is set"
	::= { dpsRTUv2 18146 }

dpsRTUv2p19146Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 18 is cleared"
	::= { dpsRTUv2 19146 }

dpsRTUv2p18147Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 19 is set"
	::= { dpsRTUv2 18147 }

dpsRTUv2p19147Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 19 is cleared"
	::= { dpsRTUv2 19147 }

dpsRTUv2p18148Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 20 is set"
	::= { dpsRTUv2 18148 }

dpsRTUv2p19148Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 20 is cleared"
	::= { dpsRTUv2 19148 }

dpsRTUv2p18149Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 21 is set"
	::= { dpsRTUv2 18149 }

dpsRTUv2p19149Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 21 is cleared"
	::= { dpsRTUv2 19149 }

dpsRTUv2p18150Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 22 is set"
	::= { dpsRTUv2 18150 }

dpsRTUv2p19150Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 22 is cleared"
	::= { dpsRTUv2 19150 }

dpsRTUv2p18151Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 23 is set"
	::= { dpsRTUv2 18151 }

dpsRTUv2p19151Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 23 is cleared"
	::= { dpsRTUv2 19151 }

dpsRTUv2p18152Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 24 is set"
	::= { dpsRTUv2 18152 }

dpsRTUv2p19152Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 24 is cleared"
	::= { dpsRTUv2 19152 }

dpsRTUv2p18153Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 25 is set"
	::= { dpsRTUv2 18153 }

dpsRTUv2p19153Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 25 is cleared"
	::= { dpsRTUv2 19153 }

dpsRTUv2p18154Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 26 is set"
	::= { dpsRTUv2 18154 }

dpsRTUv2p19154Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 26 is cleared"
	::= { dpsRTUv2 19154 }

dpsRTUv2p18155Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 27 is set"
	::= { dpsRTUv2 18155 }

dpsRTUv2p19155Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 27 is cleared"
	::= { dpsRTUv2 19155 }

dpsRTUv2p18156Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 28 is set"
	::= { dpsRTUv2 18156 }

dpsRTUv2p19156Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 28 is cleared"
	::= { dpsRTUv2 19156 }

dpsRTUv2p18157Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 29 is set"
	::= { dpsRTUv2 18157 }

dpsRTUv2p19157Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 29 is cleared"
	::= { dpsRTUv2 19157 }

dpsRTUv2p18158Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 30 is set"
	::= { dpsRTUv2 18158 }

dpsRTUv2p19158Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 30 is cleared"
	::= { dpsRTUv2 19158 }

dpsRTUv2p18159Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 31 is set"
	::= { dpsRTUv2 18159 }

dpsRTUv2p19159Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 31 is cleared"
	::= { dpsRTUv2 19159 }

dpsRTUv2p18160Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 32 is set"
	::= { dpsRTUv2 18160 }

dpsRTUv2p19160Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 32 is cleared"
	::= { dpsRTUv2 19160 }

dpsRTUv2p18161Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 33 is set"
	::= { dpsRTUv2 18161 }

dpsRTUv2p19161Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 33 is cleared"
	::= { dpsRTUv2 19161 }

dpsRTUv2p18162Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 34 is set"
	::= { dpsRTUv2 18162 }

dpsRTUv2p19162Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 34 is cleared"
	::= { dpsRTUv2 19162 }

dpsRTUv2p18163Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 35 is set"
	::= { dpsRTUv2 18163 }

dpsRTUv2p19163Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 35 is cleared"
	::= { dpsRTUv2 19163 }

dpsRTUv2p18164Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 36 is set"
	::= { dpsRTUv2 18164 }

dpsRTUv2p19164Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 36 is cleared"
	::= { dpsRTUv2 19164 }

dpsRTUv2p18165Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 37 is set"
	::= { dpsRTUv2 18165 }

dpsRTUv2p19165Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 37 is cleared"
	::= { dpsRTUv2 19165 }

dpsRTUv2p18166Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 38 is set"
	::= { dpsRTUv2 18166 }

dpsRTUv2p19166Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 38 is cleared"
	::= { dpsRTUv2 19166 }

dpsRTUv2p18167Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 39 is set"
	::= { dpsRTUv2 18167 }

dpsRTUv2p19167Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 39 is cleared"
	::= { dpsRTUv2 19167 }

dpsRTUv2p18168Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 40 is set"
	::= { dpsRTUv2 18168 }

dpsRTUv2p19168Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 40 is cleared"
	::= { dpsRTUv2 19168 }

dpsRTUv2p18169Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 41 is set"
	::= { dpsRTUv2 18169 }

dpsRTUv2p19169Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 41 is cleared"
	::= { dpsRTUv2 19169 }

dpsRTUv2p18170Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 42 is set"
	::= { dpsRTUv2 18170 }

dpsRTUv2p19170Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 42 is cleared"
	::= { dpsRTUv2 19170 }

dpsRTUv2p18171Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 43 is set"
	::= { dpsRTUv2 18171 }

dpsRTUv2p19171Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 43 is cleared"
	::= { dpsRTUv2 19171 }

dpsRTUv2p18172Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 44 is set"
	::= { dpsRTUv2 18172 }

dpsRTUv2p19172Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 44 is cleared"
	::= { dpsRTUv2 19172 }

dpsRTUv2p18173Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 45 is set"
	::= { dpsRTUv2 18173 }

dpsRTUv2p19173Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 45 is cleared"
	::= { dpsRTUv2 19173 }

dpsRTUv2p18174Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 46 is set"
	::= { dpsRTUv2 18174 }

dpsRTUv2p19174Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 46 is cleared"
	::= { dpsRTUv2 19174 }

dpsRTUv2p18175Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 47 is set"
	::= { dpsRTUv2 18175 }

dpsRTUv2p19175Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 47 is cleared"
	::= { dpsRTUv2 19175 }

dpsRTUv2p18176Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 48 is set"
	::= { dpsRTUv2 18176 }

dpsRTUv2p19176Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 48 is cleared"
	::= { dpsRTUv2 19176 }

dpsRTUv2p18177Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 49 is set"
	::= { dpsRTUv2 18177 }

dpsRTUv2p19177Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 49 is cleared"
	::= { dpsRTUv2 19177 }

dpsRTUv2p18178Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 50 is set"
	::= { dpsRTUv2 18178 }

dpsRTUv2p19178Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 50 is cleared"
	::= { dpsRTUv2 19178 }

dpsRTUv2p18179Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 51 is set"
	::= { dpsRTUv2 18179 }

dpsRTUv2p19179Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 51 is cleared"
	::= { dpsRTUv2 19179 }

dpsRTUv2p18180Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 52 is set"
	::= { dpsRTUv2 18180 }

dpsRTUv2p19180Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 52 is cleared"
	::= { dpsRTUv2 19180 }

dpsRTUv2p18181Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 53 is set"
	::= { dpsRTUv2 18181 }

dpsRTUv2p19181Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 53 is cleared"
	::= { dpsRTUv2 19181 }

dpsRTUv2p18182Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 54 is set"
	::= { dpsRTUv2 18182 }

dpsRTUv2p19182Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 54 is cleared"
	::= { dpsRTUv2 19182 }

dpsRTUv2p18183Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 55 is set"
	::= { dpsRTUv2 18183 }

dpsRTUv2p19183Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 55 is cleared"
	::= { dpsRTUv2 19183 }

dpsRTUv2p18184Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 56 is set"
	::= { dpsRTUv2 18184 }

dpsRTUv2p19184Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 56 is cleared"
	::= { dpsRTUv2 19184 }

dpsRTUv2p18185Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 57 is set"
	::= { dpsRTUv2 18185 }

dpsRTUv2p19185Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 57 is cleared"
	::= { dpsRTUv2 19185 }

dpsRTUv2p18186Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 58 is set"
	::= { dpsRTUv2 18186 }

dpsRTUv2p19186Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 58 is cleared"
	::= { dpsRTUv2 19186 }

dpsRTUv2p18187Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 59 is set"
	::= { dpsRTUv2 18187 }

dpsRTUv2p19187Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 59 is cleared"
	::= { dpsRTUv2 19187 }

dpsRTUv2p18188Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 60 is set"
	::= { dpsRTUv2 18188 }

dpsRTUv2p19188Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 60 is cleared"
	::= { dpsRTUv2 19188 }

dpsRTUv2p18189Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 61 is set"
	::= { dpsRTUv2 18189 }

dpsRTUv2p19189Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 61 is cleared"
	::= { dpsRTUv2 19189 }

dpsRTUv2p18190Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 62 is set"
	::= { dpsRTUv2 18190 }

dpsRTUv2p19190Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 62 is cleared"
	::= { dpsRTUv2 19190 }

dpsRTUv2p18191Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 63 is set"
	::= { dpsRTUv2 18191 }

dpsRTUv2p19191Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 63 is cleared"
	::= { dpsRTUv2 19191 }

dpsRTUv2p18192Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 64 is set"
	::= { dpsRTUv2 18192 }

dpsRTUv2p19192Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 3 point 64 is cleared"
	::= { dpsRTUv2 19192 }

dpsRTUv2p18193Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 1 is set"
	::= { dpsRTUv2 18193 }

dpsRTUv2p19193Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 1 is cleared"
	::= { dpsRTUv2 19193 }

dpsRTUv2p18194Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 2 is set"
	::= { dpsRTUv2 18194 }

dpsRTUv2p19194Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 2 is cleared"
	::= { dpsRTUv2 19194 }

dpsRTUv2p18195Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 3 is set"
	::= { dpsRTUv2 18195 }

dpsRTUv2p19195Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 3 is cleared"
	::= { dpsRTUv2 19195 }

dpsRTUv2p18196Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 4 is set"
	::= { dpsRTUv2 18196 }

dpsRTUv2p19196Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 4 is cleared"
	::= { dpsRTUv2 19196 }

dpsRTUv2p18197Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 5 is set"
	::= { dpsRTUv2 18197 }

dpsRTUv2p19197Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 5 is cleared"
	::= { dpsRTUv2 19197 }

dpsRTUv2p18198Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 6 is set"
	::= { dpsRTUv2 18198 }

dpsRTUv2p19198Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 6 is cleared"
	::= { dpsRTUv2 19198 }

dpsRTUv2p18199Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 7 is set"
	::= { dpsRTUv2 18199 }

dpsRTUv2p19199Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 7 is cleared"
	::= { dpsRTUv2 19199 }

dpsRTUv2p18200Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 8 is set"
	::= { dpsRTUv2 18200 }

dpsRTUv2p19200Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 8 is cleared"
	::= { dpsRTUv2 19200 }

dpsRTUv2p18201Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 9 is set"
	::= { dpsRTUv2 18201 }

dpsRTUv2p19201Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 9 is cleared"
	::= { dpsRTUv2 19201 }

dpsRTUv2p18202Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 10 is set"
	::= { dpsRTUv2 18202 }

dpsRTUv2p19202Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 10 is cleared"
	::= { dpsRTUv2 19202 }

dpsRTUv2p18203Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 11 is set"
	::= { dpsRTUv2 18203 }

dpsRTUv2p19203Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 11 is cleared"
	::= { dpsRTUv2 19203 }

dpsRTUv2p18204Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 12 is set"
	::= { dpsRTUv2 18204 }

dpsRTUv2p19204Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 12 is cleared"
	::= { dpsRTUv2 19204 }

dpsRTUv2p18205Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 13 is set"
	::= { dpsRTUv2 18205 }

dpsRTUv2p19205Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 13 is cleared"
	::= { dpsRTUv2 19205 }

dpsRTUv2p18206Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 14 is set"
	::= { dpsRTUv2 18206 }

dpsRTUv2p19206Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 14 is cleared"
	::= { dpsRTUv2 19206 }

dpsRTUv2p18207Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 15 is set"
	::= { dpsRTUv2 18207 }

dpsRTUv2p19207Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 15 is cleared"
	::= { dpsRTUv2 19207 }

dpsRTUv2p18208Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 16 is set"
	::= { dpsRTUv2 18208 }

dpsRTUv2p19208Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 16 is cleared"
	::= { dpsRTUv2 19208 }

dpsRTUv2p18209Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 17 is set"
	::= { dpsRTUv2 18209 }

dpsRTUv2p19209Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 17 is cleared"
	::= { dpsRTUv2 19209 }

dpsRTUv2p18210Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 18 is set"
	::= { dpsRTUv2 18210 }

dpsRTUv2p19210Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 18 is cleared"
	::= { dpsRTUv2 19210 }

dpsRTUv2p18211Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 19 is set"
	::= { dpsRTUv2 18211 }

dpsRTUv2p19211Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 19 is cleared"
	::= { dpsRTUv2 19211 }

dpsRTUv2p18212Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 20 is set"
	::= { dpsRTUv2 18212 }

dpsRTUv2p19212Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 20 is cleared"
	::= { dpsRTUv2 19212 }

dpsRTUv2p18213Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 21 is set"
	::= { dpsRTUv2 18213 }

dpsRTUv2p19213Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 21 is cleared"
	::= { dpsRTUv2 19213 }

dpsRTUv2p18214Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 22 is set"
	::= { dpsRTUv2 18214 }

dpsRTUv2p19214Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 22 is cleared"
	::= { dpsRTUv2 19214 }

dpsRTUv2p18215Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 23 is set"
	::= { dpsRTUv2 18215 }

dpsRTUv2p19215Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 23 is cleared"
	::= { dpsRTUv2 19215 }

dpsRTUv2p18216Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 24 is set"
	::= { dpsRTUv2 18216 }

dpsRTUv2p19216Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 24 is cleared"
	::= { dpsRTUv2 19216 }

dpsRTUv2p18217Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 25 is set"
	::= { dpsRTUv2 18217 }

dpsRTUv2p19217Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 25 is cleared"
	::= { dpsRTUv2 19217 }

dpsRTUv2p18218Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 26 is set"
	::= { dpsRTUv2 18218 }

dpsRTUv2p19218Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 26 is cleared"
	::= { dpsRTUv2 19218 }

dpsRTUv2p18219Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 27 is set"
	::= { dpsRTUv2 18219 }

dpsRTUv2p19219Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 27 is cleared"
	::= { dpsRTUv2 19219 }

dpsRTUv2p18220Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 28 is set"
	::= { dpsRTUv2 18220 }

dpsRTUv2p19220Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 28 is cleared"
	::= { dpsRTUv2 19220 }

dpsRTUv2p18221Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 29 is set"
	::= { dpsRTUv2 18221 }

dpsRTUv2p19221Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 29 is cleared"
	::= { dpsRTUv2 19221 }

dpsRTUv2p18222Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 30 is set"
	::= { dpsRTUv2 18222 }

dpsRTUv2p19222Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 30 is cleared"
	::= { dpsRTUv2 19222 }

dpsRTUv2p18223Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 31 is set"
	::= { dpsRTUv2 18223 }

dpsRTUv2p19223Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 31 is cleared"
	::= { dpsRTUv2 19223 }

dpsRTUv2p18224Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 32 is set"
	::= { dpsRTUv2 18224 }

dpsRTUv2p19224Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 32 is cleared"
	::= { dpsRTUv2 19224 }

dpsRTUv2p18225Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 33 is set"
	::= { dpsRTUv2 18225 }

dpsRTUv2p19225Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 33 is cleared"
	::= { dpsRTUv2 19225 }

dpsRTUv2p18226Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 34 is set"
	::= { dpsRTUv2 18226 }

dpsRTUv2p19226Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 34 is cleared"
	::= { dpsRTUv2 19226 }

dpsRTUv2p18227Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 35 is set"
	::= { dpsRTUv2 18227 }

dpsRTUv2p19227Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 35 is cleared"
	::= { dpsRTUv2 19227 }

dpsRTUv2p18228Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 36 is set"
	::= { dpsRTUv2 18228 }

dpsRTUv2p19228Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 36 is cleared"
	::= { dpsRTUv2 19228 }

dpsRTUv2p18229Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 37 is set"
	::= { dpsRTUv2 18229 }

dpsRTUv2p19229Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 37 is cleared"
	::= { dpsRTUv2 19229 }

dpsRTUv2p18230Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 38 is set"
	::= { dpsRTUv2 18230 }

dpsRTUv2p19230Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 38 is cleared"
	::= { dpsRTUv2 19230 }

dpsRTUv2p18231Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 39 is set"
	::= { dpsRTUv2 18231 }

dpsRTUv2p19231Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 39 is cleared"
	::= { dpsRTUv2 19231 }

dpsRTUv2p18232Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 40 is set"
	::= { dpsRTUv2 18232 }

dpsRTUv2p19232Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 40 is cleared"
	::= { dpsRTUv2 19232 }

dpsRTUv2p18233Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 41 is set"
	::= { dpsRTUv2 18233 }

dpsRTUv2p19233Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 41 is cleared"
	::= { dpsRTUv2 19233 }

dpsRTUv2p18234Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 42 is set"
	::= { dpsRTUv2 18234 }

dpsRTUv2p19234Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 42 is cleared"
	::= { dpsRTUv2 19234 }

dpsRTUv2p18235Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 43 is set"
	::= { dpsRTUv2 18235 }

dpsRTUv2p19235Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 43 is cleared"
	::= { dpsRTUv2 19235 }

dpsRTUv2p18236Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 44 is set"
	::= { dpsRTUv2 18236 }

dpsRTUv2p19236Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 44 is cleared"
	::= { dpsRTUv2 19236 }

dpsRTUv2p18237Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 45 is set"
	::= { dpsRTUv2 18237 }

dpsRTUv2p19237Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 45 is cleared"
	::= { dpsRTUv2 19237 }

dpsRTUv2p18238Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 46 is set"
	::= { dpsRTUv2 18238 }

dpsRTUv2p19238Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 46 is cleared"
	::= { dpsRTUv2 19238 }

dpsRTUv2p18239Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 47 is set"
	::= { dpsRTUv2 18239 }

dpsRTUv2p19239Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 47 is cleared"
	::= { dpsRTUv2 19239 }

dpsRTUv2p18240Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 48 is set"
	::= { dpsRTUv2 18240 }

dpsRTUv2p19240Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 48 is cleared"
	::= { dpsRTUv2 19240 }

dpsRTUv2p18241Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 49 is set"
	::= { dpsRTUv2 18241 }

dpsRTUv2p19241Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 49 is cleared"
	::= { dpsRTUv2 19241 }

dpsRTUv2p18242Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 50 is set"
	::= { dpsRTUv2 18242 }

dpsRTUv2p19242Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 50 is cleared"
	::= { dpsRTUv2 19242 }

dpsRTUv2p18243Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 51 is set"
	::= { dpsRTUv2 18243 }

dpsRTUv2p19243Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 51 is cleared"
	::= { dpsRTUv2 19243 }

dpsRTUv2p18244Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 52 is set"
	::= { dpsRTUv2 18244 }

dpsRTUv2p19244Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 52 is cleared"
	::= { dpsRTUv2 19244 }

dpsRTUv2p18245Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 53 is set"
	::= { dpsRTUv2 18245 }

dpsRTUv2p19245Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 53 is cleared"
	::= { dpsRTUv2 19245 }

dpsRTUv2p18246Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 54 is set"
	::= { dpsRTUv2 18246 }

dpsRTUv2p19246Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 54 is cleared"
	::= { dpsRTUv2 19246 }

dpsRTUv2p18247Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 55 is set"
	::= { dpsRTUv2 18247 }

dpsRTUv2p19247Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 55 is cleared"
	::= { dpsRTUv2 19247 }

dpsRTUv2p18248Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 56 is set"
	::= { dpsRTUv2 18248 }

dpsRTUv2p19248Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 56 is cleared"
	::= { dpsRTUv2 19248 }

dpsRTUv2p18249Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 57 is set"
	::= { dpsRTUv2 18249 }

dpsRTUv2p19249Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 57 is cleared"
	::= { dpsRTUv2 19249 }

dpsRTUv2p18250Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 58 is set"
	::= { dpsRTUv2 18250 }

dpsRTUv2p19250Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 58 is cleared"
	::= { dpsRTUv2 19250 }

dpsRTUv2p18251Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 59 is set"
	::= { dpsRTUv2 18251 }

dpsRTUv2p19251Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 59 is cleared"
	::= { dpsRTUv2 19251 }

dpsRTUv2p18252Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 60 is set"
	::= { dpsRTUv2 18252 }

dpsRTUv2p19252Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 60 is cleared"
	::= { dpsRTUv2 19252 }

dpsRTUv2p18253Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 61 is set"
	::= { dpsRTUv2 18253 }

dpsRTUv2p19253Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 61 is cleared"
	::= { dpsRTUv2 19253 }

dpsRTUv2p18254Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 62 is set"
	::= { dpsRTUv2 18254 }

dpsRTUv2p19254Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 62 is cleared"
	::= { dpsRTUv2 19254 }

dpsRTUv2p18255Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 63 is set"
	::= { dpsRTUv2 18255 }

dpsRTUv2p19255Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 63 is cleared"
	::= { dpsRTUv2 19255 }

dpsRTUv2p18256Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 64 is set"
	::= { dpsRTUv2 18256 }

dpsRTUv2p19256Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 4 point 64 is cleared"
	::= { dpsRTUv2 19256 }

dpsRTUv2p18257Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 1 is set"
	::= { dpsRTUv2 18257 }

dpsRTUv2p19257Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 1 is cleared"
	::= { dpsRTUv2 19257 }

dpsRTUv2p18258Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 2 is set"
	::= { dpsRTUv2 18258 }

dpsRTUv2p19258Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 2 is cleared"
	::= { dpsRTUv2 19258 }

dpsRTUv2p18259Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 3 is set"
	::= { dpsRTUv2 18259 }

dpsRTUv2p19259Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 3 is cleared"
	::= { dpsRTUv2 19259 }

dpsRTUv2p18260Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 4 is set"
	::= { dpsRTUv2 18260 }

dpsRTUv2p19260Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 4 is cleared"
	::= { dpsRTUv2 19260 }

dpsRTUv2p18261Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 5 is set"
	::= { dpsRTUv2 18261 }

dpsRTUv2p19261Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 5 is cleared"
	::= { dpsRTUv2 19261 }

dpsRTUv2p18262Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 6 is set"
	::= { dpsRTUv2 18262 }

dpsRTUv2p19262Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 6 is cleared"
	::= { dpsRTUv2 19262 }

dpsRTUv2p18263Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 7 is set"
	::= { dpsRTUv2 18263 }

dpsRTUv2p19263Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 7 is cleared"
	::= { dpsRTUv2 19263 }

dpsRTUv2p18264Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 8 is set"
	::= { dpsRTUv2 18264 }

dpsRTUv2p19264Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 8 is cleared"
	::= { dpsRTUv2 19264 }

dpsRTUv2p18265Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 9 is set"
	::= { dpsRTUv2 18265 }

dpsRTUv2p19265Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 9 is cleared"
	::= { dpsRTUv2 19265 }

dpsRTUv2p18266Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 10 is set"
	::= { dpsRTUv2 18266 }

dpsRTUv2p19266Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 10 is cleared"
	::= { dpsRTUv2 19266 }

dpsRTUv2p18267Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 11 is set"
	::= { dpsRTUv2 18267 }

dpsRTUv2p19267Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 11 is cleared"
	::= { dpsRTUv2 19267 }

dpsRTUv2p18268Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 12 is set"
	::= { dpsRTUv2 18268 }

dpsRTUv2p19268Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 12 is cleared"
	::= { dpsRTUv2 19268 }

dpsRTUv2p18269Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 13 is set"
	::= { dpsRTUv2 18269 }

dpsRTUv2p19269Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 13 is cleared"
	::= { dpsRTUv2 19269 }

dpsRTUv2p18270Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 14 is set"
	::= { dpsRTUv2 18270 }

dpsRTUv2p19270Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 14 is cleared"
	::= { dpsRTUv2 19270 }

dpsRTUv2p18271Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 15 is set"
	::= { dpsRTUv2 18271 }

dpsRTUv2p19271Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 15 is cleared"
	::= { dpsRTUv2 19271 }

dpsRTUv2p18272Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 16 is set"
	::= { dpsRTUv2 18272 }

dpsRTUv2p19272Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 16 is cleared"
	::= { dpsRTUv2 19272 }

dpsRTUv2p18273Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 17 is set"
	::= { dpsRTUv2 18273 }

dpsRTUv2p19273Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 17 is cleared"
	::= { dpsRTUv2 19273 }

dpsRTUv2p18274Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 18 is set"
	::= { dpsRTUv2 18274 }

dpsRTUv2p19274Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 18 is cleared"
	::= { dpsRTUv2 19274 }

dpsRTUv2p18275Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 19 is set"
	::= { dpsRTUv2 18275 }

dpsRTUv2p19275Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 19 is cleared"
	::= { dpsRTUv2 19275 }

dpsRTUv2p18276Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 20 is set"
	::= { dpsRTUv2 18276 }

dpsRTUv2p19276Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 20 is cleared"
	::= { dpsRTUv2 19276 }

dpsRTUv2p18277Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 21 is set"
	::= { dpsRTUv2 18277 }

dpsRTUv2p19277Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 21 is cleared"
	::= { dpsRTUv2 19277 }

dpsRTUv2p18278Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 22 is set"
	::= { dpsRTUv2 18278 }

dpsRTUv2p19278Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 22 is cleared"
	::= { dpsRTUv2 19278 }

dpsRTUv2p18279Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 23 is set"
	::= { dpsRTUv2 18279 }

dpsRTUv2p19279Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 23 is cleared"
	::= { dpsRTUv2 19279 }

dpsRTUv2p18280Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 24 is set"
	::= { dpsRTUv2 18280 }

dpsRTUv2p19280Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 24 is cleared"
	::= { dpsRTUv2 19280 }

dpsRTUv2p18281Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 25 is set"
	::= { dpsRTUv2 18281 }

dpsRTUv2p19281Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 25 is cleared"
	::= { dpsRTUv2 19281 }

dpsRTUv2p18282Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 26 is set"
	::= { dpsRTUv2 18282 }

dpsRTUv2p19282Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 26 is cleared"
	::= { dpsRTUv2 19282 }

dpsRTUv2p18283Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 27 is set"
	::= { dpsRTUv2 18283 }

dpsRTUv2p19283Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 27 is cleared"
	::= { dpsRTUv2 19283 }

dpsRTUv2p18284Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 28 is set"
	::= { dpsRTUv2 18284 }

dpsRTUv2p19284Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 28 is cleared"
	::= { dpsRTUv2 19284 }

dpsRTUv2p18285Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 29 is set"
	::= { dpsRTUv2 18285 }

dpsRTUv2p19285Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 29 is cleared"
	::= { dpsRTUv2 19285 }

dpsRTUv2p18286Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 30 is set"
	::= { dpsRTUv2 18286 }

dpsRTUv2p19286Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 30 is cleared"
	::= { dpsRTUv2 19286 }

dpsRTUv2p18287Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 31 is set"
	::= { dpsRTUv2 18287 }

dpsRTUv2p19287Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 31 is cleared"
	::= { dpsRTUv2 19287 }

dpsRTUv2p18288Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 32 is set"
	::= { dpsRTUv2 18288 }

dpsRTUv2p19288Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 32 is cleared"
	::= { dpsRTUv2 19288 }

dpsRTUv2p18289Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 33 is set"
	::= { dpsRTUv2 18289 }

dpsRTUv2p19289Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 33 is cleared"
	::= { dpsRTUv2 19289 }

dpsRTUv2p18290Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 34 is set"
	::= { dpsRTUv2 18290 }

dpsRTUv2p19290Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 34 is cleared"
	::= { dpsRTUv2 19290 }

dpsRTUv2p18291Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 35 is set"
	::= { dpsRTUv2 18291 }

dpsRTUv2p19291Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 35 is cleared"
	::= { dpsRTUv2 19291 }

dpsRTUv2p18292Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 36 is set"
	::= { dpsRTUv2 18292 }

dpsRTUv2p19292Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 36 is cleared"
	::= { dpsRTUv2 19292 }

dpsRTUv2p18293Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 37 is set"
	::= { dpsRTUv2 18293 }

dpsRTUv2p19293Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 37 is cleared"
	::= { dpsRTUv2 19293 }

dpsRTUv2p18294Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 38 is set"
	::= { dpsRTUv2 18294 }

dpsRTUv2p19294Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 38 is cleared"
	::= { dpsRTUv2 19294 }

dpsRTUv2p18295Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 39 is set"
	::= { dpsRTUv2 18295 }

dpsRTUv2p19295Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 39 is cleared"
	::= { dpsRTUv2 19295 }

dpsRTUv2p18296Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 40 is set"
	::= { dpsRTUv2 18296 }

dpsRTUv2p19296Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 40 is cleared"
	::= { dpsRTUv2 19296 }

dpsRTUv2p18297Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 41 is set"
	::= { dpsRTUv2 18297 }

dpsRTUv2p19297Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 41 is cleared"
	::= { dpsRTUv2 19297 }

dpsRTUv2p18298Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 42 is set"
	::= { dpsRTUv2 18298 }

dpsRTUv2p19298Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 42 is cleared"
	::= { dpsRTUv2 19298 }

dpsRTUv2p18299Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 43 is set"
	::= { dpsRTUv2 18299 }

dpsRTUv2p19299Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 43 is cleared"
	::= { dpsRTUv2 19299 }

dpsRTUv2p18300Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 44 is set"
	::= { dpsRTUv2 18300 }

dpsRTUv2p19300Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 44 is cleared"
	::= { dpsRTUv2 19300 }

dpsRTUv2p18301Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 45 is set"
	::= { dpsRTUv2 18301 }

dpsRTUv2p19301Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 45 is cleared"
	::= { dpsRTUv2 19301 }

dpsRTUv2p18302Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 46 is set"
	::= { dpsRTUv2 18302 }

dpsRTUv2p19302Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 46 is cleared"
	::= { dpsRTUv2 19302 }

dpsRTUv2p18303Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 47 is set"
	::= { dpsRTUv2 18303 }

dpsRTUv2p19303Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 47 is cleared"
	::= { dpsRTUv2 19303 }

dpsRTUv2p18304Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 48 is set"
	::= { dpsRTUv2 18304 }

dpsRTUv2p19304Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 48 is cleared"
	::= { dpsRTUv2 19304 }

dpsRTUv2p18305Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 49 is set"
	::= { dpsRTUv2 18305 }

dpsRTUv2p19305Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 49 is cleared"
	::= { dpsRTUv2 19305 }

dpsRTUv2p18306Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 50 is set"
	::= { dpsRTUv2 18306 }

dpsRTUv2p19306Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 50 is cleared"
	::= { dpsRTUv2 19306 }

dpsRTUv2p18307Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 51 is set"
	::= { dpsRTUv2 18307 }

dpsRTUv2p19307Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 51 is cleared"
	::= { dpsRTUv2 19307 }

dpsRTUv2p18308Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 52 is set"
	::= { dpsRTUv2 18308 }

dpsRTUv2p19308Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 52 is cleared"
	::= { dpsRTUv2 19308 }

dpsRTUv2p18309Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 53 is set"
	::= { dpsRTUv2 18309 }

dpsRTUv2p19309Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 53 is cleared"
	::= { dpsRTUv2 19309 }

dpsRTUv2p18310Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 54 is set"
	::= { dpsRTUv2 18310 }

dpsRTUv2p19310Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 54 is cleared"
	::= { dpsRTUv2 19310 }

dpsRTUv2p18311Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 55 is set"
	::= { dpsRTUv2 18311 }

dpsRTUv2p19311Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 55 is cleared"
	::= { dpsRTUv2 19311 }

dpsRTUv2p18312Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 56 is set"
	::= { dpsRTUv2 18312 }

dpsRTUv2p19312Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 56 is cleared"
	::= { dpsRTUv2 19312 }

dpsRTUv2p18313Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 57 is set"
	::= { dpsRTUv2 18313 }

dpsRTUv2p19313Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 57 is cleared"
	::= { dpsRTUv2 19313 }

dpsRTUv2p18314Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 58 is set"
	::= { dpsRTUv2 18314 }

dpsRTUv2p19314Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 58 is cleared"
	::= { dpsRTUv2 19314 }

dpsRTUv2p18315Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 59 is set"
	::= { dpsRTUv2 18315 }

dpsRTUv2p19315Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 59 is cleared"
	::= { dpsRTUv2 19315 }

dpsRTUv2p18316Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 60 is set"
	::= { dpsRTUv2 18316 }

dpsRTUv2p19316Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 60 is cleared"
	::= { dpsRTUv2 19316 }

dpsRTUv2p18317Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 61 is set"
	::= { dpsRTUv2 18317 }

dpsRTUv2p19317Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 61 is cleared"
	::= { dpsRTUv2 19317 }

dpsRTUv2p18318Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 62 is set"
	::= { dpsRTUv2 18318 }

dpsRTUv2p19318Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 62 is cleared"
	::= { dpsRTUv2 19318 }

dpsRTUv2p18319Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 63 is set"
	::= { dpsRTUv2 18319 }

dpsRTUv2p19319Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 63 is cleared"
	::= { dpsRTUv2 19319 }

dpsRTUv2p18320Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 64 is set"
	::= { dpsRTUv2 18320 }

dpsRTUv2p19320Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 5 point 64 is cleared"
	::= { dpsRTUv2 19320 }

dpsRTUv2p18321Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 1 is set"
	::= { dpsRTUv2 18321 }

dpsRTUv2p19321Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 1 is cleared"
	::= { dpsRTUv2 19321 }

dpsRTUv2p18322Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 2 is set"
	::= { dpsRTUv2 18322 }

dpsRTUv2p19322Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 2 is cleared"
	::= { dpsRTUv2 19322 }

dpsRTUv2p18323Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 3 is set"
	::= { dpsRTUv2 18323 }

dpsRTUv2p19323Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 3 is cleared"
	::= { dpsRTUv2 19323 }

dpsRTUv2p18324Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 4 is set"
	::= { dpsRTUv2 18324 }

dpsRTUv2p19324Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 4 is cleared"
	::= { dpsRTUv2 19324 }

dpsRTUv2p18325Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 5 is set"
	::= { dpsRTUv2 18325 }

dpsRTUv2p19325Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 5 is cleared"
	::= { dpsRTUv2 19325 }

dpsRTUv2p18326Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 6 is set"
	::= { dpsRTUv2 18326 }

dpsRTUv2p19326Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 6 is cleared"
	::= { dpsRTUv2 19326 }

dpsRTUv2p18327Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 7 is set"
	::= { dpsRTUv2 18327 }

dpsRTUv2p19327Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 7 is cleared"
	::= { dpsRTUv2 19327 }

dpsRTUv2p18328Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 8 is set"
	::= { dpsRTUv2 18328 }

dpsRTUv2p19328Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 8 is cleared"
	::= { dpsRTUv2 19328 }

dpsRTUv2p18329Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 9 is set"
	::= { dpsRTUv2 18329 }

dpsRTUv2p19329Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 9 is cleared"
	::= { dpsRTUv2 19329 }

dpsRTUv2p18330Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 10 is set"
	::= { dpsRTUv2 18330 }

dpsRTUv2p19330Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 10 is cleared"
	::= { dpsRTUv2 19330 }

dpsRTUv2p18331Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 11 is set"
	::= { dpsRTUv2 18331 }

dpsRTUv2p19331Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 11 is cleared"
	::= { dpsRTUv2 19331 }

dpsRTUv2p18332Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 12 is set"
	::= { dpsRTUv2 18332 }

dpsRTUv2p19332Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 12 is cleared"
	::= { dpsRTUv2 19332 }

dpsRTUv2p18333Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 13 is set"
	::= { dpsRTUv2 18333 }

dpsRTUv2p19333Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 13 is cleared"
	::= { dpsRTUv2 19333 }

dpsRTUv2p18334Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 14 is set"
	::= { dpsRTUv2 18334 }

dpsRTUv2p19334Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 14 is cleared"
	::= { dpsRTUv2 19334 }

dpsRTUv2p18335Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 15 is set"
	::= { dpsRTUv2 18335 }

dpsRTUv2p19335Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 15 is cleared"
	::= { dpsRTUv2 19335 }

dpsRTUv2p18336Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 16 is set"
	::= { dpsRTUv2 18336 }

dpsRTUv2p19336Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 16 is cleared"
	::= { dpsRTUv2 19336 }

dpsRTUv2p18337Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 17 is set"
	::= { dpsRTUv2 18337 }

dpsRTUv2p19337Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 17 is cleared"
	::= { dpsRTUv2 19337 }

dpsRTUv2p18338Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 18 is set"
	::= { dpsRTUv2 18338 }

dpsRTUv2p19338Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 18 is cleared"
	::= { dpsRTUv2 19338 }

dpsRTUv2p18339Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 19 is set"
	::= { dpsRTUv2 18339 }

dpsRTUv2p19339Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 19 is cleared"
	::= { dpsRTUv2 19339 }

dpsRTUv2p18340Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 20 is set"
	::= { dpsRTUv2 18340 }

dpsRTUv2p19340Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 20 is cleared"
	::= { dpsRTUv2 19340 }

dpsRTUv2p18341Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 21 is set"
	::= { dpsRTUv2 18341 }

dpsRTUv2p19341Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 21 is cleared"
	::= { dpsRTUv2 19341 }

dpsRTUv2p18342Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 22 is set"
	::= { dpsRTUv2 18342 }

dpsRTUv2p19342Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 22 is cleared"
	::= { dpsRTUv2 19342 }

dpsRTUv2p18343Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 23 is set"
	::= { dpsRTUv2 18343 }

dpsRTUv2p19343Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 23 is cleared"
	::= { dpsRTUv2 19343 }

dpsRTUv2p18344Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 24 is set"
	::= { dpsRTUv2 18344 }

dpsRTUv2p19344Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 24 is cleared"
	::= { dpsRTUv2 19344 }

dpsRTUv2p18345Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 25 is set"
	::= { dpsRTUv2 18345 }

dpsRTUv2p19345Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 25 is cleared"
	::= { dpsRTUv2 19345 }

dpsRTUv2p18346Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 26 is set"
	::= { dpsRTUv2 18346 }

dpsRTUv2p19346Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 26 is cleared"
	::= { dpsRTUv2 19346 }

dpsRTUv2p18347Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 27 is set"
	::= { dpsRTUv2 18347 }

dpsRTUv2p19347Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 27 is cleared"
	::= { dpsRTUv2 19347 }

dpsRTUv2p18348Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 28 is set"
	::= { dpsRTUv2 18348 }

dpsRTUv2p19348Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 28 is cleared"
	::= { dpsRTUv2 19348 }

dpsRTUv2p18349Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 29 is set"
	::= { dpsRTUv2 18349 }

dpsRTUv2p19349Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 29 is cleared"
	::= { dpsRTUv2 19349 }

dpsRTUv2p18350Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 30 is set"
	::= { dpsRTUv2 18350 }

dpsRTUv2p19350Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 30 is cleared"
	::= { dpsRTUv2 19350 }

dpsRTUv2p18351Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 31 is set"
	::= { dpsRTUv2 18351 }

dpsRTUv2p19351Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 31 is cleared"
	::= { dpsRTUv2 19351 }

dpsRTUv2p18352Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 32 is set"
	::= { dpsRTUv2 18352 }

dpsRTUv2p19352Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 32 is cleared"
	::= { dpsRTUv2 19352 }

dpsRTUv2p18353Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 33 is set"
	::= { dpsRTUv2 18353 }

dpsRTUv2p19353Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 33 is cleared"
	::= { dpsRTUv2 19353 }

dpsRTUv2p18354Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 34 is set"
	::= { dpsRTUv2 18354 }

dpsRTUv2p19354Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 34 is cleared"
	::= { dpsRTUv2 19354 }

dpsRTUv2p18355Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 35 is set"
	::= { dpsRTUv2 18355 }

dpsRTUv2p19355Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 35 is cleared"
	::= { dpsRTUv2 19355 }

dpsRTUv2p18356Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 36 is set"
	::= { dpsRTUv2 18356 }

dpsRTUv2p19356Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 36 is cleared"
	::= { dpsRTUv2 19356 }

dpsRTUv2p18357Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 37 is set"
	::= { dpsRTUv2 18357 }

dpsRTUv2p19357Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 37 is cleared"
	::= { dpsRTUv2 19357 }

dpsRTUv2p18358Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 38 is set"
	::= { dpsRTUv2 18358 }

dpsRTUv2p19358Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 38 is cleared"
	::= { dpsRTUv2 19358 }

dpsRTUv2p18359Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 39 is set"
	::= { dpsRTUv2 18359 }

dpsRTUv2p19359Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 39 is cleared"
	::= { dpsRTUv2 19359 }

dpsRTUv2p18360Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 40 is set"
	::= { dpsRTUv2 18360 }

dpsRTUv2p19360Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 40 is cleared"
	::= { dpsRTUv2 19360 }

dpsRTUv2p18361Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 41 is set"
	::= { dpsRTUv2 18361 }

dpsRTUv2p19361Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 41 is cleared"
	::= { dpsRTUv2 19361 }

dpsRTUv2p18362Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 42 is set"
	::= { dpsRTUv2 18362 }

dpsRTUv2p19362Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 42 is cleared"
	::= { dpsRTUv2 19362 }

dpsRTUv2p18363Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 43 is set"
	::= { dpsRTUv2 18363 }

dpsRTUv2p19363Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 43 is cleared"
	::= { dpsRTUv2 19363 }

dpsRTUv2p18364Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 44 is set"
	::= { dpsRTUv2 18364 }

dpsRTUv2p19364Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 44 is cleared"
	::= { dpsRTUv2 19364 }

dpsRTUv2p18365Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 45 is set"
	::= { dpsRTUv2 18365 }

dpsRTUv2p19365Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 45 is cleared"
	::= { dpsRTUv2 19365 }

dpsRTUv2p18366Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 46 is set"
	::= { dpsRTUv2 18366 }

dpsRTUv2p19366Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 46 is cleared"
	::= { dpsRTUv2 19366 }

dpsRTUv2p18367Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 47 is set"
	::= { dpsRTUv2 18367 }

dpsRTUv2p19367Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 47 is cleared"
	::= { dpsRTUv2 19367 }

dpsRTUv2p18368Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 48 is set"
	::= { dpsRTUv2 18368 }

dpsRTUv2p19368Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 48 is cleared"
	::= { dpsRTUv2 19368 }

dpsRTUv2p18369Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 49 is set"
	::= { dpsRTUv2 18369 }

dpsRTUv2p19369Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 49 is cleared"
	::= { dpsRTUv2 19369 }

dpsRTUv2p18370Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 50 is set"
	::= { dpsRTUv2 18370 }

dpsRTUv2p19370Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 50 is cleared"
	::= { dpsRTUv2 19370 }

dpsRTUv2p18371Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 51 is set"
	::= { dpsRTUv2 18371 }

dpsRTUv2p19371Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 51 is cleared"
	::= { dpsRTUv2 19371 }

dpsRTUv2p18372Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 52 is set"
	::= { dpsRTUv2 18372 }

dpsRTUv2p19372Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 52 is cleared"
	::= { dpsRTUv2 19372 }

dpsRTUv2p18373Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 53 is set"
	::= { dpsRTUv2 18373 }

dpsRTUv2p19373Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 53 is cleared"
	::= { dpsRTUv2 19373 }

dpsRTUv2p18374Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 54 is set"
	::= { dpsRTUv2 18374 }

dpsRTUv2p19374Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 54 is cleared"
	::= { dpsRTUv2 19374 }

dpsRTUv2p18375Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 55 is set"
	::= { dpsRTUv2 18375 }

dpsRTUv2p19375Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 55 is cleared"
	::= { dpsRTUv2 19375 }

dpsRTUv2p18376Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 56 is set"
	::= { dpsRTUv2 18376 }

dpsRTUv2p19376Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 56 is cleared"
	::= { dpsRTUv2 19376 }

dpsRTUv2p18377Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 57 is set"
	::= { dpsRTUv2 18377 }

dpsRTUv2p19377Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 57 is cleared"
	::= { dpsRTUv2 19377 }

dpsRTUv2p18378Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 58 is set"
	::= { dpsRTUv2 18378 }

dpsRTUv2p19378Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 58 is cleared"
	::= { dpsRTUv2 19378 }

dpsRTUv2p18379Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 59 is set"
	::= { dpsRTUv2 18379 }

dpsRTUv2p19379Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 59 is cleared"
	::= { dpsRTUv2 19379 }

dpsRTUv2p18380Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 60 is set"
	::= { dpsRTUv2 18380 }

dpsRTUv2p19380Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 60 is cleared"
	::= { dpsRTUv2 19380 }

dpsRTUv2p18381Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 61 is set"
	::= { dpsRTUv2 18381 }

dpsRTUv2p19381Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 61 is cleared"
	::= { dpsRTUv2 19381 }

dpsRTUv2p18382Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 62 is set"
	::= { dpsRTUv2 18382 }

dpsRTUv2p19382Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 62 is cleared"
	::= { dpsRTUv2 19382 }

dpsRTUv2p18383Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 63 is set"
	::= { dpsRTUv2 18383 }

dpsRTUv2p19383Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 63 is cleared"
	::= { dpsRTUv2 19383 }

dpsRTUv2p18384Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 64 is set"
	::= { dpsRTUv2 18384 }

dpsRTUv2p19384Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 6 point 64 is cleared"
	::= { dpsRTUv2 19384 }

dpsRTUv2p18385Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 1 is set"
	::= { dpsRTUv2 18385 }

dpsRTUv2p19385Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 1 is cleared"
	::= { dpsRTUv2 19385 }

dpsRTUv2p18386Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 2 is set"
	::= { dpsRTUv2 18386 }

dpsRTUv2p19386Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 2 is cleared"
	::= { dpsRTUv2 19386 }

dpsRTUv2p18387Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 3 is set"
	::= { dpsRTUv2 18387 }

dpsRTUv2p19387Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 3 is cleared"
	::= { dpsRTUv2 19387 }

dpsRTUv2p18388Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 4 is set"
	::= { dpsRTUv2 18388 }

dpsRTUv2p19388Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 4 is cleared"
	::= { dpsRTUv2 19388 }

dpsRTUv2p18389Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 5 is set"
	::= { dpsRTUv2 18389 }

dpsRTUv2p19389Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 5 is cleared"
	::= { dpsRTUv2 19389 }

dpsRTUv2p18390Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 6 is set"
	::= { dpsRTUv2 18390 }

dpsRTUv2p19390Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 6 is cleared"
	::= { dpsRTUv2 19390 }

dpsRTUv2p18391Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 7 is set"
	::= { dpsRTUv2 18391 }

dpsRTUv2p19391Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 7 is cleared"
	::= { dpsRTUv2 19391 }

dpsRTUv2p18392Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 8 is set"
	::= { dpsRTUv2 18392 }

dpsRTUv2p19392Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 8 is cleared"
	::= { dpsRTUv2 19392 }

dpsRTUv2p18393Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 9 is set"
	::= { dpsRTUv2 18393 }

dpsRTUv2p19393Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 9 is cleared"
	::= { dpsRTUv2 19393 }

dpsRTUv2p18394Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 10 is set"
	::= { dpsRTUv2 18394 }

dpsRTUv2p19394Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 10 is cleared"
	::= { dpsRTUv2 19394 }

dpsRTUv2p18395Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 11 is set"
	::= { dpsRTUv2 18395 }

dpsRTUv2p19395Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 11 is cleared"
	::= { dpsRTUv2 19395 }

dpsRTUv2p18396Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 12 is set"
	::= { dpsRTUv2 18396 }

dpsRTUv2p19396Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 12 is cleared"
	::= { dpsRTUv2 19396 }

dpsRTUv2p18397Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 13 is set"
	::= { dpsRTUv2 18397 }

dpsRTUv2p19397Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 13 is cleared"
	::= { dpsRTUv2 19397 }

dpsRTUv2p18398Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 14 is set"
	::= { dpsRTUv2 18398 }

dpsRTUv2p19398Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 14 is cleared"
	::= { dpsRTUv2 19398 }

dpsRTUv2p18399Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 15 is set"
	::= { dpsRTUv2 18399 }

dpsRTUv2p19399Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 15 is cleared"
	::= { dpsRTUv2 19399 }

dpsRTUv2p18400Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 16 is set"
	::= { dpsRTUv2 18400 }

dpsRTUv2p19400Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 16 is cleared"
	::= { dpsRTUv2 19400 }

dpsRTUv2p18401Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 17 is set"
	::= { dpsRTUv2 18401 }

dpsRTUv2p19401Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 17 is cleared"
	::= { dpsRTUv2 19401 }

dpsRTUv2p18402Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 18 is set"
	::= { dpsRTUv2 18402 }

dpsRTUv2p19402Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 18 is cleared"
	::= { dpsRTUv2 19402 }

dpsRTUv2p18403Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 19 is set"
	::= { dpsRTUv2 18403 }

dpsRTUv2p19403Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 19 is cleared"
	::= { dpsRTUv2 19403 }

dpsRTUv2p18404Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 20 is set"
	::= { dpsRTUv2 18404 }

dpsRTUv2p19404Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 20 is cleared"
	::= { dpsRTUv2 19404 }

dpsRTUv2p18405Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 21 is set"
	::= { dpsRTUv2 18405 }

dpsRTUv2p19405Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 21 is cleared"
	::= { dpsRTUv2 19405 }

dpsRTUv2p18406Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 22 is set"
	::= { dpsRTUv2 18406 }

dpsRTUv2p19406Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 22 is cleared"
	::= { dpsRTUv2 19406 }

dpsRTUv2p18407Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 23 is set"
	::= { dpsRTUv2 18407 }

dpsRTUv2p19407Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 23 is cleared"
	::= { dpsRTUv2 19407 }

dpsRTUv2p18408Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 24 is set"
	::= { dpsRTUv2 18408 }

dpsRTUv2p19408Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 24 is cleared"
	::= { dpsRTUv2 19408 }

dpsRTUv2p18409Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 25 is set"
	::= { dpsRTUv2 18409 }

dpsRTUv2p19409Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 25 is cleared"
	::= { dpsRTUv2 19409 }

dpsRTUv2p18410Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 26 is set"
	::= { dpsRTUv2 18410 }

dpsRTUv2p19410Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 26 is cleared"
	::= { dpsRTUv2 19410 }

dpsRTUv2p18411Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 27 is set"
	::= { dpsRTUv2 18411 }

dpsRTUv2p19411Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 27 is cleared"
	::= { dpsRTUv2 19411 }

dpsRTUv2p18412Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 28 is set"
	::= { dpsRTUv2 18412 }

dpsRTUv2p19412Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 28 is cleared"
	::= { dpsRTUv2 19412 }

dpsRTUv2p18413Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 29 is set"
	::= { dpsRTUv2 18413 }

dpsRTUv2p19413Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 29 is cleared"
	::= { dpsRTUv2 19413 }

dpsRTUv2p18414Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 30 is set"
	::= { dpsRTUv2 18414 }

dpsRTUv2p19414Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 30 is cleared"
	::= { dpsRTUv2 19414 }

dpsRTUv2p18415Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 31 is set"
	::= { dpsRTUv2 18415 }

dpsRTUv2p19415Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 31 is cleared"
	::= { dpsRTUv2 19415 }

dpsRTUv2p18416Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 32 is set"
	::= { dpsRTUv2 18416 }

dpsRTUv2p19416Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 32 is cleared"
	::= { dpsRTUv2 19416 }

dpsRTUv2p18417Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 33 is set"
	::= { dpsRTUv2 18417 }

dpsRTUv2p19417Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 33 is cleared"
	::= { dpsRTUv2 19417 }

dpsRTUv2p18418Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 34 is set"
	::= { dpsRTUv2 18418 }

dpsRTUv2p19418Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 34 is cleared"
	::= { dpsRTUv2 19418 }

dpsRTUv2p18419Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 35 is set"
	::= { dpsRTUv2 18419 }

dpsRTUv2p19419Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 35 is cleared"
	::= { dpsRTUv2 19419 }

dpsRTUv2p18420Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 36 is set"
	::= { dpsRTUv2 18420 }

dpsRTUv2p19420Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 36 is cleared"
	::= { dpsRTUv2 19420 }

dpsRTUv2p18421Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 37 is set"
	::= { dpsRTUv2 18421 }

dpsRTUv2p19421Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 37 is cleared"
	::= { dpsRTUv2 19421 }

dpsRTUv2p18422Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 38 is set"
	::= { dpsRTUv2 18422 }

dpsRTUv2p19422Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 38 is cleared"
	::= { dpsRTUv2 19422 }

dpsRTUv2p18423Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 39 is set"
	::= { dpsRTUv2 18423 }

dpsRTUv2p19423Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 39 is cleared"
	::= { dpsRTUv2 19423 }

dpsRTUv2p18424Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 40 is set"
	::= { dpsRTUv2 18424 }

dpsRTUv2p19424Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 40 is cleared"
	::= { dpsRTUv2 19424 }

dpsRTUv2p18425Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 41 is set"
	::= { dpsRTUv2 18425 }

dpsRTUv2p19425Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 41 is cleared"
	::= { dpsRTUv2 19425 }

dpsRTUv2p18426Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 42 is set"
	::= { dpsRTUv2 18426 }

dpsRTUv2p19426Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 42 is cleared"
	::= { dpsRTUv2 19426 }

dpsRTUv2p18427Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 43 is set"
	::= { dpsRTUv2 18427 }

dpsRTUv2p19427Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 43 is cleared"
	::= { dpsRTUv2 19427 }

dpsRTUv2p18428Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 44 is set"
	::= { dpsRTUv2 18428 }

dpsRTUv2p19428Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 44 is cleared"
	::= { dpsRTUv2 19428 }

dpsRTUv2p18429Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 45 is set"
	::= { dpsRTUv2 18429 }

dpsRTUv2p19429Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 45 is cleared"
	::= { dpsRTUv2 19429 }

dpsRTUv2p18430Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 46 is set"
	::= { dpsRTUv2 18430 }

dpsRTUv2p19430Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 46 is cleared"
	::= { dpsRTUv2 19430 }

dpsRTUv2p18431Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 47 is set"
	::= { dpsRTUv2 18431 }

dpsRTUv2p19431Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 47 is cleared"
	::= { dpsRTUv2 19431 }

dpsRTUv2p18432Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 48 is set"
	::= { dpsRTUv2 18432 }

dpsRTUv2p19432Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 48 is cleared"
	::= { dpsRTUv2 19432 }

dpsRTUv2p18433Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 49 is set"
	::= { dpsRTUv2 18433 }

dpsRTUv2p19433Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 49 is cleared"
	::= { dpsRTUv2 19433 }

dpsRTUv2p18434Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 50 is set"
	::= { dpsRTUv2 18434 }

dpsRTUv2p19434Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 50 is cleared"
	::= { dpsRTUv2 19434 }

dpsRTUv2p18435Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 51 is set"
	::= { dpsRTUv2 18435 }

dpsRTUv2p19435Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 51 is cleared"
	::= { dpsRTUv2 19435 }

dpsRTUv2p18436Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 52 is set"
	::= { dpsRTUv2 18436 }

dpsRTUv2p19436Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 52 is cleared"
	::= { dpsRTUv2 19436 }

dpsRTUv2p18437Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 53 is set"
	::= { dpsRTUv2 18437 }

dpsRTUv2p19437Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 53 is cleared"
	::= { dpsRTUv2 19437 }

dpsRTUv2p18438Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 54 is set"
	::= { dpsRTUv2 18438 }

dpsRTUv2p19438Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 54 is cleared"
	::= { dpsRTUv2 19438 }

dpsRTUv2p18439Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 55 is set"
	::= { dpsRTUv2 18439 }

dpsRTUv2p19439Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 55 is cleared"
	::= { dpsRTUv2 19439 }

dpsRTUv2p18440Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 56 is set"
	::= { dpsRTUv2 18440 }

dpsRTUv2p19440Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 56 is cleared"
	::= { dpsRTUv2 19440 }

dpsRTUv2p18441Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 57 is set"
	::= { dpsRTUv2 18441 }

dpsRTUv2p19441Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 57 is cleared"
	::= { dpsRTUv2 19441 }

dpsRTUv2p18442Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 58 is set"
	::= { dpsRTUv2 18442 }

dpsRTUv2p19442Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 58 is cleared"
	::= { dpsRTUv2 19442 }

dpsRTUv2p18443Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 59 is set"
	::= { dpsRTUv2 18443 }

dpsRTUv2p19443Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 59 is cleared"
	::= { dpsRTUv2 19443 }

dpsRTUv2p18444Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 60 is set"
	::= { dpsRTUv2 18444 }

dpsRTUv2p19444Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 60 is cleared"
	::= { dpsRTUv2 19444 }

dpsRTUv2p18445Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 61 is set"
	::= { dpsRTUv2 18445 }

dpsRTUv2p19445Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 61 is cleared"
	::= { dpsRTUv2 19445 }

dpsRTUv2p18446Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 62 is set"
	::= { dpsRTUv2 18446 }

dpsRTUv2p19446Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 62 is cleared"
	::= { dpsRTUv2 19446 }

dpsRTUv2p18447Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 63 is set"
	::= { dpsRTUv2 18447 }

dpsRTUv2p19447Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 63 is cleared"
	::= { dpsRTUv2 19447 }

dpsRTUv2p18448Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 64 is set"
	::= { dpsRTUv2 18448 }

dpsRTUv2p19448Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 7 point 64 is cleared"
	::= { dpsRTUv2 19448 }

dpsRTUv2p18449Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 1 is set"
	::= { dpsRTUv2 18449 }

dpsRTUv2p19449Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 1 is cleared"
	::= { dpsRTUv2 19449 }

dpsRTUv2p18450Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 2 is set"
	::= { dpsRTUv2 18450 }

dpsRTUv2p19450Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 2 is cleared"
	::= { dpsRTUv2 19450 }

dpsRTUv2p18451Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 3 is set"
	::= { dpsRTUv2 18451 }

dpsRTUv2p19451Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 3 is cleared"
	::= { dpsRTUv2 19451 }

dpsRTUv2p18452Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 4 is set"
	::= { dpsRTUv2 18452 }

dpsRTUv2p19452Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 4 is cleared"
	::= { dpsRTUv2 19452 }

dpsRTUv2p18453Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 5 is set"
	::= { dpsRTUv2 18453 }

dpsRTUv2p19453Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 5 is cleared"
	::= { dpsRTUv2 19453 }

dpsRTUv2p18454Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 6 is set"
	::= { dpsRTUv2 18454 }

dpsRTUv2p19454Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 6 is cleared"
	::= { dpsRTUv2 19454 }

dpsRTUv2p18455Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 7 is set"
	::= { dpsRTUv2 18455 }

dpsRTUv2p19455Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 7 is cleared"
	::= { dpsRTUv2 19455 }

dpsRTUv2p18456Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 8 is set"
	::= { dpsRTUv2 18456 }

dpsRTUv2p19456Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 8 is cleared"
	::= { dpsRTUv2 19456 }

dpsRTUv2p18457Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 9 is set"
	::= { dpsRTUv2 18457 }

dpsRTUv2p19457Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 9 is cleared"
	::= { dpsRTUv2 19457 }

dpsRTUv2p18458Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 10 is set"
	::= { dpsRTUv2 18458 }

dpsRTUv2p19458Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 10 is cleared"
	::= { dpsRTUv2 19458 }

dpsRTUv2p18459Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 11 is set"
	::= { dpsRTUv2 18459 }

dpsRTUv2p19459Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 11 is cleared"
	::= { dpsRTUv2 19459 }

dpsRTUv2p18460Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 12 is set"
	::= { dpsRTUv2 18460 }

dpsRTUv2p19460Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 12 is cleared"
	::= { dpsRTUv2 19460 }

dpsRTUv2p18461Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 13 is set"
	::= { dpsRTUv2 18461 }

dpsRTUv2p19461Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 13 is cleared"
	::= { dpsRTUv2 19461 }

dpsRTUv2p18462Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 14 is set"
	::= { dpsRTUv2 18462 }

dpsRTUv2p19462Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 14 is cleared"
	::= { dpsRTUv2 19462 }

dpsRTUv2p18463Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 15 is set"
	::= { dpsRTUv2 18463 }

dpsRTUv2p19463Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 15 is cleared"
	::= { dpsRTUv2 19463 }

dpsRTUv2p18464Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 16 is set"
	::= { dpsRTUv2 18464 }

dpsRTUv2p19464Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 16 is cleared"
	::= { dpsRTUv2 19464 }

dpsRTUv2p18465Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 17 is set"
	::= { dpsRTUv2 18465 }

dpsRTUv2p19465Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 17 is cleared"
	::= { dpsRTUv2 19465 }

dpsRTUv2p18466Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 18 is set"
	::= { dpsRTUv2 18466 }

dpsRTUv2p19466Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 18 is cleared"
	::= { dpsRTUv2 19466 }

dpsRTUv2p18467Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 19 is set"
	::= { dpsRTUv2 18467 }

dpsRTUv2p19467Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 19 is cleared"
	::= { dpsRTUv2 19467 }

dpsRTUv2p18468Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 20 is set"
	::= { dpsRTUv2 18468 }

dpsRTUv2p19468Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 20 is cleared"
	::= { dpsRTUv2 19468 }

dpsRTUv2p18469Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 21 is set"
	::= { dpsRTUv2 18469 }

dpsRTUv2p19469Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 21 is cleared"
	::= { dpsRTUv2 19469 }

dpsRTUv2p18470Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 22 is set"
	::= { dpsRTUv2 18470 }

dpsRTUv2p19470Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 22 is cleared"
	::= { dpsRTUv2 19470 }

dpsRTUv2p18471Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 23 is set"
	::= { dpsRTUv2 18471 }

dpsRTUv2p19471Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 23 is cleared"
	::= { dpsRTUv2 19471 }

dpsRTUv2p18472Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 24 is set"
	::= { dpsRTUv2 18472 }

dpsRTUv2p19472Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 24 is cleared"
	::= { dpsRTUv2 19472 }

dpsRTUv2p18473Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 25 is set"
	::= { dpsRTUv2 18473 }

dpsRTUv2p19473Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 25 is cleared"
	::= { dpsRTUv2 19473 }

dpsRTUv2p18474Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 26 is set"
	::= { dpsRTUv2 18474 }

dpsRTUv2p19474Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 26 is cleared"
	::= { dpsRTUv2 19474 }

dpsRTUv2p18475Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 27 is set"
	::= { dpsRTUv2 18475 }

dpsRTUv2p19475Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 27 is cleared"
	::= { dpsRTUv2 19475 }

dpsRTUv2p18476Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 28 is set"
	::= { dpsRTUv2 18476 }

dpsRTUv2p19476Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 28 is cleared"
	::= { dpsRTUv2 19476 }

dpsRTUv2p18477Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 29 is set"
	::= { dpsRTUv2 18477 }

dpsRTUv2p19477Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 29 is cleared"
	::= { dpsRTUv2 19477 }

dpsRTUv2p18478Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 30 is set"
	::= { dpsRTUv2 18478 }

dpsRTUv2p19478Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 30 is cleared"
	::= { dpsRTUv2 19478 }

dpsRTUv2p18479Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 31 is set"
	::= { dpsRTUv2 18479 }

dpsRTUv2p19479Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 31 is cleared"
	::= { dpsRTUv2 19479 }

dpsRTUv2p18480Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 32 is set"
	::= { dpsRTUv2 18480 }

dpsRTUv2p19480Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 32 is cleared"
	::= { dpsRTUv2 19480 }

dpsRTUv2p18481Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 33 is set"
	::= { dpsRTUv2 18481 }

dpsRTUv2p19481Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 33 is cleared"
	::= { dpsRTUv2 19481 }

dpsRTUv2p18482Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 34 is set"
	::= { dpsRTUv2 18482 }

dpsRTUv2p19482Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 34 is cleared"
	::= { dpsRTUv2 19482 }

dpsRTUv2p18483Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 35 is set"
	::= { dpsRTUv2 18483 }

dpsRTUv2p19483Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 35 is cleared"
	::= { dpsRTUv2 19483 }

dpsRTUv2p18484Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 36 is set"
	::= { dpsRTUv2 18484 }

dpsRTUv2p19484Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 36 is cleared"
	::= { dpsRTUv2 19484 }

dpsRTUv2p18485Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 37 is set"
	::= { dpsRTUv2 18485 }

dpsRTUv2p19485Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 37 is cleared"
	::= { dpsRTUv2 19485 }

dpsRTUv2p18486Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 38 is set"
	::= { dpsRTUv2 18486 }

dpsRTUv2p19486Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 38 is cleared"
	::= { dpsRTUv2 19486 }

dpsRTUv2p18487Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 39 is set"
	::= { dpsRTUv2 18487 }

dpsRTUv2p19487Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 39 is cleared"
	::= { dpsRTUv2 19487 }

dpsRTUv2p18488Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 40 is set"
	::= { dpsRTUv2 18488 }

dpsRTUv2p19488Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 40 is cleared"
	::= { dpsRTUv2 19488 }

dpsRTUv2p18489Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 41 is set"
	::= { dpsRTUv2 18489 }

dpsRTUv2p19489Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 41 is cleared"
	::= { dpsRTUv2 19489 }

dpsRTUv2p18490Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 42 is set"
	::= { dpsRTUv2 18490 }

dpsRTUv2p19490Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 42 is cleared"
	::= { dpsRTUv2 19490 }

dpsRTUv2p18491Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 43 is set"
	::= { dpsRTUv2 18491 }

dpsRTUv2p19491Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 43 is cleared"
	::= { dpsRTUv2 19491 }

dpsRTUv2p18492Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 44 is set"
	::= { dpsRTUv2 18492 }

dpsRTUv2p19492Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 44 is cleared"
	::= { dpsRTUv2 19492 }

dpsRTUv2p18493Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 45 is set"
	::= { dpsRTUv2 18493 }

dpsRTUv2p19493Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 45 is cleared"
	::= { dpsRTUv2 19493 }

dpsRTUv2p18494Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 46 is set"
	::= { dpsRTUv2 18494 }

dpsRTUv2p19494Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 46 is cleared"
	::= { dpsRTUv2 19494 }

dpsRTUv2p18495Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 47 is set"
	::= { dpsRTUv2 18495 }

dpsRTUv2p19495Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 47 is cleared"
	::= { dpsRTUv2 19495 }

dpsRTUv2p18496Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 48 is set"
	::= { dpsRTUv2 18496 }

dpsRTUv2p19496Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 48 is cleared"
	::= { dpsRTUv2 19496 }

dpsRTUv2p18497Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 49 is set"
	::= { dpsRTUv2 18497 }

dpsRTUv2p19497Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 49 is cleared"
	::= { dpsRTUv2 19497 }

dpsRTUv2p18498Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 50 is set"
	::= { dpsRTUv2 18498 }

dpsRTUv2p19498Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 50 is cleared"
	::= { dpsRTUv2 19498 }

dpsRTUv2p18499Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 51 is set"
	::= { dpsRTUv2 18499 }

dpsRTUv2p19499Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 51 is cleared"
	::= { dpsRTUv2 19499 }

dpsRTUv2p18500Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 52 is set"
	::= { dpsRTUv2 18500 }

dpsRTUv2p19500Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 52 is cleared"
	::= { dpsRTUv2 19500 }

dpsRTUv2p18501Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 53 is set"
	::= { dpsRTUv2 18501 }

dpsRTUv2p19501Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 53 is cleared"
	::= { dpsRTUv2 19501 }

dpsRTUv2p18502Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 54 is set"
	::= { dpsRTUv2 18502 }

dpsRTUv2p19502Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 54 is cleared"
	::= { dpsRTUv2 19502 }

dpsRTUv2p18503Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 55 is set"
	::= { dpsRTUv2 18503 }

dpsRTUv2p19503Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 55 is cleared"
	::= { dpsRTUv2 19503 }

dpsRTUv2p18504Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 56 is set"
	::= { dpsRTUv2 18504 }

dpsRTUv2p19504Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 56 is cleared"
	::= { dpsRTUv2 19504 }

dpsRTUv2p18505Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 57 is set"
	::= { dpsRTUv2 18505 }

dpsRTUv2p19505Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 57 is cleared"
	::= { dpsRTUv2 19505 }

dpsRTUv2p18506Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 58 is set"
	::= { dpsRTUv2 18506 }

dpsRTUv2p19506Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 58 is cleared"
	::= { dpsRTUv2 19506 }

dpsRTUv2p18507Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 59 is set"
	::= { dpsRTUv2 18507 }

dpsRTUv2p19507Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 59 is cleared"
	::= { dpsRTUv2 19507 }

dpsRTUv2p18508Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 60 is set"
	::= { dpsRTUv2 18508 }

dpsRTUv2p19508Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 60 is cleared"
	::= { dpsRTUv2 19508 }

dpsRTUv2p18509Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 61 is set"
	::= { dpsRTUv2 18509 }

dpsRTUv2p19509Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 61 is cleared"
	::= { dpsRTUv2 19509 }

dpsRTUv2p18510Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 62 is set"
	::= { dpsRTUv2 18510 }

dpsRTUv2p19510Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 62 is cleared"
	::= { dpsRTUv2 19510 }

dpsRTUv2p18511Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 63 is set"
	::= { dpsRTUv2 18511 }

dpsRTUv2p19511Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 63 is cleared"
	::= { dpsRTUv2 19511 }

dpsRTUv2p18512Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 64 is set"
	::= { dpsRTUv2 18512 }

dpsRTUv2p19512Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 5 display 8 point 64 is cleared"
	::= { dpsRTUv2 19512 }

dpsRTUv2p20001Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 1 is set"
	::= { dpsRTUv2 20001 }

dpsRTUv2p21001Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 1 is cleared"
	::= { dpsRTUv2 21001 }

dpsRTUv2p20002Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 2 is set"
	::= { dpsRTUv2 20002 }

dpsRTUv2p21002Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 2 is cleared"
	::= { dpsRTUv2 21002 }

dpsRTUv2p20003Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 3 is set"
	::= { dpsRTUv2 20003 }

dpsRTUv2p21003Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 3 is cleared"
	::= { dpsRTUv2 21003 }

dpsRTUv2p20004Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 4 is set"
	::= { dpsRTUv2 20004 }

dpsRTUv2p21004Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 4 is cleared"
	::= { dpsRTUv2 21004 }

dpsRTUv2p20005Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 5 is set"
	::= { dpsRTUv2 20005 }

dpsRTUv2p21005Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 5 is cleared"
	::= { dpsRTUv2 21005 }

dpsRTUv2p20006Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 6 is set"
	::= { dpsRTUv2 20006 }

dpsRTUv2p21006Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 6 is cleared"
	::= { dpsRTUv2 21006 }

dpsRTUv2p20007Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 7 is set"
	::= { dpsRTUv2 20007 }

dpsRTUv2p21007Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 7 is cleared"
	::= { dpsRTUv2 21007 }

dpsRTUv2p20008Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 8 is set"
	::= { dpsRTUv2 20008 }

dpsRTUv2p21008Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 8 is cleared"
	::= { dpsRTUv2 21008 }

dpsRTUv2p20009Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 9 is set"
	::= { dpsRTUv2 20009 }

dpsRTUv2p21009Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 9 is cleared"
	::= { dpsRTUv2 21009 }

dpsRTUv2p20010Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 10 is set"
	::= { dpsRTUv2 20010 }

dpsRTUv2p21010Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 10 is cleared"
	::= { dpsRTUv2 21010 }

dpsRTUv2p20011Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 11 is set"
	::= { dpsRTUv2 20011 }

dpsRTUv2p21011Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 11 is cleared"
	::= { dpsRTUv2 21011 }

dpsRTUv2p20012Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 12 is set"
	::= { dpsRTUv2 20012 }

dpsRTUv2p21012Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 12 is cleared"
	::= { dpsRTUv2 21012 }

dpsRTUv2p20013Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 13 is set"
	::= { dpsRTUv2 20013 }

dpsRTUv2p21013Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 13 is cleared"
	::= { dpsRTUv2 21013 }

dpsRTUv2p20014Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 14 is set"
	::= { dpsRTUv2 20014 }

dpsRTUv2p21014Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 14 is cleared"
	::= { dpsRTUv2 21014 }

dpsRTUv2p20015Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 15 is set"
	::= { dpsRTUv2 20015 }

dpsRTUv2p21015Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 15 is cleared"
	::= { dpsRTUv2 21015 }

dpsRTUv2p20016Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 16 is set"
	::= { dpsRTUv2 20016 }

dpsRTUv2p21016Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 16 is cleared"
	::= { dpsRTUv2 21016 }

dpsRTUv2p20017Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 17 is set"
	::= { dpsRTUv2 20017 }

dpsRTUv2p21017Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 17 is cleared"
	::= { dpsRTUv2 21017 }

dpsRTUv2p20018Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 18 is set"
	::= { dpsRTUv2 20018 }

dpsRTUv2p21018Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 18 is cleared"
	::= { dpsRTUv2 21018 }

dpsRTUv2p20019Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 19 is set"
	::= { dpsRTUv2 20019 }

dpsRTUv2p21019Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 19 is cleared"
	::= { dpsRTUv2 21019 }

dpsRTUv2p20020Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 20 is set"
	::= { dpsRTUv2 20020 }

dpsRTUv2p21020Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 20 is cleared"
	::= { dpsRTUv2 21020 }

dpsRTUv2p20021Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 21 is set"
	::= { dpsRTUv2 20021 }

dpsRTUv2p21021Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 21 is cleared"
	::= { dpsRTUv2 21021 }

dpsRTUv2p20022Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 22 is set"
	::= { dpsRTUv2 20022 }

dpsRTUv2p21022Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 22 is cleared"
	::= { dpsRTUv2 21022 }

dpsRTUv2p20023Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 23 is set"
	::= { dpsRTUv2 20023 }

dpsRTUv2p21023Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 23 is cleared"
	::= { dpsRTUv2 21023 }

dpsRTUv2p20024Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 24 is set"
	::= { dpsRTUv2 20024 }

dpsRTUv2p21024Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 24 is cleared"
	::= { dpsRTUv2 21024 }

dpsRTUv2p20025Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 25 is set"
	::= { dpsRTUv2 20025 }

dpsRTUv2p21025Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 25 is cleared"
	::= { dpsRTUv2 21025 }

dpsRTUv2p20026Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 26 is set"
	::= { dpsRTUv2 20026 }

dpsRTUv2p21026Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 26 is cleared"
	::= { dpsRTUv2 21026 }

dpsRTUv2p20027Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 27 is set"
	::= { dpsRTUv2 20027 }

dpsRTUv2p21027Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 27 is cleared"
	::= { dpsRTUv2 21027 }

dpsRTUv2p20028Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 28 is set"
	::= { dpsRTUv2 20028 }

dpsRTUv2p21028Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 28 is cleared"
	::= { dpsRTUv2 21028 }

dpsRTUv2p20029Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 29 is set"
	::= { dpsRTUv2 20029 }

dpsRTUv2p21029Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 29 is cleared"
	::= { dpsRTUv2 21029 }

dpsRTUv2p20030Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 30 is set"
	::= { dpsRTUv2 20030 }

dpsRTUv2p21030Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 30 is cleared"
	::= { dpsRTUv2 21030 }

dpsRTUv2p20031Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 31 is set"
	::= { dpsRTUv2 20031 }

dpsRTUv2p21031Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 31 is cleared"
	::= { dpsRTUv2 21031 }

dpsRTUv2p20032Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 32 is set"
	::= { dpsRTUv2 20032 }

dpsRTUv2p21032Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 32 is cleared"
	::= { dpsRTUv2 21032 }

dpsRTUv2p20033Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 33 is set"
	::= { dpsRTUv2 20033 }

dpsRTUv2p21033Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 33 is cleared"
	::= { dpsRTUv2 21033 }

dpsRTUv2p20034Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 34 is set"
	::= { dpsRTUv2 20034 }

dpsRTUv2p21034Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 34 is cleared"
	::= { dpsRTUv2 21034 }

dpsRTUv2p20035Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 35 is set"
	::= { dpsRTUv2 20035 }

dpsRTUv2p21035Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 35 is cleared"
	::= { dpsRTUv2 21035 }

dpsRTUv2p20036Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 36 is set"
	::= { dpsRTUv2 20036 }

dpsRTUv2p21036Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 36 is cleared"
	::= { dpsRTUv2 21036 }

dpsRTUv2p20037Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 37 is set"
	::= { dpsRTUv2 20037 }

dpsRTUv2p21037Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 37 is cleared"
	::= { dpsRTUv2 21037 }

dpsRTUv2p20038Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 38 is set"
	::= { dpsRTUv2 20038 }

dpsRTUv2p21038Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 38 is cleared"
	::= { dpsRTUv2 21038 }

dpsRTUv2p20039Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 39 is set"
	::= { dpsRTUv2 20039 }

dpsRTUv2p21039Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 39 is cleared"
	::= { dpsRTUv2 21039 }

dpsRTUv2p20040Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 40 is set"
	::= { dpsRTUv2 20040 }

dpsRTUv2p21040Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 40 is cleared"
	::= { dpsRTUv2 21040 }

dpsRTUv2p20041Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 41 is set"
	::= { dpsRTUv2 20041 }

dpsRTUv2p21041Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 41 is cleared"
	::= { dpsRTUv2 21041 }

dpsRTUv2p20042Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 42 is set"
	::= { dpsRTUv2 20042 }

dpsRTUv2p21042Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 42 is cleared"
	::= { dpsRTUv2 21042 }

dpsRTUv2p20043Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 43 is set"
	::= { dpsRTUv2 20043 }

dpsRTUv2p21043Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 43 is cleared"
	::= { dpsRTUv2 21043 }

dpsRTUv2p20044Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 44 is set"
	::= { dpsRTUv2 20044 }

dpsRTUv2p21044Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 44 is cleared"
	::= { dpsRTUv2 21044 }

dpsRTUv2p20045Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 45 is set"
	::= { dpsRTUv2 20045 }

dpsRTUv2p21045Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 45 is cleared"
	::= { dpsRTUv2 21045 }

dpsRTUv2p20046Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 46 is set"
	::= { dpsRTUv2 20046 }

dpsRTUv2p21046Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 46 is cleared"
	::= { dpsRTUv2 21046 }

dpsRTUv2p20047Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 47 is set"
	::= { dpsRTUv2 20047 }

dpsRTUv2p21047Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 47 is cleared"
	::= { dpsRTUv2 21047 }

dpsRTUv2p20048Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 48 is set"
	::= { dpsRTUv2 20048 }

dpsRTUv2p21048Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 48 is cleared"
	::= { dpsRTUv2 21048 }

dpsRTUv2p20049Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 49 is set"
	::= { dpsRTUv2 20049 }

dpsRTUv2p21049Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 49 is cleared"
	::= { dpsRTUv2 21049 }

dpsRTUv2p20050Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 50 is set"
	::= { dpsRTUv2 20050 }

dpsRTUv2p21050Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 50 is cleared"
	::= { dpsRTUv2 21050 }

dpsRTUv2p20051Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 51 is set"
	::= { dpsRTUv2 20051 }

dpsRTUv2p21051Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 51 is cleared"
	::= { dpsRTUv2 21051 }

dpsRTUv2p20052Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 52 is set"
	::= { dpsRTUv2 20052 }

dpsRTUv2p21052Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 52 is cleared"
	::= { dpsRTUv2 21052 }

dpsRTUv2p20053Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 53 is set"
	::= { dpsRTUv2 20053 }

dpsRTUv2p21053Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 53 is cleared"
	::= { dpsRTUv2 21053 }

dpsRTUv2p20054Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 54 is set"
	::= { dpsRTUv2 20054 }

dpsRTUv2p21054Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 54 is cleared"
	::= { dpsRTUv2 21054 }

dpsRTUv2p20055Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 55 is set"
	::= { dpsRTUv2 20055 }

dpsRTUv2p21055Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 55 is cleared"
	::= { dpsRTUv2 21055 }

dpsRTUv2p20056Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 56 is set"
	::= { dpsRTUv2 20056 }

dpsRTUv2p21056Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 56 is cleared"
	::= { dpsRTUv2 21056 }

dpsRTUv2p20057Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 57 is set"
	::= { dpsRTUv2 20057 }

dpsRTUv2p21057Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 57 is cleared"
	::= { dpsRTUv2 21057 }

dpsRTUv2p20058Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 58 is set"
	::= { dpsRTUv2 20058 }

dpsRTUv2p21058Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 58 is cleared"
	::= { dpsRTUv2 21058 }

dpsRTUv2p20059Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 59 is set"
	::= { dpsRTUv2 20059 }

dpsRTUv2p21059Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 59 is cleared"
	::= { dpsRTUv2 21059 }

dpsRTUv2p20060Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 60 is set"
	::= { dpsRTUv2 20060 }

dpsRTUv2p21060Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 60 is cleared"
	::= { dpsRTUv2 21060 }

dpsRTUv2p20061Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 61 is set"
	::= { dpsRTUv2 20061 }

dpsRTUv2p21061Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 61 is cleared"
	::= { dpsRTUv2 21061 }

dpsRTUv2p20062Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 62 is set"
	::= { dpsRTUv2 20062 }

dpsRTUv2p21062Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 62 is cleared"
	::= { dpsRTUv2 21062 }

dpsRTUv2p20063Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 63 is set"
	::= { dpsRTUv2 20063 }

dpsRTUv2p21063Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 63 is cleared"
	::= { dpsRTUv2 21063 }

dpsRTUv2p20064Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 64 is set"
	::= { dpsRTUv2 20064 }

dpsRTUv2p21064Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 1 point 64 is cleared"
	::= { dpsRTUv2 21064 }

dpsRTUv2p20065Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 1 is set"
	::= { dpsRTUv2 20065 }

dpsRTUv2p21065Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 1 is cleared"
	::= { dpsRTUv2 21065 }

dpsRTUv2p20066Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 2 is set"
	::= { dpsRTUv2 20066 }

dpsRTUv2p21066Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 2 is cleared"
	::= { dpsRTUv2 21066 }

dpsRTUv2p20067Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 3 is set"
	::= { dpsRTUv2 20067 }

dpsRTUv2p21067Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 3 is cleared"
	::= { dpsRTUv2 21067 }

dpsRTUv2p20068Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 4 is set"
	::= { dpsRTUv2 20068 }

dpsRTUv2p21068Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 4 is cleared"
	::= { dpsRTUv2 21068 }

dpsRTUv2p20069Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 5 is set"
	::= { dpsRTUv2 20069 }

dpsRTUv2p21069Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 5 is cleared"
	::= { dpsRTUv2 21069 }

dpsRTUv2p20070Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 6 is set"
	::= { dpsRTUv2 20070 }

dpsRTUv2p21070Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 6 is cleared"
	::= { dpsRTUv2 21070 }

dpsRTUv2p20071Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 7 is set"
	::= { dpsRTUv2 20071 }

dpsRTUv2p21071Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 7 is cleared"
	::= { dpsRTUv2 21071 }

dpsRTUv2p20072Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 8 is set"
	::= { dpsRTUv2 20072 }

dpsRTUv2p21072Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 8 is cleared"
	::= { dpsRTUv2 21072 }

dpsRTUv2p20073Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 9 is set"
	::= { dpsRTUv2 20073 }

dpsRTUv2p21073Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 9 is cleared"
	::= { dpsRTUv2 21073 }

dpsRTUv2p20074Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 10 is set"
	::= { dpsRTUv2 20074 }

dpsRTUv2p21074Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 10 is cleared"
	::= { dpsRTUv2 21074 }

dpsRTUv2p20075Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 11 is set"
	::= { dpsRTUv2 20075 }

dpsRTUv2p21075Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 11 is cleared"
	::= { dpsRTUv2 21075 }

dpsRTUv2p20076Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 12 is set"
	::= { dpsRTUv2 20076 }

dpsRTUv2p21076Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 12 is cleared"
	::= { dpsRTUv2 21076 }

dpsRTUv2p20077Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 13 is set"
	::= { dpsRTUv2 20077 }

dpsRTUv2p21077Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 13 is cleared"
	::= { dpsRTUv2 21077 }

dpsRTUv2p20078Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 14 is set"
	::= { dpsRTUv2 20078 }

dpsRTUv2p21078Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 14 is cleared"
	::= { dpsRTUv2 21078 }

dpsRTUv2p20079Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 15 is set"
	::= { dpsRTUv2 20079 }

dpsRTUv2p21079Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 15 is cleared"
	::= { dpsRTUv2 21079 }

dpsRTUv2p20080Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 16 is set"
	::= { dpsRTUv2 20080 }

dpsRTUv2p21080Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 16 is cleared"
	::= { dpsRTUv2 21080 }

dpsRTUv2p20081Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 17 is set"
	::= { dpsRTUv2 20081 }

dpsRTUv2p21081Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 17 is cleared"
	::= { dpsRTUv2 21081 }

dpsRTUv2p20082Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 18 is set"
	::= { dpsRTUv2 20082 }

dpsRTUv2p21082Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 18 is cleared"
	::= { dpsRTUv2 21082 }

dpsRTUv2p20083Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 19 is set"
	::= { dpsRTUv2 20083 }

dpsRTUv2p21083Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 19 is cleared"
	::= { dpsRTUv2 21083 }

dpsRTUv2p20084Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 20 is set"
	::= { dpsRTUv2 20084 }

dpsRTUv2p21084Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 20 is cleared"
	::= { dpsRTUv2 21084 }

dpsRTUv2p20085Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 21 is set"
	::= { dpsRTUv2 20085 }

dpsRTUv2p21085Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 21 is cleared"
	::= { dpsRTUv2 21085 }

dpsRTUv2p20086Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 22 is set"
	::= { dpsRTUv2 20086 }

dpsRTUv2p21086Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 22 is cleared"
	::= { dpsRTUv2 21086 }

dpsRTUv2p20087Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 23 is set"
	::= { dpsRTUv2 20087 }

dpsRTUv2p21087Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 23 is cleared"
	::= { dpsRTUv2 21087 }

dpsRTUv2p20088Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 24 is set"
	::= { dpsRTUv2 20088 }

dpsRTUv2p21088Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 24 is cleared"
	::= { dpsRTUv2 21088 }

dpsRTUv2p20089Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 25 is set"
	::= { dpsRTUv2 20089 }

dpsRTUv2p21089Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 25 is cleared"
	::= { dpsRTUv2 21089 }

dpsRTUv2p20090Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 26 is set"
	::= { dpsRTUv2 20090 }

dpsRTUv2p21090Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 26 is cleared"
	::= { dpsRTUv2 21090 }

dpsRTUv2p20091Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 27 is set"
	::= { dpsRTUv2 20091 }

dpsRTUv2p21091Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 27 is cleared"
	::= { dpsRTUv2 21091 }

dpsRTUv2p20092Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 28 is set"
	::= { dpsRTUv2 20092 }

dpsRTUv2p21092Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 28 is cleared"
	::= { dpsRTUv2 21092 }

dpsRTUv2p20093Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 29 is set"
	::= { dpsRTUv2 20093 }

dpsRTUv2p21093Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 29 is cleared"
	::= { dpsRTUv2 21093 }

dpsRTUv2p20094Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 30 is set"
	::= { dpsRTUv2 20094 }

dpsRTUv2p21094Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 30 is cleared"
	::= { dpsRTUv2 21094 }

dpsRTUv2p20095Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 31 is set"
	::= { dpsRTUv2 20095 }

dpsRTUv2p21095Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 31 is cleared"
	::= { dpsRTUv2 21095 }

dpsRTUv2p20096Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 32 is set"
	::= { dpsRTUv2 20096 }

dpsRTUv2p21096Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 32 is cleared"
	::= { dpsRTUv2 21096 }

dpsRTUv2p20097Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 33 is set"
	::= { dpsRTUv2 20097 }

dpsRTUv2p21097Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 33 is cleared"
	::= { dpsRTUv2 21097 }

dpsRTUv2p20098Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 34 is set"
	::= { dpsRTUv2 20098 }

dpsRTUv2p21098Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 34 is cleared"
	::= { dpsRTUv2 21098 }

dpsRTUv2p20099Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 35 is set"
	::= { dpsRTUv2 20099 }

dpsRTUv2p21099Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 35 is cleared"
	::= { dpsRTUv2 21099 }

dpsRTUv2p20100Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 36 is set"
	::= { dpsRTUv2 20100 }

dpsRTUv2p21100Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 36 is cleared"
	::= { dpsRTUv2 21100 }

dpsRTUv2p20101Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 37 is set"
	::= { dpsRTUv2 20101 }

dpsRTUv2p21101Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 37 is cleared"
	::= { dpsRTUv2 21101 }

dpsRTUv2p20102Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 38 is set"
	::= { dpsRTUv2 20102 }

dpsRTUv2p21102Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 38 is cleared"
	::= { dpsRTUv2 21102 }

dpsRTUv2p20103Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 39 is set"
	::= { dpsRTUv2 20103 }

dpsRTUv2p21103Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 39 is cleared"
	::= { dpsRTUv2 21103 }

dpsRTUv2p20104Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 40 is set"
	::= { dpsRTUv2 20104 }

dpsRTUv2p21104Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 40 is cleared"
	::= { dpsRTUv2 21104 }

dpsRTUv2p20105Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 41 is set"
	::= { dpsRTUv2 20105 }

dpsRTUv2p21105Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 41 is cleared"
	::= { dpsRTUv2 21105 }

dpsRTUv2p20106Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 42 is set"
	::= { dpsRTUv2 20106 }

dpsRTUv2p21106Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 42 is cleared"
	::= { dpsRTUv2 21106 }

dpsRTUv2p20107Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 43 is set"
	::= { dpsRTUv2 20107 }

dpsRTUv2p21107Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 43 is cleared"
	::= { dpsRTUv2 21107 }

dpsRTUv2p20108Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 44 is set"
	::= { dpsRTUv2 20108 }

dpsRTUv2p21108Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 44 is cleared"
	::= { dpsRTUv2 21108 }

dpsRTUv2p20109Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 45 is set"
	::= { dpsRTUv2 20109 }

dpsRTUv2p21109Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 45 is cleared"
	::= { dpsRTUv2 21109 }

dpsRTUv2p20110Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 46 is set"
	::= { dpsRTUv2 20110 }

dpsRTUv2p21110Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 46 is cleared"
	::= { dpsRTUv2 21110 }

dpsRTUv2p20111Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 47 is set"
	::= { dpsRTUv2 20111 }

dpsRTUv2p21111Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 47 is cleared"
	::= { dpsRTUv2 21111 }

dpsRTUv2p20112Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 48 is set"
	::= { dpsRTUv2 20112 }

dpsRTUv2p21112Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 48 is cleared"
	::= { dpsRTUv2 21112 }

dpsRTUv2p20113Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 49 is set"
	::= { dpsRTUv2 20113 }

dpsRTUv2p21113Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 49 is cleared"
	::= { dpsRTUv2 21113 }

dpsRTUv2p20114Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 50 is set"
	::= { dpsRTUv2 20114 }

dpsRTUv2p21114Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 50 is cleared"
	::= { dpsRTUv2 21114 }

dpsRTUv2p20115Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 51 is set"
	::= { dpsRTUv2 20115 }

dpsRTUv2p21115Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 51 is cleared"
	::= { dpsRTUv2 21115 }

dpsRTUv2p20116Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 52 is set"
	::= { dpsRTUv2 20116 }

dpsRTUv2p21116Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 52 is cleared"
	::= { dpsRTUv2 21116 }

dpsRTUv2p20117Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 53 is set"
	::= { dpsRTUv2 20117 }

dpsRTUv2p21117Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 53 is cleared"
	::= { dpsRTUv2 21117 }

dpsRTUv2p20118Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 54 is set"
	::= { dpsRTUv2 20118 }

dpsRTUv2p21118Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 54 is cleared"
	::= { dpsRTUv2 21118 }

dpsRTUv2p20119Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 55 is set"
	::= { dpsRTUv2 20119 }

dpsRTUv2p21119Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 55 is cleared"
	::= { dpsRTUv2 21119 }

dpsRTUv2p20120Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 56 is set"
	::= { dpsRTUv2 20120 }

dpsRTUv2p21120Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 56 is cleared"
	::= { dpsRTUv2 21120 }

dpsRTUv2p20121Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 57 is set"
	::= { dpsRTUv2 20121 }

dpsRTUv2p21121Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 57 is cleared"
	::= { dpsRTUv2 21121 }

dpsRTUv2p20122Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 58 is set"
	::= { dpsRTUv2 20122 }

dpsRTUv2p21122Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 58 is cleared"
	::= { dpsRTUv2 21122 }

dpsRTUv2p20123Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 59 is set"
	::= { dpsRTUv2 20123 }

dpsRTUv2p21123Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 59 is cleared"
	::= { dpsRTUv2 21123 }

dpsRTUv2p20124Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 60 is set"
	::= { dpsRTUv2 20124 }

dpsRTUv2p21124Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 60 is cleared"
	::= { dpsRTUv2 21124 }

dpsRTUv2p20125Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 61 is set"
	::= { dpsRTUv2 20125 }

dpsRTUv2p21125Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 61 is cleared"
	::= { dpsRTUv2 21125 }

dpsRTUv2p20126Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 62 is set"
	::= { dpsRTUv2 20126 }

dpsRTUv2p21126Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 62 is cleared"
	::= { dpsRTUv2 21126 }

dpsRTUv2p20127Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 63 is set"
	::= { dpsRTUv2 20127 }

dpsRTUv2p21127Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 63 is cleared"
	::= { dpsRTUv2 21127 }

dpsRTUv2p20128Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 64 is set"
	::= { dpsRTUv2 20128 }

dpsRTUv2p21128Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 2 point 64 is cleared"
	::= { dpsRTUv2 21128 }

dpsRTUv2p20129Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 1 is set"
	::= { dpsRTUv2 20129 }

dpsRTUv2p21129Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 1 is cleared"
	::= { dpsRTUv2 21129 }

dpsRTUv2p20130Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 2 is set"
	::= { dpsRTUv2 20130 }

dpsRTUv2p21130Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 2 is cleared"
	::= { dpsRTUv2 21130 }

dpsRTUv2p20131Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 3 is set"
	::= { dpsRTUv2 20131 }

dpsRTUv2p21131Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 3 is cleared"
	::= { dpsRTUv2 21131 }

dpsRTUv2p20132Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 4 is set"
	::= { dpsRTUv2 20132 }

dpsRTUv2p21132Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 4 is cleared"
	::= { dpsRTUv2 21132 }

dpsRTUv2p20133Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 5 is set"
	::= { dpsRTUv2 20133 }

dpsRTUv2p21133Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 5 is cleared"
	::= { dpsRTUv2 21133 }

dpsRTUv2p20134Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 6 is set"
	::= { dpsRTUv2 20134 }

dpsRTUv2p21134Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 6 is cleared"
	::= { dpsRTUv2 21134 }

dpsRTUv2p20135Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 7 is set"
	::= { dpsRTUv2 20135 }

dpsRTUv2p21135Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 7 is cleared"
	::= { dpsRTUv2 21135 }

dpsRTUv2p20136Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 8 is set"
	::= { dpsRTUv2 20136 }

dpsRTUv2p21136Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 8 is cleared"
	::= { dpsRTUv2 21136 }

dpsRTUv2p20137Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 9 is set"
	::= { dpsRTUv2 20137 }

dpsRTUv2p21137Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 9 is cleared"
	::= { dpsRTUv2 21137 }

dpsRTUv2p20138Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 10 is set"
	::= { dpsRTUv2 20138 }

dpsRTUv2p21138Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 10 is cleared"
	::= { dpsRTUv2 21138 }

dpsRTUv2p20139Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 11 is set"
	::= { dpsRTUv2 20139 }

dpsRTUv2p21139Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 11 is cleared"
	::= { dpsRTUv2 21139 }

dpsRTUv2p20140Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 12 is set"
	::= { dpsRTUv2 20140 }

dpsRTUv2p21140Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 12 is cleared"
	::= { dpsRTUv2 21140 }

dpsRTUv2p20141Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 13 is set"
	::= { dpsRTUv2 20141 }

dpsRTUv2p21141Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 13 is cleared"
	::= { dpsRTUv2 21141 }

dpsRTUv2p20142Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 14 is set"
	::= { dpsRTUv2 20142 }

dpsRTUv2p21142Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 14 is cleared"
	::= { dpsRTUv2 21142 }

dpsRTUv2p20143Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 15 is set"
	::= { dpsRTUv2 20143 }

dpsRTUv2p21143Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 15 is cleared"
	::= { dpsRTUv2 21143 }

dpsRTUv2p20144Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 16 is set"
	::= { dpsRTUv2 20144 }

dpsRTUv2p21144Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 16 is cleared"
	::= { dpsRTUv2 21144 }

dpsRTUv2p20145Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 17 is set"
	::= { dpsRTUv2 20145 }

dpsRTUv2p21145Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 17 is cleared"
	::= { dpsRTUv2 21145 }

dpsRTUv2p20146Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 18 is set"
	::= { dpsRTUv2 20146 }

dpsRTUv2p21146Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 18 is cleared"
	::= { dpsRTUv2 21146 }

dpsRTUv2p20147Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 19 is set"
	::= { dpsRTUv2 20147 }

dpsRTUv2p21147Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 19 is cleared"
	::= { dpsRTUv2 21147 }

dpsRTUv2p20148Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 20 is set"
	::= { dpsRTUv2 20148 }

dpsRTUv2p21148Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 20 is cleared"
	::= { dpsRTUv2 21148 }

dpsRTUv2p20149Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 21 is set"
	::= { dpsRTUv2 20149 }

dpsRTUv2p21149Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 21 is cleared"
	::= { dpsRTUv2 21149 }

dpsRTUv2p20150Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 22 is set"
	::= { dpsRTUv2 20150 }

dpsRTUv2p21150Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 22 is cleared"
	::= { dpsRTUv2 21150 }

dpsRTUv2p20151Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 23 is set"
	::= { dpsRTUv2 20151 }

dpsRTUv2p21151Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 23 is cleared"
	::= { dpsRTUv2 21151 }

dpsRTUv2p20152Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 24 is set"
	::= { dpsRTUv2 20152 }

dpsRTUv2p21152Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 24 is cleared"
	::= { dpsRTUv2 21152 }

dpsRTUv2p20153Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 25 is set"
	::= { dpsRTUv2 20153 }

dpsRTUv2p21153Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 25 is cleared"
	::= { dpsRTUv2 21153 }

dpsRTUv2p20154Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 26 is set"
	::= { dpsRTUv2 20154 }

dpsRTUv2p21154Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 26 is cleared"
	::= { dpsRTUv2 21154 }

dpsRTUv2p20155Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 27 is set"
	::= { dpsRTUv2 20155 }

dpsRTUv2p21155Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 27 is cleared"
	::= { dpsRTUv2 21155 }

dpsRTUv2p20156Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 28 is set"
	::= { dpsRTUv2 20156 }

dpsRTUv2p21156Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 28 is cleared"
	::= { dpsRTUv2 21156 }

dpsRTUv2p20157Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 29 is set"
	::= { dpsRTUv2 20157 }

dpsRTUv2p21157Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 29 is cleared"
	::= { dpsRTUv2 21157 }

dpsRTUv2p20158Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 30 is set"
	::= { dpsRTUv2 20158 }

dpsRTUv2p21158Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 30 is cleared"
	::= { dpsRTUv2 21158 }

dpsRTUv2p20159Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 31 is set"
	::= { dpsRTUv2 20159 }

dpsRTUv2p21159Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 31 is cleared"
	::= { dpsRTUv2 21159 }

dpsRTUv2p20160Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 32 is set"
	::= { dpsRTUv2 20160 }

dpsRTUv2p21160Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 32 is cleared"
	::= { dpsRTUv2 21160 }

dpsRTUv2p20161Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 33 is set"
	::= { dpsRTUv2 20161 }

dpsRTUv2p21161Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 33 is cleared"
	::= { dpsRTUv2 21161 }

dpsRTUv2p20162Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 34 is set"
	::= { dpsRTUv2 20162 }

dpsRTUv2p21162Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 34 is cleared"
	::= { dpsRTUv2 21162 }

dpsRTUv2p20163Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 35 is set"
	::= { dpsRTUv2 20163 }

dpsRTUv2p21163Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 35 is cleared"
	::= { dpsRTUv2 21163 }

dpsRTUv2p20164Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 36 is set"
	::= { dpsRTUv2 20164 }

dpsRTUv2p21164Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 36 is cleared"
	::= { dpsRTUv2 21164 }

dpsRTUv2p20165Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 37 is set"
	::= { dpsRTUv2 20165 }

dpsRTUv2p21165Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 37 is cleared"
	::= { dpsRTUv2 21165 }

dpsRTUv2p20166Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 38 is set"
	::= { dpsRTUv2 20166 }

dpsRTUv2p21166Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 38 is cleared"
	::= { dpsRTUv2 21166 }

dpsRTUv2p20167Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 39 is set"
	::= { dpsRTUv2 20167 }

dpsRTUv2p21167Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 39 is cleared"
	::= { dpsRTUv2 21167 }

dpsRTUv2p20168Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 40 is set"
	::= { dpsRTUv2 20168 }

dpsRTUv2p21168Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 40 is cleared"
	::= { dpsRTUv2 21168 }

dpsRTUv2p20169Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 41 is set"
	::= { dpsRTUv2 20169 }

dpsRTUv2p21169Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 41 is cleared"
	::= { dpsRTUv2 21169 }

dpsRTUv2p20170Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 42 is set"
	::= { dpsRTUv2 20170 }

dpsRTUv2p21170Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 42 is cleared"
	::= { dpsRTUv2 21170 }

dpsRTUv2p20171Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 43 is set"
	::= { dpsRTUv2 20171 }

dpsRTUv2p21171Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 43 is cleared"
	::= { dpsRTUv2 21171 }

dpsRTUv2p20172Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 44 is set"
	::= { dpsRTUv2 20172 }

dpsRTUv2p21172Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 44 is cleared"
	::= { dpsRTUv2 21172 }

dpsRTUv2p20173Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 45 is set"
	::= { dpsRTUv2 20173 }

dpsRTUv2p21173Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 45 is cleared"
	::= { dpsRTUv2 21173 }

dpsRTUv2p20174Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 46 is set"
	::= { dpsRTUv2 20174 }

dpsRTUv2p21174Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 46 is cleared"
	::= { dpsRTUv2 21174 }

dpsRTUv2p20175Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 47 is set"
	::= { dpsRTUv2 20175 }

dpsRTUv2p21175Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 47 is cleared"
	::= { dpsRTUv2 21175 }

dpsRTUv2p20176Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 48 is set"
	::= { dpsRTUv2 20176 }

dpsRTUv2p21176Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 48 is cleared"
	::= { dpsRTUv2 21176 }

dpsRTUv2p20177Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 49 is set"
	::= { dpsRTUv2 20177 }

dpsRTUv2p21177Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 49 is cleared"
	::= { dpsRTUv2 21177 }

dpsRTUv2p20178Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 50 is set"
	::= { dpsRTUv2 20178 }

dpsRTUv2p21178Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 50 is cleared"
	::= { dpsRTUv2 21178 }

dpsRTUv2p20179Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 51 is set"
	::= { dpsRTUv2 20179 }

dpsRTUv2p21179Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 51 is cleared"
	::= { dpsRTUv2 21179 }

dpsRTUv2p20180Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 52 is set"
	::= { dpsRTUv2 20180 }

dpsRTUv2p21180Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 52 is cleared"
	::= { dpsRTUv2 21180 }

dpsRTUv2p20181Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 53 is set"
	::= { dpsRTUv2 20181 }

dpsRTUv2p21181Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 53 is cleared"
	::= { dpsRTUv2 21181 }

dpsRTUv2p20182Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 54 is set"
	::= { dpsRTUv2 20182 }

dpsRTUv2p21182Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 54 is cleared"
	::= { dpsRTUv2 21182 }

dpsRTUv2p20183Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 55 is set"
	::= { dpsRTUv2 20183 }

dpsRTUv2p21183Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 55 is cleared"
	::= { dpsRTUv2 21183 }

dpsRTUv2p20184Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 56 is set"
	::= { dpsRTUv2 20184 }

dpsRTUv2p21184Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 56 is cleared"
	::= { dpsRTUv2 21184 }

dpsRTUv2p20185Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 57 is set"
	::= { dpsRTUv2 20185 }

dpsRTUv2p21185Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 57 is cleared"
	::= { dpsRTUv2 21185 }

dpsRTUv2p20186Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 58 is set"
	::= { dpsRTUv2 20186 }

dpsRTUv2p21186Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 58 is cleared"
	::= { dpsRTUv2 21186 }

dpsRTUv2p20187Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 59 is set"
	::= { dpsRTUv2 20187 }

dpsRTUv2p21187Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 59 is cleared"
	::= { dpsRTUv2 21187 }

dpsRTUv2p20188Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 60 is set"
	::= { dpsRTUv2 20188 }

dpsRTUv2p21188Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 60 is cleared"
	::= { dpsRTUv2 21188 }

dpsRTUv2p20189Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 61 is set"
	::= { dpsRTUv2 20189 }

dpsRTUv2p21189Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 61 is cleared"
	::= { dpsRTUv2 21189 }

dpsRTUv2p20190Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 62 is set"
	::= { dpsRTUv2 20190 }

dpsRTUv2p21190Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 62 is cleared"
	::= { dpsRTUv2 21190 }

dpsRTUv2p20191Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 63 is set"
	::= { dpsRTUv2 20191 }

dpsRTUv2p21191Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 63 is cleared"
	::= { dpsRTUv2 21191 }

dpsRTUv2p20192Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 64 is set"
	::= { dpsRTUv2 20192 }

dpsRTUv2p21192Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 3 point 64 is cleared"
	::= { dpsRTUv2 21192 }

dpsRTUv2p20193Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 1 is set"
	::= { dpsRTUv2 20193 }

dpsRTUv2p21193Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 1 is cleared"
	::= { dpsRTUv2 21193 }

dpsRTUv2p20194Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 2 is set"
	::= { dpsRTUv2 20194 }

dpsRTUv2p21194Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 2 is cleared"
	::= { dpsRTUv2 21194 }

dpsRTUv2p20195Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 3 is set"
	::= { dpsRTUv2 20195 }

dpsRTUv2p21195Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 3 is cleared"
	::= { dpsRTUv2 21195 }

dpsRTUv2p20196Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 4 is set"
	::= { dpsRTUv2 20196 }

dpsRTUv2p21196Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 4 is cleared"
	::= { dpsRTUv2 21196 }

dpsRTUv2p20197Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 5 is set"
	::= { dpsRTUv2 20197 }

dpsRTUv2p21197Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 5 is cleared"
	::= { dpsRTUv2 21197 }

dpsRTUv2p20198Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 6 is set"
	::= { dpsRTUv2 20198 }

dpsRTUv2p21198Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 6 is cleared"
	::= { dpsRTUv2 21198 }

dpsRTUv2p20199Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 7 is set"
	::= { dpsRTUv2 20199 }

dpsRTUv2p21199Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 7 is cleared"
	::= { dpsRTUv2 21199 }

dpsRTUv2p20200Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 8 is set"
	::= { dpsRTUv2 20200 }

dpsRTUv2p21200Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 8 is cleared"
	::= { dpsRTUv2 21200 }

dpsRTUv2p20201Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 9 is set"
	::= { dpsRTUv2 20201 }

dpsRTUv2p21201Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 9 is cleared"
	::= { dpsRTUv2 21201 }

dpsRTUv2p20202Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 10 is set"
	::= { dpsRTUv2 20202 }

dpsRTUv2p21202Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 10 is cleared"
	::= { dpsRTUv2 21202 }

dpsRTUv2p20203Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 11 is set"
	::= { dpsRTUv2 20203 }

dpsRTUv2p21203Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 11 is cleared"
	::= { dpsRTUv2 21203 }

dpsRTUv2p20204Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 12 is set"
	::= { dpsRTUv2 20204 }

dpsRTUv2p21204Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 12 is cleared"
	::= { dpsRTUv2 21204 }

dpsRTUv2p20205Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 13 is set"
	::= { dpsRTUv2 20205 }

dpsRTUv2p21205Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 13 is cleared"
	::= { dpsRTUv2 21205 }

dpsRTUv2p20206Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 14 is set"
	::= { dpsRTUv2 20206 }

dpsRTUv2p21206Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 14 is cleared"
	::= { dpsRTUv2 21206 }

dpsRTUv2p20207Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 15 is set"
	::= { dpsRTUv2 20207 }

dpsRTUv2p21207Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 15 is cleared"
	::= { dpsRTUv2 21207 }

dpsRTUv2p20208Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 16 is set"
	::= { dpsRTUv2 20208 }

dpsRTUv2p21208Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 16 is cleared"
	::= { dpsRTUv2 21208 }

dpsRTUv2p20209Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 17 is set"
	::= { dpsRTUv2 20209 }

dpsRTUv2p21209Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 17 is cleared"
	::= { dpsRTUv2 21209 }

dpsRTUv2p20210Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 18 is set"
	::= { dpsRTUv2 20210 }

dpsRTUv2p21210Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 18 is cleared"
	::= { dpsRTUv2 21210 }

dpsRTUv2p20211Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 19 is set"
	::= { dpsRTUv2 20211 }

dpsRTUv2p21211Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 19 is cleared"
	::= { dpsRTUv2 21211 }

dpsRTUv2p20212Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 20 is set"
	::= { dpsRTUv2 20212 }

dpsRTUv2p21212Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 20 is cleared"
	::= { dpsRTUv2 21212 }

dpsRTUv2p20213Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 21 is set"
	::= { dpsRTUv2 20213 }

dpsRTUv2p21213Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 21 is cleared"
	::= { dpsRTUv2 21213 }

dpsRTUv2p20214Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 22 is set"
	::= { dpsRTUv2 20214 }

dpsRTUv2p21214Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 22 is cleared"
	::= { dpsRTUv2 21214 }

dpsRTUv2p20215Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 23 is set"
	::= { dpsRTUv2 20215 }

dpsRTUv2p21215Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 23 is cleared"
	::= { dpsRTUv2 21215 }

dpsRTUv2p20216Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 24 is set"
	::= { dpsRTUv2 20216 }

dpsRTUv2p21216Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 24 is cleared"
	::= { dpsRTUv2 21216 }

dpsRTUv2p20217Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 25 is set"
	::= { dpsRTUv2 20217 }

dpsRTUv2p21217Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 25 is cleared"
	::= { dpsRTUv2 21217 }

dpsRTUv2p20218Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 26 is set"
	::= { dpsRTUv2 20218 }

dpsRTUv2p21218Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 26 is cleared"
	::= { dpsRTUv2 21218 }

dpsRTUv2p20219Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 27 is set"
	::= { dpsRTUv2 20219 }

dpsRTUv2p21219Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 27 is cleared"
	::= { dpsRTUv2 21219 }

dpsRTUv2p20220Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 28 is set"
	::= { dpsRTUv2 20220 }

dpsRTUv2p21220Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 28 is cleared"
	::= { dpsRTUv2 21220 }

dpsRTUv2p20221Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 29 is set"
	::= { dpsRTUv2 20221 }

dpsRTUv2p21221Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 29 is cleared"
	::= { dpsRTUv2 21221 }

dpsRTUv2p20222Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 30 is set"
	::= { dpsRTUv2 20222 }

dpsRTUv2p21222Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 30 is cleared"
	::= { dpsRTUv2 21222 }

dpsRTUv2p20223Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 31 is set"
	::= { dpsRTUv2 20223 }

dpsRTUv2p21223Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 31 is cleared"
	::= { dpsRTUv2 21223 }

dpsRTUv2p20224Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 32 is set"
	::= { dpsRTUv2 20224 }

dpsRTUv2p21224Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 32 is cleared"
	::= { dpsRTUv2 21224 }

dpsRTUv2p20225Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 33 is set"
	::= { dpsRTUv2 20225 }

dpsRTUv2p21225Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 33 is cleared"
	::= { dpsRTUv2 21225 }

dpsRTUv2p20226Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 34 is set"
	::= { dpsRTUv2 20226 }

dpsRTUv2p21226Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 34 is cleared"
	::= { dpsRTUv2 21226 }

dpsRTUv2p20227Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 35 is set"
	::= { dpsRTUv2 20227 }

dpsRTUv2p21227Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 35 is cleared"
	::= { dpsRTUv2 21227 }

dpsRTUv2p20228Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 36 is set"
	::= { dpsRTUv2 20228 }

dpsRTUv2p21228Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 36 is cleared"
	::= { dpsRTUv2 21228 }

dpsRTUv2p20229Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 37 is set"
	::= { dpsRTUv2 20229 }

dpsRTUv2p21229Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 37 is cleared"
	::= { dpsRTUv2 21229 }

dpsRTUv2p20230Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 38 is set"
	::= { dpsRTUv2 20230 }

dpsRTUv2p21230Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 38 is cleared"
	::= { dpsRTUv2 21230 }

dpsRTUv2p20231Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 39 is set"
	::= { dpsRTUv2 20231 }

dpsRTUv2p21231Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 39 is cleared"
	::= { dpsRTUv2 21231 }

dpsRTUv2p20232Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 40 is set"
	::= { dpsRTUv2 20232 }

dpsRTUv2p21232Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 40 is cleared"
	::= { dpsRTUv2 21232 }

dpsRTUv2p20233Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 41 is set"
	::= { dpsRTUv2 20233 }

dpsRTUv2p21233Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 41 is cleared"
	::= { dpsRTUv2 21233 }

dpsRTUv2p20234Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 42 is set"
	::= { dpsRTUv2 20234 }

dpsRTUv2p21234Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 42 is cleared"
	::= { dpsRTUv2 21234 }

dpsRTUv2p20235Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 43 is set"
	::= { dpsRTUv2 20235 }

dpsRTUv2p21235Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 43 is cleared"
	::= { dpsRTUv2 21235 }

dpsRTUv2p20236Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 44 is set"
	::= { dpsRTUv2 20236 }

dpsRTUv2p21236Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 44 is cleared"
	::= { dpsRTUv2 21236 }

dpsRTUv2p20237Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 45 is set"
	::= { dpsRTUv2 20237 }

dpsRTUv2p21237Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 45 is cleared"
	::= { dpsRTUv2 21237 }

dpsRTUv2p20238Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 46 is set"
	::= { dpsRTUv2 20238 }

dpsRTUv2p21238Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 46 is cleared"
	::= { dpsRTUv2 21238 }

dpsRTUv2p20239Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 47 is set"
	::= { dpsRTUv2 20239 }

dpsRTUv2p21239Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 47 is cleared"
	::= { dpsRTUv2 21239 }

dpsRTUv2p20240Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 48 is set"
	::= { dpsRTUv2 20240 }

dpsRTUv2p21240Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 48 is cleared"
	::= { dpsRTUv2 21240 }

dpsRTUv2p20241Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 49 is set"
	::= { dpsRTUv2 20241 }

dpsRTUv2p21241Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 49 is cleared"
	::= { dpsRTUv2 21241 }

dpsRTUv2p20242Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 50 is set"
	::= { dpsRTUv2 20242 }

dpsRTUv2p21242Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 50 is cleared"
	::= { dpsRTUv2 21242 }

dpsRTUv2p20243Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 51 is set"
	::= { dpsRTUv2 20243 }

dpsRTUv2p21243Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 51 is cleared"
	::= { dpsRTUv2 21243 }

dpsRTUv2p20244Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 52 is set"
	::= { dpsRTUv2 20244 }

dpsRTUv2p21244Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 52 is cleared"
	::= { dpsRTUv2 21244 }

dpsRTUv2p20245Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 53 is set"
	::= { dpsRTUv2 20245 }

dpsRTUv2p21245Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 53 is cleared"
	::= { dpsRTUv2 21245 }

dpsRTUv2p20246Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 54 is set"
	::= { dpsRTUv2 20246 }

dpsRTUv2p21246Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 54 is cleared"
	::= { dpsRTUv2 21246 }

dpsRTUv2p20247Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 55 is set"
	::= { dpsRTUv2 20247 }

dpsRTUv2p21247Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 55 is cleared"
	::= { dpsRTUv2 21247 }

dpsRTUv2p20248Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 56 is set"
	::= { dpsRTUv2 20248 }

dpsRTUv2p21248Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 56 is cleared"
	::= { dpsRTUv2 21248 }

dpsRTUv2p20249Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 57 is set"
	::= { dpsRTUv2 20249 }

dpsRTUv2p21249Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 57 is cleared"
	::= { dpsRTUv2 21249 }

dpsRTUv2p20250Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 58 is set"
	::= { dpsRTUv2 20250 }

dpsRTUv2p21250Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 58 is cleared"
	::= { dpsRTUv2 21250 }

dpsRTUv2p20251Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 59 is set"
	::= { dpsRTUv2 20251 }

dpsRTUv2p21251Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 59 is cleared"
	::= { dpsRTUv2 21251 }

dpsRTUv2p20252Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 60 is set"
	::= { dpsRTUv2 20252 }

dpsRTUv2p21252Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 60 is cleared"
	::= { dpsRTUv2 21252 }

dpsRTUv2p20253Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 61 is set"
	::= { dpsRTUv2 20253 }

dpsRTUv2p21253Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 61 is cleared"
	::= { dpsRTUv2 21253 }

dpsRTUv2p20254Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 62 is set"
	::= { dpsRTUv2 20254 }

dpsRTUv2p21254Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 62 is cleared"
	::= { dpsRTUv2 21254 }

dpsRTUv2p20255Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 63 is set"
	::= { dpsRTUv2 20255 }

dpsRTUv2p21255Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 63 is cleared"
	::= { dpsRTUv2 21255 }

dpsRTUv2p20256Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 64 is set"
	::= { dpsRTUv2 20256 }

dpsRTUv2p21256Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 4 point 64 is cleared"
	::= { dpsRTUv2 21256 }

dpsRTUv2p20257Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 1 is set"
	::= { dpsRTUv2 20257 }

dpsRTUv2p21257Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 1 is cleared"
	::= { dpsRTUv2 21257 }

dpsRTUv2p20258Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 2 is set"
	::= { dpsRTUv2 20258 }

dpsRTUv2p21258Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 2 is cleared"
	::= { dpsRTUv2 21258 }

dpsRTUv2p20259Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 3 is set"
	::= { dpsRTUv2 20259 }

dpsRTUv2p21259Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 3 is cleared"
	::= { dpsRTUv2 21259 }

dpsRTUv2p20260Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 4 is set"
	::= { dpsRTUv2 20260 }

dpsRTUv2p21260Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 4 is cleared"
	::= { dpsRTUv2 21260 }

dpsRTUv2p20261Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 5 is set"
	::= { dpsRTUv2 20261 }

dpsRTUv2p21261Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 5 is cleared"
	::= { dpsRTUv2 21261 }

dpsRTUv2p20262Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 6 is set"
	::= { dpsRTUv2 20262 }

dpsRTUv2p21262Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 6 is cleared"
	::= { dpsRTUv2 21262 }

dpsRTUv2p20263Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 7 is set"
	::= { dpsRTUv2 20263 }

dpsRTUv2p21263Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 7 is cleared"
	::= { dpsRTUv2 21263 }

dpsRTUv2p20264Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 8 is set"
	::= { dpsRTUv2 20264 }

dpsRTUv2p21264Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 8 is cleared"
	::= { dpsRTUv2 21264 }

dpsRTUv2p20265Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 9 is set"
	::= { dpsRTUv2 20265 }

dpsRTUv2p21265Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 9 is cleared"
	::= { dpsRTUv2 21265 }

dpsRTUv2p20266Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 10 is set"
	::= { dpsRTUv2 20266 }

dpsRTUv2p21266Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 10 is cleared"
	::= { dpsRTUv2 21266 }

dpsRTUv2p20267Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 11 is set"
	::= { dpsRTUv2 20267 }

dpsRTUv2p21267Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 11 is cleared"
	::= { dpsRTUv2 21267 }

dpsRTUv2p20268Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 12 is set"
	::= { dpsRTUv2 20268 }

dpsRTUv2p21268Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 12 is cleared"
	::= { dpsRTUv2 21268 }

dpsRTUv2p20269Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 13 is set"
	::= { dpsRTUv2 20269 }

dpsRTUv2p21269Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 13 is cleared"
	::= { dpsRTUv2 21269 }

dpsRTUv2p20270Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 14 is set"
	::= { dpsRTUv2 20270 }

dpsRTUv2p21270Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 14 is cleared"
	::= { dpsRTUv2 21270 }

dpsRTUv2p20271Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 15 is set"
	::= { dpsRTUv2 20271 }

dpsRTUv2p21271Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 15 is cleared"
	::= { dpsRTUv2 21271 }

dpsRTUv2p20272Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 16 is set"
	::= { dpsRTUv2 20272 }

dpsRTUv2p21272Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 16 is cleared"
	::= { dpsRTUv2 21272 }

dpsRTUv2p20273Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 17 is set"
	::= { dpsRTUv2 20273 }

dpsRTUv2p21273Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 17 is cleared"
	::= { dpsRTUv2 21273 }

dpsRTUv2p20274Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 18 is set"
	::= { dpsRTUv2 20274 }

dpsRTUv2p21274Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 18 is cleared"
	::= { dpsRTUv2 21274 }

dpsRTUv2p20275Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 19 is set"
	::= { dpsRTUv2 20275 }

dpsRTUv2p21275Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 19 is cleared"
	::= { dpsRTUv2 21275 }

dpsRTUv2p20276Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 20 is set"
	::= { dpsRTUv2 20276 }

dpsRTUv2p21276Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 20 is cleared"
	::= { dpsRTUv2 21276 }

dpsRTUv2p20277Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 21 is set"
	::= { dpsRTUv2 20277 }

dpsRTUv2p21277Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 21 is cleared"
	::= { dpsRTUv2 21277 }

dpsRTUv2p20278Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 22 is set"
	::= { dpsRTUv2 20278 }

dpsRTUv2p21278Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 22 is cleared"
	::= { dpsRTUv2 21278 }

dpsRTUv2p20279Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 23 is set"
	::= { dpsRTUv2 20279 }

dpsRTUv2p21279Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 23 is cleared"
	::= { dpsRTUv2 21279 }

dpsRTUv2p20280Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 24 is set"
	::= { dpsRTUv2 20280 }

dpsRTUv2p21280Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 24 is cleared"
	::= { dpsRTUv2 21280 }

dpsRTUv2p20281Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 25 is set"
	::= { dpsRTUv2 20281 }

dpsRTUv2p21281Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 25 is cleared"
	::= { dpsRTUv2 21281 }

dpsRTUv2p20282Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 26 is set"
	::= { dpsRTUv2 20282 }

dpsRTUv2p21282Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 26 is cleared"
	::= { dpsRTUv2 21282 }

dpsRTUv2p20283Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 27 is set"
	::= { dpsRTUv2 20283 }

dpsRTUv2p21283Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 27 is cleared"
	::= { dpsRTUv2 21283 }

dpsRTUv2p20284Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 28 is set"
	::= { dpsRTUv2 20284 }

dpsRTUv2p21284Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 28 is cleared"
	::= { dpsRTUv2 21284 }

dpsRTUv2p20285Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 29 is set"
	::= { dpsRTUv2 20285 }

dpsRTUv2p21285Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 29 is cleared"
	::= { dpsRTUv2 21285 }

dpsRTUv2p20286Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 30 is set"
	::= { dpsRTUv2 20286 }

dpsRTUv2p21286Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 30 is cleared"
	::= { dpsRTUv2 21286 }

dpsRTUv2p20287Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 31 is set"
	::= { dpsRTUv2 20287 }

dpsRTUv2p21287Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 31 is cleared"
	::= { dpsRTUv2 21287 }

dpsRTUv2p20288Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 32 is set"
	::= { dpsRTUv2 20288 }

dpsRTUv2p21288Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 32 is cleared"
	::= { dpsRTUv2 21288 }

dpsRTUv2p20289Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 33 is set"
	::= { dpsRTUv2 20289 }

dpsRTUv2p21289Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 33 is cleared"
	::= { dpsRTUv2 21289 }

dpsRTUv2p20290Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 34 is set"
	::= { dpsRTUv2 20290 }

dpsRTUv2p21290Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 34 is cleared"
	::= { dpsRTUv2 21290 }

dpsRTUv2p20291Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 35 is set"
	::= { dpsRTUv2 20291 }

dpsRTUv2p21291Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 35 is cleared"
	::= { dpsRTUv2 21291 }

dpsRTUv2p20292Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 36 is set"
	::= { dpsRTUv2 20292 }

dpsRTUv2p21292Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 36 is cleared"
	::= { dpsRTUv2 21292 }

dpsRTUv2p20293Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 37 is set"
	::= { dpsRTUv2 20293 }

dpsRTUv2p21293Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 37 is cleared"
	::= { dpsRTUv2 21293 }

dpsRTUv2p20294Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 38 is set"
	::= { dpsRTUv2 20294 }

dpsRTUv2p21294Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 38 is cleared"
	::= { dpsRTUv2 21294 }

dpsRTUv2p20295Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 39 is set"
	::= { dpsRTUv2 20295 }

dpsRTUv2p21295Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 39 is cleared"
	::= { dpsRTUv2 21295 }

dpsRTUv2p20296Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 40 is set"
	::= { dpsRTUv2 20296 }

dpsRTUv2p21296Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 40 is cleared"
	::= { dpsRTUv2 21296 }

dpsRTUv2p20297Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 41 is set"
	::= { dpsRTUv2 20297 }

dpsRTUv2p21297Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 41 is cleared"
	::= { dpsRTUv2 21297 }

dpsRTUv2p20298Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 42 is set"
	::= { dpsRTUv2 20298 }

dpsRTUv2p21298Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 42 is cleared"
	::= { dpsRTUv2 21298 }

dpsRTUv2p20299Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 43 is set"
	::= { dpsRTUv2 20299 }

dpsRTUv2p21299Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 43 is cleared"
	::= { dpsRTUv2 21299 }

dpsRTUv2p20300Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 44 is set"
	::= { dpsRTUv2 20300 }

dpsRTUv2p21300Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 44 is cleared"
	::= { dpsRTUv2 21300 }

dpsRTUv2p20301Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 45 is set"
	::= { dpsRTUv2 20301 }

dpsRTUv2p21301Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 45 is cleared"
	::= { dpsRTUv2 21301 }

dpsRTUv2p20302Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 46 is set"
	::= { dpsRTUv2 20302 }

dpsRTUv2p21302Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 46 is cleared"
	::= { dpsRTUv2 21302 }

dpsRTUv2p20303Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 47 is set"
	::= { dpsRTUv2 20303 }

dpsRTUv2p21303Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 47 is cleared"
	::= { dpsRTUv2 21303 }

dpsRTUv2p20304Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 48 is set"
	::= { dpsRTUv2 20304 }

dpsRTUv2p21304Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 48 is cleared"
	::= { dpsRTUv2 21304 }

dpsRTUv2p20305Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 49 is set"
	::= { dpsRTUv2 20305 }

dpsRTUv2p21305Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 49 is cleared"
	::= { dpsRTUv2 21305 }

dpsRTUv2p20306Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 50 is set"
	::= { dpsRTUv2 20306 }

dpsRTUv2p21306Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 50 is cleared"
	::= { dpsRTUv2 21306 }

dpsRTUv2p20307Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 51 is set"
	::= { dpsRTUv2 20307 }

dpsRTUv2p21307Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 51 is cleared"
	::= { dpsRTUv2 21307 }

dpsRTUv2p20308Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 52 is set"
	::= { dpsRTUv2 20308 }

dpsRTUv2p21308Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 52 is cleared"
	::= { dpsRTUv2 21308 }

dpsRTUv2p20309Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 53 is set"
	::= { dpsRTUv2 20309 }

dpsRTUv2p21309Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 53 is cleared"
	::= { dpsRTUv2 21309 }

dpsRTUv2p20310Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 54 is set"
	::= { dpsRTUv2 20310 }

dpsRTUv2p21310Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 54 is cleared"
	::= { dpsRTUv2 21310 }

dpsRTUv2p20311Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 55 is set"
	::= { dpsRTUv2 20311 }

dpsRTUv2p21311Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 55 is cleared"
	::= { dpsRTUv2 21311 }

dpsRTUv2p20312Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 56 is set"
	::= { dpsRTUv2 20312 }

dpsRTUv2p21312Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 56 is cleared"
	::= { dpsRTUv2 21312 }

dpsRTUv2p20313Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 57 is set"
	::= { dpsRTUv2 20313 }

dpsRTUv2p21313Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 57 is cleared"
	::= { dpsRTUv2 21313 }

dpsRTUv2p20314Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 58 is set"
	::= { dpsRTUv2 20314 }

dpsRTUv2p21314Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 58 is cleared"
	::= { dpsRTUv2 21314 }

dpsRTUv2p20315Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 59 is set"
	::= { dpsRTUv2 20315 }

dpsRTUv2p21315Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 59 is cleared"
	::= { dpsRTUv2 21315 }

dpsRTUv2p20316Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 60 is set"
	::= { dpsRTUv2 20316 }

dpsRTUv2p21316Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 60 is cleared"
	::= { dpsRTUv2 21316 }

dpsRTUv2p20317Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 61 is set"
	::= { dpsRTUv2 20317 }

dpsRTUv2p21317Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 61 is cleared"
	::= { dpsRTUv2 21317 }

dpsRTUv2p20318Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 62 is set"
	::= { dpsRTUv2 20318 }

dpsRTUv2p21318Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 62 is cleared"
	::= { dpsRTUv2 21318 }

dpsRTUv2p20319Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 63 is set"
	::= { dpsRTUv2 20319 }

dpsRTUv2p21319Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 63 is cleared"
	::= { dpsRTUv2 21319 }

dpsRTUv2p20320Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 64 is set"
	::= { dpsRTUv2 20320 }

dpsRTUv2p21320Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 5 point 64 is cleared"
	::= { dpsRTUv2 21320 }

dpsRTUv2p20321Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 1 is set"
	::= { dpsRTUv2 20321 }

dpsRTUv2p21321Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 1 is cleared"
	::= { dpsRTUv2 21321 }

dpsRTUv2p20322Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 2 is set"
	::= { dpsRTUv2 20322 }

dpsRTUv2p21322Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 2 is cleared"
	::= { dpsRTUv2 21322 }

dpsRTUv2p20323Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 3 is set"
	::= { dpsRTUv2 20323 }

dpsRTUv2p21323Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 3 is cleared"
	::= { dpsRTUv2 21323 }

dpsRTUv2p20324Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 4 is set"
	::= { dpsRTUv2 20324 }

dpsRTUv2p21324Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 4 is cleared"
	::= { dpsRTUv2 21324 }

dpsRTUv2p20325Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 5 is set"
	::= { dpsRTUv2 20325 }

dpsRTUv2p21325Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 5 is cleared"
	::= { dpsRTUv2 21325 }

dpsRTUv2p20326Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 6 is set"
	::= { dpsRTUv2 20326 }

dpsRTUv2p21326Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 6 is cleared"
	::= { dpsRTUv2 21326 }

dpsRTUv2p20327Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 7 is set"
	::= { dpsRTUv2 20327 }

dpsRTUv2p21327Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 7 is cleared"
	::= { dpsRTUv2 21327 }

dpsRTUv2p20328Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 8 is set"
	::= { dpsRTUv2 20328 }

dpsRTUv2p21328Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 8 is cleared"
	::= { dpsRTUv2 21328 }

dpsRTUv2p20329Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 9 is set"
	::= { dpsRTUv2 20329 }

dpsRTUv2p21329Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 9 is cleared"
	::= { dpsRTUv2 21329 }

dpsRTUv2p20330Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 10 is set"
	::= { dpsRTUv2 20330 }

dpsRTUv2p21330Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 10 is cleared"
	::= { dpsRTUv2 21330 }

dpsRTUv2p20331Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 11 is set"
	::= { dpsRTUv2 20331 }

dpsRTUv2p21331Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 11 is cleared"
	::= { dpsRTUv2 21331 }

dpsRTUv2p20332Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 12 is set"
	::= { dpsRTUv2 20332 }

dpsRTUv2p21332Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 12 is cleared"
	::= { dpsRTUv2 21332 }

dpsRTUv2p20333Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 13 is set"
	::= { dpsRTUv2 20333 }

dpsRTUv2p21333Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 13 is cleared"
	::= { dpsRTUv2 21333 }

dpsRTUv2p20334Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 14 is set"
	::= { dpsRTUv2 20334 }

dpsRTUv2p21334Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 14 is cleared"
	::= { dpsRTUv2 21334 }

dpsRTUv2p20335Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 15 is set"
	::= { dpsRTUv2 20335 }

dpsRTUv2p21335Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 15 is cleared"
	::= { dpsRTUv2 21335 }

dpsRTUv2p20336Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 16 is set"
	::= { dpsRTUv2 20336 }

dpsRTUv2p21336Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 16 is cleared"
	::= { dpsRTUv2 21336 }

dpsRTUv2p20337Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 17 is set"
	::= { dpsRTUv2 20337 }

dpsRTUv2p21337Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 17 is cleared"
	::= { dpsRTUv2 21337 }

dpsRTUv2p20338Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 18 is set"
	::= { dpsRTUv2 20338 }

dpsRTUv2p21338Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 18 is cleared"
	::= { dpsRTUv2 21338 }

dpsRTUv2p20339Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 19 is set"
	::= { dpsRTUv2 20339 }

dpsRTUv2p21339Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 19 is cleared"
	::= { dpsRTUv2 21339 }

dpsRTUv2p20340Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 20 is set"
	::= { dpsRTUv2 20340 }

dpsRTUv2p21340Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 20 is cleared"
	::= { dpsRTUv2 21340 }

dpsRTUv2p20341Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 21 is set"
	::= { dpsRTUv2 20341 }

dpsRTUv2p21341Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 21 is cleared"
	::= { dpsRTUv2 21341 }

dpsRTUv2p20342Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 22 is set"
	::= { dpsRTUv2 20342 }

dpsRTUv2p21342Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 22 is cleared"
	::= { dpsRTUv2 21342 }

dpsRTUv2p20343Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 23 is set"
	::= { dpsRTUv2 20343 }

dpsRTUv2p21343Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 23 is cleared"
	::= { dpsRTUv2 21343 }

dpsRTUv2p20344Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 24 is set"
	::= { dpsRTUv2 20344 }

dpsRTUv2p21344Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 24 is cleared"
	::= { dpsRTUv2 21344 }

dpsRTUv2p20345Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 25 is set"
	::= { dpsRTUv2 20345 }

dpsRTUv2p21345Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 25 is cleared"
	::= { dpsRTUv2 21345 }

dpsRTUv2p20346Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 26 is set"
	::= { dpsRTUv2 20346 }

dpsRTUv2p21346Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 26 is cleared"
	::= { dpsRTUv2 21346 }

dpsRTUv2p20347Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 27 is set"
	::= { dpsRTUv2 20347 }

dpsRTUv2p21347Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 27 is cleared"
	::= { dpsRTUv2 21347 }

dpsRTUv2p20348Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 28 is set"
	::= { dpsRTUv2 20348 }

dpsRTUv2p21348Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 28 is cleared"
	::= { dpsRTUv2 21348 }

dpsRTUv2p20349Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 29 is set"
	::= { dpsRTUv2 20349 }

dpsRTUv2p21349Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 29 is cleared"
	::= { dpsRTUv2 21349 }

dpsRTUv2p20350Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 30 is set"
	::= { dpsRTUv2 20350 }

dpsRTUv2p21350Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 30 is cleared"
	::= { dpsRTUv2 21350 }

dpsRTUv2p20351Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 31 is set"
	::= { dpsRTUv2 20351 }

dpsRTUv2p21351Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 31 is cleared"
	::= { dpsRTUv2 21351 }

dpsRTUv2p20352Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 32 is set"
	::= { dpsRTUv2 20352 }

dpsRTUv2p21352Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 32 is cleared"
	::= { dpsRTUv2 21352 }

dpsRTUv2p20353Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 33 is set"
	::= { dpsRTUv2 20353 }

dpsRTUv2p21353Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 33 is cleared"
	::= { dpsRTUv2 21353 }

dpsRTUv2p20354Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 34 is set"
	::= { dpsRTUv2 20354 }

dpsRTUv2p21354Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 34 is cleared"
	::= { dpsRTUv2 21354 }

dpsRTUv2p20355Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 35 is set"
	::= { dpsRTUv2 20355 }

dpsRTUv2p21355Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 35 is cleared"
	::= { dpsRTUv2 21355 }

dpsRTUv2p20356Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 36 is set"
	::= { dpsRTUv2 20356 }

dpsRTUv2p21356Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 36 is cleared"
	::= { dpsRTUv2 21356 }

dpsRTUv2p20357Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 37 is set"
	::= { dpsRTUv2 20357 }

dpsRTUv2p21357Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 37 is cleared"
	::= { dpsRTUv2 21357 }

dpsRTUv2p20358Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 38 is set"
	::= { dpsRTUv2 20358 }

dpsRTUv2p21358Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 38 is cleared"
	::= { dpsRTUv2 21358 }

dpsRTUv2p20359Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 39 is set"
	::= { dpsRTUv2 20359 }

dpsRTUv2p21359Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 39 is cleared"
	::= { dpsRTUv2 21359 }

dpsRTUv2p20360Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 40 is set"
	::= { dpsRTUv2 20360 }

dpsRTUv2p21360Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 40 is cleared"
	::= { dpsRTUv2 21360 }

dpsRTUv2p20361Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 41 is set"
	::= { dpsRTUv2 20361 }

dpsRTUv2p21361Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 41 is cleared"
	::= { dpsRTUv2 21361 }

dpsRTUv2p20362Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 42 is set"
	::= { dpsRTUv2 20362 }

dpsRTUv2p21362Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 42 is cleared"
	::= { dpsRTUv2 21362 }

dpsRTUv2p20363Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 43 is set"
	::= { dpsRTUv2 20363 }

dpsRTUv2p21363Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 43 is cleared"
	::= { dpsRTUv2 21363 }

dpsRTUv2p20364Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 44 is set"
	::= { dpsRTUv2 20364 }

dpsRTUv2p21364Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 44 is cleared"
	::= { dpsRTUv2 21364 }

dpsRTUv2p20365Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 45 is set"
	::= { dpsRTUv2 20365 }

dpsRTUv2p21365Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 45 is cleared"
	::= { dpsRTUv2 21365 }

dpsRTUv2p20366Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 46 is set"
	::= { dpsRTUv2 20366 }

dpsRTUv2p21366Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 46 is cleared"
	::= { dpsRTUv2 21366 }

dpsRTUv2p20367Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 47 is set"
	::= { dpsRTUv2 20367 }

dpsRTUv2p21367Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 47 is cleared"
	::= { dpsRTUv2 21367 }

dpsRTUv2p20368Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 48 is set"
	::= { dpsRTUv2 20368 }

dpsRTUv2p21368Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 48 is cleared"
	::= { dpsRTUv2 21368 }

dpsRTUv2p20369Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 49 is set"
	::= { dpsRTUv2 20369 }

dpsRTUv2p21369Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 49 is cleared"
	::= { dpsRTUv2 21369 }

dpsRTUv2p20370Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 50 is set"
	::= { dpsRTUv2 20370 }

dpsRTUv2p21370Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 50 is cleared"
	::= { dpsRTUv2 21370 }

dpsRTUv2p20371Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 51 is set"
	::= { dpsRTUv2 20371 }

dpsRTUv2p21371Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 51 is cleared"
	::= { dpsRTUv2 21371 }

dpsRTUv2p20372Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 52 is set"
	::= { dpsRTUv2 20372 }

dpsRTUv2p21372Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 52 is cleared"
	::= { dpsRTUv2 21372 }

dpsRTUv2p20373Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 53 is set"
	::= { dpsRTUv2 20373 }

dpsRTUv2p21373Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 53 is cleared"
	::= { dpsRTUv2 21373 }

dpsRTUv2p20374Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 54 is set"
	::= { dpsRTUv2 20374 }

dpsRTUv2p21374Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 54 is cleared"
	::= { dpsRTUv2 21374 }

dpsRTUv2p20375Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 55 is set"
	::= { dpsRTUv2 20375 }

dpsRTUv2p21375Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 55 is cleared"
	::= { dpsRTUv2 21375 }

dpsRTUv2p20376Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 56 is set"
	::= { dpsRTUv2 20376 }

dpsRTUv2p21376Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 56 is cleared"
	::= { dpsRTUv2 21376 }

dpsRTUv2p20377Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 57 is set"
	::= { dpsRTUv2 20377 }

dpsRTUv2p21377Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 57 is cleared"
	::= { dpsRTUv2 21377 }

dpsRTUv2p20378Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 58 is set"
	::= { dpsRTUv2 20378 }

dpsRTUv2p21378Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 58 is cleared"
	::= { dpsRTUv2 21378 }

dpsRTUv2p20379Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 59 is set"
	::= { dpsRTUv2 20379 }

dpsRTUv2p21379Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 59 is cleared"
	::= { dpsRTUv2 21379 }

dpsRTUv2p20380Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 60 is set"
	::= { dpsRTUv2 20380 }

dpsRTUv2p21380Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 60 is cleared"
	::= { dpsRTUv2 21380 }

dpsRTUv2p20381Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 61 is set"
	::= { dpsRTUv2 20381 }

dpsRTUv2p21381Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 61 is cleared"
	::= { dpsRTUv2 21381 }

dpsRTUv2p20382Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 62 is set"
	::= { dpsRTUv2 20382 }

dpsRTUv2p21382Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 62 is cleared"
	::= { dpsRTUv2 21382 }

dpsRTUv2p20383Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 63 is set"
	::= { dpsRTUv2 20383 }

dpsRTUv2p21383Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 63 is cleared"
	::= { dpsRTUv2 21383 }

dpsRTUv2p20384Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 64 is set"
	::= { dpsRTUv2 20384 }

dpsRTUv2p21384Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 6 point 64 is cleared"
	::= { dpsRTUv2 21384 }

dpsRTUv2p20385Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 1 is set"
	::= { dpsRTUv2 20385 }

dpsRTUv2p21385Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 1 is cleared"
	::= { dpsRTUv2 21385 }

dpsRTUv2p20386Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 2 is set"
	::= { dpsRTUv2 20386 }

dpsRTUv2p21386Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 2 is cleared"
	::= { dpsRTUv2 21386 }

dpsRTUv2p20387Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 3 is set"
	::= { dpsRTUv2 20387 }

dpsRTUv2p21387Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 3 is cleared"
	::= { dpsRTUv2 21387 }

dpsRTUv2p20388Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 4 is set"
	::= { dpsRTUv2 20388 }

dpsRTUv2p21388Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 4 is cleared"
	::= { dpsRTUv2 21388 }

dpsRTUv2p20389Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 5 is set"
	::= { dpsRTUv2 20389 }

dpsRTUv2p21389Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 5 is cleared"
	::= { dpsRTUv2 21389 }

dpsRTUv2p20390Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 6 is set"
	::= { dpsRTUv2 20390 }

dpsRTUv2p21390Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 6 is cleared"
	::= { dpsRTUv2 21390 }

dpsRTUv2p20391Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 7 is set"
	::= { dpsRTUv2 20391 }

dpsRTUv2p21391Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 7 is cleared"
	::= { dpsRTUv2 21391 }

dpsRTUv2p20392Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 8 is set"
	::= { dpsRTUv2 20392 }

dpsRTUv2p21392Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 8 is cleared"
	::= { dpsRTUv2 21392 }

dpsRTUv2p20393Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 9 is set"
	::= { dpsRTUv2 20393 }

dpsRTUv2p21393Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 9 is cleared"
	::= { dpsRTUv2 21393 }

dpsRTUv2p20394Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 10 is set"
	::= { dpsRTUv2 20394 }

dpsRTUv2p21394Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 10 is cleared"
	::= { dpsRTUv2 21394 }

dpsRTUv2p20395Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 11 is set"
	::= { dpsRTUv2 20395 }

dpsRTUv2p21395Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 11 is cleared"
	::= { dpsRTUv2 21395 }

dpsRTUv2p20396Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 12 is set"
	::= { dpsRTUv2 20396 }

dpsRTUv2p21396Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 12 is cleared"
	::= { dpsRTUv2 21396 }

dpsRTUv2p20397Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 13 is set"
	::= { dpsRTUv2 20397 }

dpsRTUv2p21397Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 13 is cleared"
	::= { dpsRTUv2 21397 }

dpsRTUv2p20398Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 14 is set"
	::= { dpsRTUv2 20398 }

dpsRTUv2p21398Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 14 is cleared"
	::= { dpsRTUv2 21398 }

dpsRTUv2p20399Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 15 is set"
	::= { dpsRTUv2 20399 }

dpsRTUv2p21399Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 15 is cleared"
	::= { dpsRTUv2 21399 }

dpsRTUv2p20400Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 16 is set"
	::= { dpsRTUv2 20400 }

dpsRTUv2p21400Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 16 is cleared"
	::= { dpsRTUv2 21400 }

dpsRTUv2p20401Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 17 is set"
	::= { dpsRTUv2 20401 }

dpsRTUv2p21401Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 17 is cleared"
	::= { dpsRTUv2 21401 }

dpsRTUv2p20402Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 18 is set"
	::= { dpsRTUv2 20402 }

dpsRTUv2p21402Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 18 is cleared"
	::= { dpsRTUv2 21402 }

dpsRTUv2p20403Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 19 is set"
	::= { dpsRTUv2 20403 }

dpsRTUv2p21403Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 19 is cleared"
	::= { dpsRTUv2 21403 }

dpsRTUv2p20404Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 20 is set"
	::= { dpsRTUv2 20404 }

dpsRTUv2p21404Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 20 is cleared"
	::= { dpsRTUv2 21404 }

dpsRTUv2p20405Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 21 is set"
	::= { dpsRTUv2 20405 }

dpsRTUv2p21405Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 21 is cleared"
	::= { dpsRTUv2 21405 }

dpsRTUv2p20406Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 22 is set"
	::= { dpsRTUv2 20406 }

dpsRTUv2p21406Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 22 is cleared"
	::= { dpsRTUv2 21406 }

dpsRTUv2p20407Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 23 is set"
	::= { dpsRTUv2 20407 }

dpsRTUv2p21407Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 23 is cleared"
	::= { dpsRTUv2 21407 }

dpsRTUv2p20408Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 24 is set"
	::= { dpsRTUv2 20408 }

dpsRTUv2p21408Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 24 is cleared"
	::= { dpsRTUv2 21408 }

dpsRTUv2p20409Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 25 is set"
	::= { dpsRTUv2 20409 }

dpsRTUv2p21409Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 25 is cleared"
	::= { dpsRTUv2 21409 }

dpsRTUv2p20410Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 26 is set"
	::= { dpsRTUv2 20410 }

dpsRTUv2p21410Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 26 is cleared"
	::= { dpsRTUv2 21410 }

dpsRTUv2p20411Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 27 is set"
	::= { dpsRTUv2 20411 }

dpsRTUv2p21411Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 27 is cleared"
	::= { dpsRTUv2 21411 }

dpsRTUv2p20412Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 28 is set"
	::= { dpsRTUv2 20412 }

dpsRTUv2p21412Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 28 is cleared"
	::= { dpsRTUv2 21412 }

dpsRTUv2p20413Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 29 is set"
	::= { dpsRTUv2 20413 }

dpsRTUv2p21413Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 29 is cleared"
	::= { dpsRTUv2 21413 }

dpsRTUv2p20414Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 30 is set"
	::= { dpsRTUv2 20414 }

dpsRTUv2p21414Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 30 is cleared"
	::= { dpsRTUv2 21414 }

dpsRTUv2p20415Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 31 is set"
	::= { dpsRTUv2 20415 }

dpsRTUv2p21415Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 31 is cleared"
	::= { dpsRTUv2 21415 }

dpsRTUv2p20416Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 32 is set"
	::= { dpsRTUv2 20416 }

dpsRTUv2p21416Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 32 is cleared"
	::= { dpsRTUv2 21416 }

dpsRTUv2p20417Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 33 is set"
	::= { dpsRTUv2 20417 }

dpsRTUv2p21417Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 33 is cleared"
	::= { dpsRTUv2 21417 }

dpsRTUv2p20418Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 34 is set"
	::= { dpsRTUv2 20418 }

dpsRTUv2p21418Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 34 is cleared"
	::= { dpsRTUv2 21418 }

dpsRTUv2p20419Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 35 is set"
	::= { dpsRTUv2 20419 }

dpsRTUv2p21419Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 35 is cleared"
	::= { dpsRTUv2 21419 }

dpsRTUv2p20420Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 36 is set"
	::= { dpsRTUv2 20420 }

dpsRTUv2p21420Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 36 is cleared"
	::= { dpsRTUv2 21420 }

dpsRTUv2p20421Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 37 is set"
	::= { dpsRTUv2 20421 }

dpsRTUv2p21421Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 37 is cleared"
	::= { dpsRTUv2 21421 }

dpsRTUv2p20422Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 38 is set"
	::= { dpsRTUv2 20422 }

dpsRTUv2p21422Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 38 is cleared"
	::= { dpsRTUv2 21422 }

dpsRTUv2p20423Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 39 is set"
	::= { dpsRTUv2 20423 }

dpsRTUv2p21423Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 39 is cleared"
	::= { dpsRTUv2 21423 }

dpsRTUv2p20424Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 40 is set"
	::= { dpsRTUv2 20424 }

dpsRTUv2p21424Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 40 is cleared"
	::= { dpsRTUv2 21424 }

dpsRTUv2p20425Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 41 is set"
	::= { dpsRTUv2 20425 }

dpsRTUv2p21425Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 41 is cleared"
	::= { dpsRTUv2 21425 }

dpsRTUv2p20426Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 42 is set"
	::= { dpsRTUv2 20426 }

dpsRTUv2p21426Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 42 is cleared"
	::= { dpsRTUv2 21426 }

dpsRTUv2p20427Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 43 is set"
	::= { dpsRTUv2 20427 }

dpsRTUv2p21427Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 43 is cleared"
	::= { dpsRTUv2 21427 }

dpsRTUv2p20428Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 44 is set"
	::= { dpsRTUv2 20428 }

dpsRTUv2p21428Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 44 is cleared"
	::= { dpsRTUv2 21428 }

dpsRTUv2p20429Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 45 is set"
	::= { dpsRTUv2 20429 }

dpsRTUv2p21429Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 45 is cleared"
	::= { dpsRTUv2 21429 }

dpsRTUv2p20430Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 46 is set"
	::= { dpsRTUv2 20430 }

dpsRTUv2p21430Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 46 is cleared"
	::= { dpsRTUv2 21430 }

dpsRTUv2p20431Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 47 is set"
	::= { dpsRTUv2 20431 }

dpsRTUv2p21431Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 47 is cleared"
	::= { dpsRTUv2 21431 }

dpsRTUv2p20432Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 48 is set"
	::= { dpsRTUv2 20432 }

dpsRTUv2p21432Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 48 is cleared"
	::= { dpsRTUv2 21432 }

dpsRTUv2p20433Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 49 is set"
	::= { dpsRTUv2 20433 }

dpsRTUv2p21433Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 49 is cleared"
	::= { dpsRTUv2 21433 }

dpsRTUv2p20434Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 50 is set"
	::= { dpsRTUv2 20434 }

dpsRTUv2p21434Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 50 is cleared"
	::= { dpsRTUv2 21434 }

dpsRTUv2p20435Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 51 is set"
	::= { dpsRTUv2 20435 }

dpsRTUv2p21435Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 51 is cleared"
	::= { dpsRTUv2 21435 }

dpsRTUv2p20436Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 52 is set"
	::= { dpsRTUv2 20436 }

dpsRTUv2p21436Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 52 is cleared"
	::= { dpsRTUv2 21436 }

dpsRTUv2p20437Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 53 is set"
	::= { dpsRTUv2 20437 }

dpsRTUv2p21437Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 53 is cleared"
	::= { dpsRTUv2 21437 }

dpsRTUv2p20438Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 54 is set"
	::= { dpsRTUv2 20438 }

dpsRTUv2p21438Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 54 is cleared"
	::= { dpsRTUv2 21438 }

dpsRTUv2p20439Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 55 is set"
	::= { dpsRTUv2 20439 }

dpsRTUv2p21439Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 55 is cleared"
	::= { dpsRTUv2 21439 }

dpsRTUv2p20440Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 56 is set"
	::= { dpsRTUv2 20440 }

dpsRTUv2p21440Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 56 is cleared"
	::= { dpsRTUv2 21440 }

dpsRTUv2p20441Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 57 is set"
	::= { dpsRTUv2 20441 }

dpsRTUv2p21441Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 57 is cleared"
	::= { dpsRTUv2 21441 }

dpsRTUv2p20442Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 58 is set"
	::= { dpsRTUv2 20442 }

dpsRTUv2p21442Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 58 is cleared"
	::= { dpsRTUv2 21442 }

dpsRTUv2p20443Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 59 is set"
	::= { dpsRTUv2 20443 }

dpsRTUv2p21443Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 59 is cleared"
	::= { dpsRTUv2 21443 }

dpsRTUv2p20444Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 60 is set"
	::= { dpsRTUv2 20444 }

dpsRTUv2p21444Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 60 is cleared"
	::= { dpsRTUv2 21444 }

dpsRTUv2p20445Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 61 is set"
	::= { dpsRTUv2 20445 }

dpsRTUv2p21445Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 61 is cleared"
	::= { dpsRTUv2 21445 }

dpsRTUv2p20446Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 62 is set"
	::= { dpsRTUv2 20446 }

dpsRTUv2p21446Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 62 is cleared"
	::= { dpsRTUv2 21446 }

dpsRTUv2p20447Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 63 is set"
	::= { dpsRTUv2 20447 }

dpsRTUv2p21447Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 63 is cleared"
	::= { dpsRTUv2 21447 }

dpsRTUv2p20448Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 64 is set"
	::= { dpsRTUv2 20448 }

dpsRTUv2p21448Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 7 point 64 is cleared"
	::= { dpsRTUv2 21448 }

dpsRTUv2p20449Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 1 is set"
	::= { dpsRTUv2 20449 }

dpsRTUv2p21449Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 1 is cleared"
	::= { dpsRTUv2 21449 }

dpsRTUv2p20450Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 2 is set"
	::= { dpsRTUv2 20450 }

dpsRTUv2p21450Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 2 is cleared"
	::= { dpsRTUv2 21450 }

dpsRTUv2p20451Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 3 is set"
	::= { dpsRTUv2 20451 }

dpsRTUv2p21451Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 3 is cleared"
	::= { dpsRTUv2 21451 }

dpsRTUv2p20452Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 4 is set"
	::= { dpsRTUv2 20452 }

dpsRTUv2p21452Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 4 is cleared"
	::= { dpsRTUv2 21452 }

dpsRTUv2p20453Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 5 is set"
	::= { dpsRTUv2 20453 }

dpsRTUv2p21453Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 5 is cleared"
	::= { dpsRTUv2 21453 }

dpsRTUv2p20454Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 6 is set"
	::= { dpsRTUv2 20454 }

dpsRTUv2p21454Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 6 is cleared"
	::= { dpsRTUv2 21454 }

dpsRTUv2p20455Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 7 is set"
	::= { dpsRTUv2 20455 }

dpsRTUv2p21455Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 7 is cleared"
	::= { dpsRTUv2 21455 }

dpsRTUv2p20456Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 8 is set"
	::= { dpsRTUv2 20456 }

dpsRTUv2p21456Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 8 is cleared"
	::= { dpsRTUv2 21456 }

dpsRTUv2p20457Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 9 is set"
	::= { dpsRTUv2 20457 }

dpsRTUv2p21457Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 9 is cleared"
	::= { dpsRTUv2 21457 }

dpsRTUv2p20458Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 10 is set"
	::= { dpsRTUv2 20458 }

dpsRTUv2p21458Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 10 is cleared"
	::= { dpsRTUv2 21458 }

dpsRTUv2p20459Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 11 is set"
	::= { dpsRTUv2 20459 }

dpsRTUv2p21459Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 11 is cleared"
	::= { dpsRTUv2 21459 }

dpsRTUv2p20460Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 12 is set"
	::= { dpsRTUv2 20460 }

dpsRTUv2p21460Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 12 is cleared"
	::= { dpsRTUv2 21460 }

dpsRTUv2p20461Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 13 is set"
	::= { dpsRTUv2 20461 }

dpsRTUv2p21461Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 13 is cleared"
	::= { dpsRTUv2 21461 }

dpsRTUv2p20462Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 14 is set"
	::= { dpsRTUv2 20462 }

dpsRTUv2p21462Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 14 is cleared"
	::= { dpsRTUv2 21462 }

dpsRTUv2p20463Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 15 is set"
	::= { dpsRTUv2 20463 }

dpsRTUv2p21463Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 15 is cleared"
	::= { dpsRTUv2 21463 }

dpsRTUv2p20464Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 16 is set"
	::= { dpsRTUv2 20464 }

dpsRTUv2p21464Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 16 is cleared"
	::= { dpsRTUv2 21464 }

dpsRTUv2p20465Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 17 is set"
	::= { dpsRTUv2 20465 }

dpsRTUv2p21465Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 17 is cleared"
	::= { dpsRTUv2 21465 }

dpsRTUv2p20466Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 18 is set"
	::= { dpsRTUv2 20466 }

dpsRTUv2p21466Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 18 is cleared"
	::= { dpsRTUv2 21466 }

dpsRTUv2p20467Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 19 is set"
	::= { dpsRTUv2 20467 }

dpsRTUv2p21467Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 19 is cleared"
	::= { dpsRTUv2 21467 }

dpsRTUv2p20468Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 20 is set"
	::= { dpsRTUv2 20468 }

dpsRTUv2p21468Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 20 is cleared"
	::= { dpsRTUv2 21468 }

dpsRTUv2p20469Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 21 is set"
	::= { dpsRTUv2 20469 }

dpsRTUv2p21469Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 21 is cleared"
	::= { dpsRTUv2 21469 }

dpsRTUv2p20470Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 22 is set"
	::= { dpsRTUv2 20470 }

dpsRTUv2p21470Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 22 is cleared"
	::= { dpsRTUv2 21470 }

dpsRTUv2p20471Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 23 is set"
	::= { dpsRTUv2 20471 }

dpsRTUv2p21471Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 23 is cleared"
	::= { dpsRTUv2 21471 }

dpsRTUv2p20472Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 24 is set"
	::= { dpsRTUv2 20472 }

dpsRTUv2p21472Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 24 is cleared"
	::= { dpsRTUv2 21472 }

dpsRTUv2p20473Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 25 is set"
	::= { dpsRTUv2 20473 }

dpsRTUv2p21473Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 25 is cleared"
	::= { dpsRTUv2 21473 }

dpsRTUv2p20474Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 26 is set"
	::= { dpsRTUv2 20474 }

dpsRTUv2p21474Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 26 is cleared"
	::= { dpsRTUv2 21474 }

dpsRTUv2p20475Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 27 is set"
	::= { dpsRTUv2 20475 }

dpsRTUv2p21475Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 27 is cleared"
	::= { dpsRTUv2 21475 }

dpsRTUv2p20476Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 28 is set"
	::= { dpsRTUv2 20476 }

dpsRTUv2p21476Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 28 is cleared"
	::= { dpsRTUv2 21476 }

dpsRTUv2p20477Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 29 is set"
	::= { dpsRTUv2 20477 }

dpsRTUv2p21477Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 29 is cleared"
	::= { dpsRTUv2 21477 }

dpsRTUv2p20478Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 30 is set"
	::= { dpsRTUv2 20478 }

dpsRTUv2p21478Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 30 is cleared"
	::= { dpsRTUv2 21478 }

dpsRTUv2p20479Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 31 is set"
	::= { dpsRTUv2 20479 }

dpsRTUv2p21479Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 31 is cleared"
	::= { dpsRTUv2 21479 }

dpsRTUv2p20480Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 32 is set"
	::= { dpsRTUv2 20480 }

dpsRTUv2p21480Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 32 is cleared"
	::= { dpsRTUv2 21480 }

dpsRTUv2p20481Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 33 is set"
	::= { dpsRTUv2 20481 }

dpsRTUv2p21481Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 33 is cleared"
	::= { dpsRTUv2 21481 }

dpsRTUv2p20482Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 34 is set"
	::= { dpsRTUv2 20482 }

dpsRTUv2p21482Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 34 is cleared"
	::= { dpsRTUv2 21482 }

dpsRTUv2p20483Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 35 is set"
	::= { dpsRTUv2 20483 }

dpsRTUv2p21483Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 35 is cleared"
	::= { dpsRTUv2 21483 }

dpsRTUv2p20484Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 36 is set"
	::= { dpsRTUv2 20484 }

dpsRTUv2p21484Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 36 is cleared"
	::= { dpsRTUv2 21484 }

dpsRTUv2p20485Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 37 is set"
	::= { dpsRTUv2 20485 }

dpsRTUv2p21485Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 37 is cleared"
	::= { dpsRTUv2 21485 }

dpsRTUv2p20486Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 38 is set"
	::= { dpsRTUv2 20486 }

dpsRTUv2p21486Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 38 is cleared"
	::= { dpsRTUv2 21486 }

dpsRTUv2p20487Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 39 is set"
	::= { dpsRTUv2 20487 }

dpsRTUv2p21487Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 39 is cleared"
	::= { dpsRTUv2 21487 }

dpsRTUv2p20488Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 40 is set"
	::= { dpsRTUv2 20488 }

dpsRTUv2p21488Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 40 is cleared"
	::= { dpsRTUv2 21488 }

dpsRTUv2p20489Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 41 is set"
	::= { dpsRTUv2 20489 }

dpsRTUv2p21489Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 41 is cleared"
	::= { dpsRTUv2 21489 }

dpsRTUv2p20490Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 42 is set"
	::= { dpsRTUv2 20490 }

dpsRTUv2p21490Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 42 is cleared"
	::= { dpsRTUv2 21490 }

dpsRTUv2p20491Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 43 is set"
	::= { dpsRTUv2 20491 }

dpsRTUv2p21491Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 43 is cleared"
	::= { dpsRTUv2 21491 }

dpsRTUv2p20492Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 44 is set"
	::= { dpsRTUv2 20492 }

dpsRTUv2p21492Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 44 is cleared"
	::= { dpsRTUv2 21492 }

dpsRTUv2p20493Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 45 is set"
	::= { dpsRTUv2 20493 }

dpsRTUv2p21493Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 45 is cleared"
	::= { dpsRTUv2 21493 }

dpsRTUv2p20494Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 46 is set"
	::= { dpsRTUv2 20494 }

dpsRTUv2p21494Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 46 is cleared"
	::= { dpsRTUv2 21494 }

dpsRTUv2p20495Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 47 is set"
	::= { dpsRTUv2 20495 }

dpsRTUv2p21495Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 47 is cleared"
	::= { dpsRTUv2 21495 }

dpsRTUv2p20496Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 48 is set"
	::= { dpsRTUv2 20496 }

dpsRTUv2p21496Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 48 is cleared"
	::= { dpsRTUv2 21496 }

dpsRTUv2p20497Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 49 is set"
	::= { dpsRTUv2 20497 }

dpsRTUv2p21497Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 49 is cleared"
	::= { dpsRTUv2 21497 }

dpsRTUv2p20498Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 50 is set"
	::= { dpsRTUv2 20498 }

dpsRTUv2p21498Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 50 is cleared"
	::= { dpsRTUv2 21498 }

dpsRTUv2p20499Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 51 is set"
	::= { dpsRTUv2 20499 }

dpsRTUv2p21499Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 51 is cleared"
	::= { dpsRTUv2 21499 }

dpsRTUv2p20500Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 52 is set"
	::= { dpsRTUv2 20500 }

dpsRTUv2p21500Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 52 is cleared"
	::= { dpsRTUv2 21500 }

dpsRTUv2p20501Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 53 is set"
	::= { dpsRTUv2 20501 }

dpsRTUv2p21501Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 53 is cleared"
	::= { dpsRTUv2 21501 }

dpsRTUv2p20502Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 54 is set"
	::= { dpsRTUv2 20502 }

dpsRTUv2p21502Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 54 is cleared"
	::= { dpsRTUv2 21502 }

dpsRTUv2p20503Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 55 is set"
	::= { dpsRTUv2 20503 }

dpsRTUv2p21503Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 55 is cleared"
	::= { dpsRTUv2 21503 }

dpsRTUv2p20504Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 56 is set"
	::= { dpsRTUv2 20504 }

dpsRTUv2p21504Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 56 is cleared"
	::= { dpsRTUv2 21504 }

dpsRTUv2p20505Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 57 is set"
	::= { dpsRTUv2 20505 }

dpsRTUv2p21505Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 57 is cleared"
	::= { dpsRTUv2 21505 }

dpsRTUv2p20506Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 58 is set"
	::= { dpsRTUv2 20506 }

dpsRTUv2p21506Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 58 is cleared"
	::= { dpsRTUv2 21506 }

dpsRTUv2p20507Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 59 is set"
	::= { dpsRTUv2 20507 }

dpsRTUv2p21507Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 59 is cleared"
	::= { dpsRTUv2 21507 }

dpsRTUv2p20508Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 60 is set"
	::= { dpsRTUv2 20508 }

dpsRTUv2p21508Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 60 is cleared"
	::= { dpsRTUv2 21508 }

dpsRTUv2p20509Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 61 is set"
	::= { dpsRTUv2 20509 }

dpsRTUv2p21509Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 61 is cleared"
	::= { dpsRTUv2 21509 }

dpsRTUv2p20510Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 62 is set"
	::= { dpsRTUv2 20510 }

dpsRTUv2p21510Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 62 is cleared"
	::= { dpsRTUv2 21510 }

dpsRTUv2p20511Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 63 is set"
	::= { dpsRTUv2 20511 }

dpsRTUv2p21511Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 63 is cleared"
	::= { dpsRTUv2 21511 }

dpsRTUv2p20512Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 64 is set"
	::= { dpsRTUv2 20512 }

dpsRTUv2p21512Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 6 display 8 point 64 is cleared"
	::= { dpsRTUv2 21512 }

dpsRTUv2p22001Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 1 is set"
	::= { dpsRTUv2 22001 }

dpsRTUv2p23001Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 1 is cleared"
	::= { dpsRTUv2 23001 }

dpsRTUv2p22002Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 2 is set"
	::= { dpsRTUv2 22002 }

dpsRTUv2p23002Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 2 is cleared"
	::= { dpsRTUv2 23002 }

dpsRTUv2p22003Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 3 is set"
	::= { dpsRTUv2 22003 }

dpsRTUv2p23003Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 3 is cleared"
	::= { dpsRTUv2 23003 }

dpsRTUv2p22004Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 4 is set"
	::= { dpsRTUv2 22004 }

dpsRTUv2p23004Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 4 is cleared"
	::= { dpsRTUv2 23004 }

dpsRTUv2p22005Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 5 is set"
	::= { dpsRTUv2 22005 }

dpsRTUv2p23005Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 5 is cleared"
	::= { dpsRTUv2 23005 }

dpsRTUv2p22006Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 6 is set"
	::= { dpsRTUv2 22006 }

dpsRTUv2p23006Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 6 is cleared"
	::= { dpsRTUv2 23006 }

dpsRTUv2p22007Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 7 is set"
	::= { dpsRTUv2 22007 }

dpsRTUv2p23007Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 7 is cleared"
	::= { dpsRTUv2 23007 }

dpsRTUv2p22008Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 8 is set"
	::= { dpsRTUv2 22008 }

dpsRTUv2p23008Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 8 is cleared"
	::= { dpsRTUv2 23008 }

dpsRTUv2p22009Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 9 is set"
	::= { dpsRTUv2 22009 }

dpsRTUv2p23009Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 9 is cleared"
	::= { dpsRTUv2 23009 }

dpsRTUv2p22010Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 10 is set"
	::= { dpsRTUv2 22010 }

dpsRTUv2p23010Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 10 is cleared"
	::= { dpsRTUv2 23010 }

dpsRTUv2p22011Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 11 is set"
	::= { dpsRTUv2 22011 }

dpsRTUv2p23011Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 11 is cleared"
	::= { dpsRTUv2 23011 }

dpsRTUv2p22012Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 12 is set"
	::= { dpsRTUv2 22012 }

dpsRTUv2p23012Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 12 is cleared"
	::= { dpsRTUv2 23012 }

dpsRTUv2p22013Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 13 is set"
	::= { dpsRTUv2 22013 }

dpsRTUv2p23013Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 13 is cleared"
	::= { dpsRTUv2 23013 }

dpsRTUv2p22014Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 14 is set"
	::= { dpsRTUv2 22014 }

dpsRTUv2p23014Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 14 is cleared"
	::= { dpsRTUv2 23014 }

dpsRTUv2p22015Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 15 is set"
	::= { dpsRTUv2 22015 }

dpsRTUv2p23015Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 15 is cleared"
	::= { dpsRTUv2 23015 }

dpsRTUv2p22016Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 16 is set"
	::= { dpsRTUv2 22016 }

dpsRTUv2p23016Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 16 is cleared"
	::= { dpsRTUv2 23016 }

dpsRTUv2p22017Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 17 is set"
	::= { dpsRTUv2 22017 }

dpsRTUv2p23017Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 17 is cleared"
	::= { dpsRTUv2 23017 }

dpsRTUv2p22018Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 18 is set"
	::= { dpsRTUv2 22018 }

dpsRTUv2p23018Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 18 is cleared"
	::= { dpsRTUv2 23018 }

dpsRTUv2p22019Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 19 is set"
	::= { dpsRTUv2 22019 }

dpsRTUv2p23019Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 19 is cleared"
	::= { dpsRTUv2 23019 }

dpsRTUv2p22020Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 20 is set"
	::= { dpsRTUv2 22020 }

dpsRTUv2p23020Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 20 is cleared"
	::= { dpsRTUv2 23020 }

dpsRTUv2p22021Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 21 is set"
	::= { dpsRTUv2 22021 }

dpsRTUv2p23021Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 21 is cleared"
	::= { dpsRTUv2 23021 }

dpsRTUv2p22022Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 22 is set"
	::= { dpsRTUv2 22022 }

dpsRTUv2p23022Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 22 is cleared"
	::= { dpsRTUv2 23022 }

dpsRTUv2p22023Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 23 is set"
	::= { dpsRTUv2 22023 }

dpsRTUv2p23023Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 23 is cleared"
	::= { dpsRTUv2 23023 }

dpsRTUv2p22024Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 24 is set"
	::= { dpsRTUv2 22024 }

dpsRTUv2p23024Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 24 is cleared"
	::= { dpsRTUv2 23024 }

dpsRTUv2p22025Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 25 is set"
	::= { dpsRTUv2 22025 }

dpsRTUv2p23025Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 25 is cleared"
	::= { dpsRTUv2 23025 }

dpsRTUv2p22026Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 26 is set"
	::= { dpsRTUv2 22026 }

dpsRTUv2p23026Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 26 is cleared"
	::= { dpsRTUv2 23026 }

dpsRTUv2p22027Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 27 is set"
	::= { dpsRTUv2 22027 }

dpsRTUv2p23027Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 27 is cleared"
	::= { dpsRTUv2 23027 }

dpsRTUv2p22028Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 28 is set"
	::= { dpsRTUv2 22028 }

dpsRTUv2p23028Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 28 is cleared"
	::= { dpsRTUv2 23028 }

dpsRTUv2p22029Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 29 is set"
	::= { dpsRTUv2 22029 }

dpsRTUv2p23029Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 29 is cleared"
	::= { dpsRTUv2 23029 }

dpsRTUv2p22030Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 30 is set"
	::= { dpsRTUv2 22030 }

dpsRTUv2p23030Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 30 is cleared"
	::= { dpsRTUv2 23030 }

dpsRTUv2p22031Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 31 is set"
	::= { dpsRTUv2 22031 }

dpsRTUv2p23031Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 31 is cleared"
	::= { dpsRTUv2 23031 }

dpsRTUv2p22032Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 32 is set"
	::= { dpsRTUv2 22032 }

dpsRTUv2p23032Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 32 is cleared"
	::= { dpsRTUv2 23032 }

dpsRTUv2p22033Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 33 is set"
	::= { dpsRTUv2 22033 }

dpsRTUv2p23033Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 33 is cleared"
	::= { dpsRTUv2 23033 }

dpsRTUv2p22034Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 34 is set"
	::= { dpsRTUv2 22034 }

dpsRTUv2p23034Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 34 is cleared"
	::= { dpsRTUv2 23034 }

dpsRTUv2p22035Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 35 is set"
	::= { dpsRTUv2 22035 }

dpsRTUv2p23035Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 35 is cleared"
	::= { dpsRTUv2 23035 }

dpsRTUv2p22036Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 36 is set"
	::= { dpsRTUv2 22036 }

dpsRTUv2p23036Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 36 is cleared"
	::= { dpsRTUv2 23036 }

dpsRTUv2p22037Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 37 is set"
	::= { dpsRTUv2 22037 }

dpsRTUv2p23037Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 37 is cleared"
	::= { dpsRTUv2 23037 }

dpsRTUv2p22038Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 38 is set"
	::= { dpsRTUv2 22038 }

dpsRTUv2p23038Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 38 is cleared"
	::= { dpsRTUv2 23038 }

dpsRTUv2p22039Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 39 is set"
	::= { dpsRTUv2 22039 }

dpsRTUv2p23039Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 39 is cleared"
	::= { dpsRTUv2 23039 }

dpsRTUv2p22040Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 40 is set"
	::= { dpsRTUv2 22040 }

dpsRTUv2p23040Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 40 is cleared"
	::= { dpsRTUv2 23040 }

dpsRTUv2p22041Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 41 is set"
	::= { dpsRTUv2 22041 }

dpsRTUv2p23041Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 41 is cleared"
	::= { dpsRTUv2 23041 }

dpsRTUv2p22042Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 42 is set"
	::= { dpsRTUv2 22042 }

dpsRTUv2p23042Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 42 is cleared"
	::= { dpsRTUv2 23042 }

dpsRTUv2p22043Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 43 is set"
	::= { dpsRTUv2 22043 }

dpsRTUv2p23043Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 43 is cleared"
	::= { dpsRTUv2 23043 }

dpsRTUv2p22044Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 44 is set"
	::= { dpsRTUv2 22044 }

dpsRTUv2p23044Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 44 is cleared"
	::= { dpsRTUv2 23044 }

dpsRTUv2p22045Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 45 is set"
	::= { dpsRTUv2 22045 }

dpsRTUv2p23045Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 45 is cleared"
	::= { dpsRTUv2 23045 }

dpsRTUv2p22046Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 46 is set"
	::= { dpsRTUv2 22046 }

dpsRTUv2p23046Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 46 is cleared"
	::= { dpsRTUv2 23046 }

dpsRTUv2p22047Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 47 is set"
	::= { dpsRTUv2 22047 }

dpsRTUv2p23047Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 47 is cleared"
	::= { dpsRTUv2 23047 }

dpsRTUv2p22048Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 48 is set"
	::= { dpsRTUv2 22048 }

dpsRTUv2p23048Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 48 is cleared"
	::= { dpsRTUv2 23048 }

dpsRTUv2p22049Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 49 is set"
	::= { dpsRTUv2 22049 }

dpsRTUv2p23049Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 49 is cleared"
	::= { dpsRTUv2 23049 }

dpsRTUv2p22050Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 50 is set"
	::= { dpsRTUv2 22050 }

dpsRTUv2p23050Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 50 is cleared"
	::= { dpsRTUv2 23050 }

dpsRTUv2p22051Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 51 is set"
	::= { dpsRTUv2 22051 }

dpsRTUv2p23051Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 51 is cleared"
	::= { dpsRTUv2 23051 }

dpsRTUv2p22052Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 52 is set"
	::= { dpsRTUv2 22052 }

dpsRTUv2p23052Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 52 is cleared"
	::= { dpsRTUv2 23052 }

dpsRTUv2p22053Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 53 is set"
	::= { dpsRTUv2 22053 }

dpsRTUv2p23053Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 53 is cleared"
	::= { dpsRTUv2 23053 }

dpsRTUv2p22054Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 54 is set"
	::= { dpsRTUv2 22054 }

dpsRTUv2p23054Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 54 is cleared"
	::= { dpsRTUv2 23054 }

dpsRTUv2p22055Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 55 is set"
	::= { dpsRTUv2 22055 }

dpsRTUv2p23055Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 55 is cleared"
	::= { dpsRTUv2 23055 }

dpsRTUv2p22056Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 56 is set"
	::= { dpsRTUv2 22056 }

dpsRTUv2p23056Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 56 is cleared"
	::= { dpsRTUv2 23056 }

dpsRTUv2p22057Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 57 is set"
	::= { dpsRTUv2 22057 }

dpsRTUv2p23057Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 57 is cleared"
	::= { dpsRTUv2 23057 }

dpsRTUv2p22058Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 58 is set"
	::= { dpsRTUv2 22058 }

dpsRTUv2p23058Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 58 is cleared"
	::= { dpsRTUv2 23058 }

dpsRTUv2p22059Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 59 is set"
	::= { dpsRTUv2 22059 }

dpsRTUv2p23059Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 59 is cleared"
	::= { dpsRTUv2 23059 }

dpsRTUv2p22060Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 60 is set"
	::= { dpsRTUv2 22060 }

dpsRTUv2p23060Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 60 is cleared"
	::= { dpsRTUv2 23060 }

dpsRTUv2p22061Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 61 is set"
	::= { dpsRTUv2 22061 }

dpsRTUv2p23061Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 61 is cleared"
	::= { dpsRTUv2 23061 }

dpsRTUv2p22062Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 62 is set"
	::= { dpsRTUv2 22062 }

dpsRTUv2p23062Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 62 is cleared"
	::= { dpsRTUv2 23062 }

dpsRTUv2p22063Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 63 is set"
	::= { dpsRTUv2 22063 }

dpsRTUv2p23063Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 63 is cleared"
	::= { dpsRTUv2 23063 }

dpsRTUv2p22064Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 64 is set"
	::= { dpsRTUv2 22064 }

dpsRTUv2p23064Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 1 point 64 is cleared"
	::= { dpsRTUv2 23064 }

dpsRTUv2p22065Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 1 is set"
	::= { dpsRTUv2 22065 }

dpsRTUv2p23065Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 1 is cleared"
	::= { dpsRTUv2 23065 }

dpsRTUv2p22066Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 2 is set"
	::= { dpsRTUv2 22066 }

dpsRTUv2p23066Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 2 is cleared"
	::= { dpsRTUv2 23066 }

dpsRTUv2p22067Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 3 is set"
	::= { dpsRTUv2 22067 }

dpsRTUv2p23067Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 3 is cleared"
	::= { dpsRTUv2 23067 }

dpsRTUv2p22068Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 4 is set"
	::= { dpsRTUv2 22068 }

dpsRTUv2p23068Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 4 is cleared"
	::= { dpsRTUv2 23068 }

dpsRTUv2p22069Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 5 is set"
	::= { dpsRTUv2 22069 }

dpsRTUv2p23069Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 5 is cleared"
	::= { dpsRTUv2 23069 }

dpsRTUv2p22070Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 6 is set"
	::= { dpsRTUv2 22070 }

dpsRTUv2p23070Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 6 is cleared"
	::= { dpsRTUv2 23070 }

dpsRTUv2p22071Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 7 is set"
	::= { dpsRTUv2 22071 }

dpsRTUv2p23071Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 7 is cleared"
	::= { dpsRTUv2 23071 }

dpsRTUv2p22072Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 8 is set"
	::= { dpsRTUv2 22072 }

dpsRTUv2p23072Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 8 is cleared"
	::= { dpsRTUv2 23072 }

dpsRTUv2p22073Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 9 is set"
	::= { dpsRTUv2 22073 }

dpsRTUv2p23073Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 9 is cleared"
	::= { dpsRTUv2 23073 }

dpsRTUv2p22074Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 10 is set"
	::= { dpsRTUv2 22074 }

dpsRTUv2p23074Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 10 is cleared"
	::= { dpsRTUv2 23074 }

dpsRTUv2p22075Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 11 is set"
	::= { dpsRTUv2 22075 }

dpsRTUv2p23075Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 11 is cleared"
	::= { dpsRTUv2 23075 }

dpsRTUv2p22076Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 12 is set"
	::= { dpsRTUv2 22076 }

dpsRTUv2p23076Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 12 is cleared"
	::= { dpsRTUv2 23076 }

dpsRTUv2p22077Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 13 is set"
	::= { dpsRTUv2 22077 }

dpsRTUv2p23077Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 13 is cleared"
	::= { dpsRTUv2 23077 }

dpsRTUv2p22078Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 14 is set"
	::= { dpsRTUv2 22078 }

dpsRTUv2p23078Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 14 is cleared"
	::= { dpsRTUv2 23078 }

dpsRTUv2p22079Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 15 is set"
	::= { dpsRTUv2 22079 }

dpsRTUv2p23079Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 15 is cleared"
	::= { dpsRTUv2 23079 }

dpsRTUv2p22080Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 16 is set"
	::= { dpsRTUv2 22080 }

dpsRTUv2p23080Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 16 is cleared"
	::= { dpsRTUv2 23080 }

dpsRTUv2p22081Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 17 is set"
	::= { dpsRTUv2 22081 }

dpsRTUv2p23081Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 17 is cleared"
	::= { dpsRTUv2 23081 }

dpsRTUv2p22082Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 18 is set"
	::= { dpsRTUv2 22082 }

dpsRTUv2p23082Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 18 is cleared"
	::= { dpsRTUv2 23082 }

dpsRTUv2p22083Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 19 is set"
	::= { dpsRTUv2 22083 }

dpsRTUv2p23083Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 19 is cleared"
	::= { dpsRTUv2 23083 }

dpsRTUv2p22084Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 20 is set"
	::= { dpsRTUv2 22084 }

dpsRTUv2p23084Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 20 is cleared"
	::= { dpsRTUv2 23084 }

dpsRTUv2p22085Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 21 is set"
	::= { dpsRTUv2 22085 }

dpsRTUv2p23085Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 21 is cleared"
	::= { dpsRTUv2 23085 }

dpsRTUv2p22086Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 22 is set"
	::= { dpsRTUv2 22086 }

dpsRTUv2p23086Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 22 is cleared"
	::= { dpsRTUv2 23086 }

dpsRTUv2p22087Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 23 is set"
	::= { dpsRTUv2 22087 }

dpsRTUv2p23087Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 23 is cleared"
	::= { dpsRTUv2 23087 }

dpsRTUv2p22088Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 24 is set"
	::= { dpsRTUv2 22088 }

dpsRTUv2p23088Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 24 is cleared"
	::= { dpsRTUv2 23088 }

dpsRTUv2p22089Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 25 is set"
	::= { dpsRTUv2 22089 }

dpsRTUv2p23089Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 25 is cleared"
	::= { dpsRTUv2 23089 }

dpsRTUv2p22090Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 26 is set"
	::= { dpsRTUv2 22090 }

dpsRTUv2p23090Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 26 is cleared"
	::= { dpsRTUv2 23090 }

dpsRTUv2p22091Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 27 is set"
	::= { dpsRTUv2 22091 }

dpsRTUv2p23091Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 27 is cleared"
	::= { dpsRTUv2 23091 }

dpsRTUv2p22092Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 28 is set"
	::= { dpsRTUv2 22092 }

dpsRTUv2p23092Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 28 is cleared"
	::= { dpsRTUv2 23092 }

dpsRTUv2p22093Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 29 is set"
	::= { dpsRTUv2 22093 }

dpsRTUv2p23093Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 29 is cleared"
	::= { dpsRTUv2 23093 }

dpsRTUv2p22094Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 30 is set"
	::= { dpsRTUv2 22094 }

dpsRTUv2p23094Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 30 is cleared"
	::= { dpsRTUv2 23094 }

dpsRTUv2p22095Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 31 is set"
	::= { dpsRTUv2 22095 }

dpsRTUv2p23095Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 31 is cleared"
	::= { dpsRTUv2 23095 }

dpsRTUv2p22096Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 32 is set"
	::= { dpsRTUv2 22096 }

dpsRTUv2p23096Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 32 is cleared"
	::= { dpsRTUv2 23096 }

dpsRTUv2p22097Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 33 is set"
	::= { dpsRTUv2 22097 }

dpsRTUv2p23097Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 33 is cleared"
	::= { dpsRTUv2 23097 }

dpsRTUv2p22098Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 34 is set"
	::= { dpsRTUv2 22098 }

dpsRTUv2p23098Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 34 is cleared"
	::= { dpsRTUv2 23098 }

dpsRTUv2p22099Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 35 is set"
	::= { dpsRTUv2 22099 }

dpsRTUv2p23099Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 35 is cleared"
	::= { dpsRTUv2 23099 }

dpsRTUv2p22100Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 36 is set"
	::= { dpsRTUv2 22100 }

dpsRTUv2p23100Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 36 is cleared"
	::= { dpsRTUv2 23100 }

dpsRTUv2p22101Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 37 is set"
	::= { dpsRTUv2 22101 }

dpsRTUv2p23101Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 37 is cleared"
	::= { dpsRTUv2 23101 }

dpsRTUv2p22102Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 38 is set"
	::= { dpsRTUv2 22102 }

dpsRTUv2p23102Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 38 is cleared"
	::= { dpsRTUv2 23102 }

dpsRTUv2p22103Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 39 is set"
	::= { dpsRTUv2 22103 }

dpsRTUv2p23103Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 39 is cleared"
	::= { dpsRTUv2 23103 }

dpsRTUv2p22104Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 40 is set"
	::= { dpsRTUv2 22104 }

dpsRTUv2p23104Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 40 is cleared"
	::= { dpsRTUv2 23104 }

dpsRTUv2p22105Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 41 is set"
	::= { dpsRTUv2 22105 }

dpsRTUv2p23105Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 41 is cleared"
	::= { dpsRTUv2 23105 }

dpsRTUv2p22106Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 42 is set"
	::= { dpsRTUv2 22106 }

dpsRTUv2p23106Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 42 is cleared"
	::= { dpsRTUv2 23106 }

dpsRTUv2p22107Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 43 is set"
	::= { dpsRTUv2 22107 }

dpsRTUv2p23107Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 43 is cleared"
	::= { dpsRTUv2 23107 }

dpsRTUv2p22108Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 44 is set"
	::= { dpsRTUv2 22108 }

dpsRTUv2p23108Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 44 is cleared"
	::= { dpsRTUv2 23108 }

dpsRTUv2p22109Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 45 is set"
	::= { dpsRTUv2 22109 }

dpsRTUv2p23109Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 45 is cleared"
	::= { dpsRTUv2 23109 }

dpsRTUv2p22110Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 46 is set"
	::= { dpsRTUv2 22110 }

dpsRTUv2p23110Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 46 is cleared"
	::= { dpsRTUv2 23110 }

dpsRTUv2p22111Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 47 is set"
	::= { dpsRTUv2 22111 }

dpsRTUv2p23111Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 47 is cleared"
	::= { dpsRTUv2 23111 }

dpsRTUv2p22112Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 48 is set"
	::= { dpsRTUv2 22112 }

dpsRTUv2p23112Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 48 is cleared"
	::= { dpsRTUv2 23112 }

dpsRTUv2p22113Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 49 is set"
	::= { dpsRTUv2 22113 }

dpsRTUv2p23113Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 49 is cleared"
	::= { dpsRTUv2 23113 }

dpsRTUv2p22114Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 50 is set"
	::= { dpsRTUv2 22114 }

dpsRTUv2p23114Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 50 is cleared"
	::= { dpsRTUv2 23114 }

dpsRTUv2p22115Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 51 is set"
	::= { dpsRTUv2 22115 }

dpsRTUv2p23115Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 51 is cleared"
	::= { dpsRTUv2 23115 }

dpsRTUv2p22116Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 52 is set"
	::= { dpsRTUv2 22116 }

dpsRTUv2p23116Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 52 is cleared"
	::= { dpsRTUv2 23116 }

dpsRTUv2p22117Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 53 is set"
	::= { dpsRTUv2 22117 }

dpsRTUv2p23117Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 53 is cleared"
	::= { dpsRTUv2 23117 }

dpsRTUv2p22118Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 54 is set"
	::= { dpsRTUv2 22118 }

dpsRTUv2p23118Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 54 is cleared"
	::= { dpsRTUv2 23118 }

dpsRTUv2p22119Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 55 is set"
	::= { dpsRTUv2 22119 }

dpsRTUv2p23119Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 55 is cleared"
	::= { dpsRTUv2 23119 }

dpsRTUv2p22120Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 56 is set"
	::= { dpsRTUv2 22120 }

dpsRTUv2p23120Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 56 is cleared"
	::= { dpsRTUv2 23120 }

dpsRTUv2p22121Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 57 is set"
	::= { dpsRTUv2 22121 }

dpsRTUv2p23121Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 57 is cleared"
	::= { dpsRTUv2 23121 }

dpsRTUv2p22122Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 58 is set"
	::= { dpsRTUv2 22122 }

dpsRTUv2p23122Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 58 is cleared"
	::= { dpsRTUv2 23122 }

dpsRTUv2p22123Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 59 is set"
	::= { dpsRTUv2 22123 }

dpsRTUv2p23123Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 59 is cleared"
	::= { dpsRTUv2 23123 }

dpsRTUv2p22124Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 60 is set"
	::= { dpsRTUv2 22124 }

dpsRTUv2p23124Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 60 is cleared"
	::= { dpsRTUv2 23124 }

dpsRTUv2p22125Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 61 is set"
	::= { dpsRTUv2 22125 }

dpsRTUv2p23125Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 61 is cleared"
	::= { dpsRTUv2 23125 }

dpsRTUv2p22126Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 62 is set"
	::= { dpsRTUv2 22126 }

dpsRTUv2p23126Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 62 is cleared"
	::= { dpsRTUv2 23126 }

dpsRTUv2p22127Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 63 is set"
	::= { dpsRTUv2 22127 }

dpsRTUv2p23127Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 63 is cleared"
	::= { dpsRTUv2 23127 }

dpsRTUv2p22128Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 64 is set"
	::= { dpsRTUv2 22128 }

dpsRTUv2p23128Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 2 point 64 is cleared"
	::= { dpsRTUv2 23128 }

dpsRTUv2p22129Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 1 is set"
	::= { dpsRTUv2 22129 }

dpsRTUv2p23129Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 1 is cleared"
	::= { dpsRTUv2 23129 }

dpsRTUv2p22130Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 2 is set"
	::= { dpsRTUv2 22130 }

dpsRTUv2p23130Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 2 is cleared"
	::= { dpsRTUv2 23130 }

dpsRTUv2p22131Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 3 is set"
	::= { dpsRTUv2 22131 }

dpsRTUv2p23131Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 3 is cleared"
	::= { dpsRTUv2 23131 }

dpsRTUv2p22132Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 4 is set"
	::= { dpsRTUv2 22132 }

dpsRTUv2p23132Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 4 is cleared"
	::= { dpsRTUv2 23132 }

dpsRTUv2p22133Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 5 is set"
	::= { dpsRTUv2 22133 }

dpsRTUv2p23133Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 5 is cleared"
	::= { dpsRTUv2 23133 }

dpsRTUv2p22134Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 6 is set"
	::= { dpsRTUv2 22134 }

dpsRTUv2p23134Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 6 is cleared"
	::= { dpsRTUv2 23134 }

dpsRTUv2p22135Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 7 is set"
	::= { dpsRTUv2 22135 }

dpsRTUv2p23135Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 7 is cleared"
	::= { dpsRTUv2 23135 }

dpsRTUv2p22136Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 8 is set"
	::= { dpsRTUv2 22136 }

dpsRTUv2p23136Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 8 is cleared"
	::= { dpsRTUv2 23136 }

dpsRTUv2p22137Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 9 is set"
	::= { dpsRTUv2 22137 }

dpsRTUv2p23137Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 9 is cleared"
	::= { dpsRTUv2 23137 }

dpsRTUv2p22138Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 10 is set"
	::= { dpsRTUv2 22138 }

dpsRTUv2p23138Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 10 is cleared"
	::= { dpsRTUv2 23138 }

dpsRTUv2p22139Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 11 is set"
	::= { dpsRTUv2 22139 }

dpsRTUv2p23139Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 11 is cleared"
	::= { dpsRTUv2 23139 }

dpsRTUv2p22140Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 12 is set"
	::= { dpsRTUv2 22140 }

dpsRTUv2p23140Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 12 is cleared"
	::= { dpsRTUv2 23140 }

dpsRTUv2p22141Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 13 is set"
	::= { dpsRTUv2 22141 }

dpsRTUv2p23141Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 13 is cleared"
	::= { dpsRTUv2 23141 }

dpsRTUv2p22142Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 14 is set"
	::= { dpsRTUv2 22142 }

dpsRTUv2p23142Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 14 is cleared"
	::= { dpsRTUv2 23142 }

dpsRTUv2p22143Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 15 is set"
	::= { dpsRTUv2 22143 }

dpsRTUv2p23143Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 15 is cleared"
	::= { dpsRTUv2 23143 }

dpsRTUv2p22144Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 16 is set"
	::= { dpsRTUv2 22144 }

dpsRTUv2p23144Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 16 is cleared"
	::= { dpsRTUv2 23144 }

dpsRTUv2p22145Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 17 is set"
	::= { dpsRTUv2 22145 }

dpsRTUv2p23145Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 17 is cleared"
	::= { dpsRTUv2 23145 }

dpsRTUv2p22146Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 18 is set"
	::= { dpsRTUv2 22146 }

dpsRTUv2p23146Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 18 is cleared"
	::= { dpsRTUv2 23146 }

dpsRTUv2p22147Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 19 is set"
	::= { dpsRTUv2 22147 }

dpsRTUv2p23147Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 19 is cleared"
	::= { dpsRTUv2 23147 }

dpsRTUv2p22148Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 20 is set"
	::= { dpsRTUv2 22148 }

dpsRTUv2p23148Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 20 is cleared"
	::= { dpsRTUv2 23148 }

dpsRTUv2p22149Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 21 is set"
	::= { dpsRTUv2 22149 }

dpsRTUv2p23149Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 21 is cleared"
	::= { dpsRTUv2 23149 }

dpsRTUv2p22150Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 22 is set"
	::= { dpsRTUv2 22150 }

dpsRTUv2p23150Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 22 is cleared"
	::= { dpsRTUv2 23150 }

dpsRTUv2p22151Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 23 is set"
	::= { dpsRTUv2 22151 }

dpsRTUv2p23151Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 23 is cleared"
	::= { dpsRTUv2 23151 }

dpsRTUv2p22152Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 24 is set"
	::= { dpsRTUv2 22152 }

dpsRTUv2p23152Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 24 is cleared"
	::= { dpsRTUv2 23152 }

dpsRTUv2p22153Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 25 is set"
	::= { dpsRTUv2 22153 }

dpsRTUv2p23153Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 25 is cleared"
	::= { dpsRTUv2 23153 }

dpsRTUv2p22154Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 26 is set"
	::= { dpsRTUv2 22154 }

dpsRTUv2p23154Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 26 is cleared"
	::= { dpsRTUv2 23154 }

dpsRTUv2p22155Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 27 is set"
	::= { dpsRTUv2 22155 }

dpsRTUv2p23155Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 27 is cleared"
	::= { dpsRTUv2 23155 }

dpsRTUv2p22156Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 28 is set"
	::= { dpsRTUv2 22156 }

dpsRTUv2p23156Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 28 is cleared"
	::= { dpsRTUv2 23156 }

dpsRTUv2p22157Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 29 is set"
	::= { dpsRTUv2 22157 }

dpsRTUv2p23157Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 29 is cleared"
	::= { dpsRTUv2 23157 }

dpsRTUv2p22158Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 30 is set"
	::= { dpsRTUv2 22158 }

dpsRTUv2p23158Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 30 is cleared"
	::= { dpsRTUv2 23158 }

dpsRTUv2p22159Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 31 is set"
	::= { dpsRTUv2 22159 }

dpsRTUv2p23159Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 31 is cleared"
	::= { dpsRTUv2 23159 }

dpsRTUv2p22160Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 32 is set"
	::= { dpsRTUv2 22160 }

dpsRTUv2p23160Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 32 is cleared"
	::= { dpsRTUv2 23160 }

dpsRTUv2p22161Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 33 is set"
	::= { dpsRTUv2 22161 }

dpsRTUv2p23161Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 33 is cleared"
	::= { dpsRTUv2 23161 }

dpsRTUv2p22162Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 34 is set"
	::= { dpsRTUv2 22162 }

dpsRTUv2p23162Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 34 is cleared"
	::= { dpsRTUv2 23162 }

dpsRTUv2p22163Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 35 is set"
	::= { dpsRTUv2 22163 }

dpsRTUv2p23163Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 35 is cleared"
	::= { dpsRTUv2 23163 }

dpsRTUv2p22164Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 36 is set"
	::= { dpsRTUv2 22164 }

dpsRTUv2p23164Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 36 is cleared"
	::= { dpsRTUv2 23164 }

dpsRTUv2p22165Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 37 is set"
	::= { dpsRTUv2 22165 }

dpsRTUv2p23165Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 37 is cleared"
	::= { dpsRTUv2 23165 }

dpsRTUv2p22166Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 38 is set"
	::= { dpsRTUv2 22166 }

dpsRTUv2p23166Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 38 is cleared"
	::= { dpsRTUv2 23166 }

dpsRTUv2p22167Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 39 is set"
	::= { dpsRTUv2 22167 }

dpsRTUv2p23167Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 39 is cleared"
	::= { dpsRTUv2 23167 }

dpsRTUv2p22168Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 40 is set"
	::= { dpsRTUv2 22168 }

dpsRTUv2p23168Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 40 is cleared"
	::= { dpsRTUv2 23168 }

dpsRTUv2p22169Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 41 is set"
	::= { dpsRTUv2 22169 }

dpsRTUv2p23169Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 41 is cleared"
	::= { dpsRTUv2 23169 }

dpsRTUv2p22170Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 42 is set"
	::= { dpsRTUv2 22170 }

dpsRTUv2p23170Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 42 is cleared"
	::= { dpsRTUv2 23170 }

dpsRTUv2p22171Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 43 is set"
	::= { dpsRTUv2 22171 }

dpsRTUv2p23171Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 43 is cleared"
	::= { dpsRTUv2 23171 }

dpsRTUv2p22172Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 44 is set"
	::= { dpsRTUv2 22172 }

dpsRTUv2p23172Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 44 is cleared"
	::= { dpsRTUv2 23172 }

dpsRTUv2p22173Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 45 is set"
	::= { dpsRTUv2 22173 }

dpsRTUv2p23173Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 45 is cleared"
	::= { dpsRTUv2 23173 }

dpsRTUv2p22174Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 46 is set"
	::= { dpsRTUv2 22174 }

dpsRTUv2p23174Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 46 is cleared"
	::= { dpsRTUv2 23174 }

dpsRTUv2p22175Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 47 is set"
	::= { dpsRTUv2 22175 }

dpsRTUv2p23175Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 47 is cleared"
	::= { dpsRTUv2 23175 }

dpsRTUv2p22176Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 48 is set"
	::= { dpsRTUv2 22176 }

dpsRTUv2p23176Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 48 is cleared"
	::= { dpsRTUv2 23176 }

dpsRTUv2p22177Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 49 is set"
	::= { dpsRTUv2 22177 }

dpsRTUv2p23177Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 49 is cleared"
	::= { dpsRTUv2 23177 }

dpsRTUv2p22178Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 50 is set"
	::= { dpsRTUv2 22178 }

dpsRTUv2p23178Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 50 is cleared"
	::= { dpsRTUv2 23178 }

dpsRTUv2p22179Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 51 is set"
	::= { dpsRTUv2 22179 }

dpsRTUv2p23179Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 51 is cleared"
	::= { dpsRTUv2 23179 }

dpsRTUv2p22180Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 52 is set"
	::= { dpsRTUv2 22180 }

dpsRTUv2p23180Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 52 is cleared"
	::= { dpsRTUv2 23180 }

dpsRTUv2p22181Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 53 is set"
	::= { dpsRTUv2 22181 }

dpsRTUv2p23181Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 53 is cleared"
	::= { dpsRTUv2 23181 }

dpsRTUv2p22182Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 54 is set"
	::= { dpsRTUv2 22182 }

dpsRTUv2p23182Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 54 is cleared"
	::= { dpsRTUv2 23182 }

dpsRTUv2p22183Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 55 is set"
	::= { dpsRTUv2 22183 }

dpsRTUv2p23183Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 55 is cleared"
	::= { dpsRTUv2 23183 }

dpsRTUv2p22184Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 56 is set"
	::= { dpsRTUv2 22184 }

dpsRTUv2p23184Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 56 is cleared"
	::= { dpsRTUv2 23184 }

dpsRTUv2p22185Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 57 is set"
	::= { dpsRTUv2 22185 }

dpsRTUv2p23185Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 57 is cleared"
	::= { dpsRTUv2 23185 }

dpsRTUv2p22186Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 58 is set"
	::= { dpsRTUv2 22186 }

dpsRTUv2p23186Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 58 is cleared"
	::= { dpsRTUv2 23186 }

dpsRTUv2p22187Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 59 is set"
	::= { dpsRTUv2 22187 }

dpsRTUv2p23187Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 59 is cleared"
	::= { dpsRTUv2 23187 }

dpsRTUv2p22188Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 60 is set"
	::= { dpsRTUv2 22188 }

dpsRTUv2p23188Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 60 is cleared"
	::= { dpsRTUv2 23188 }

dpsRTUv2p22189Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 61 is set"
	::= { dpsRTUv2 22189 }

dpsRTUv2p23189Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 61 is cleared"
	::= { dpsRTUv2 23189 }

dpsRTUv2p22190Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 62 is set"
	::= { dpsRTUv2 22190 }

dpsRTUv2p23190Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 62 is cleared"
	::= { dpsRTUv2 23190 }

dpsRTUv2p22191Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 63 is set"
	::= { dpsRTUv2 22191 }

dpsRTUv2p23191Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 63 is cleared"
	::= { dpsRTUv2 23191 }

dpsRTUv2p22192Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 64 is set"
	::= { dpsRTUv2 22192 }

dpsRTUv2p23192Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 3 point 64 is cleared"
	::= { dpsRTUv2 23192 }

dpsRTUv2p22193Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 1 is set"
	::= { dpsRTUv2 22193 }

dpsRTUv2p23193Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 1 is cleared"
	::= { dpsRTUv2 23193 }

dpsRTUv2p22194Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 2 is set"
	::= { dpsRTUv2 22194 }

dpsRTUv2p23194Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 2 is cleared"
	::= { dpsRTUv2 23194 }

dpsRTUv2p22195Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 3 is set"
	::= { dpsRTUv2 22195 }

dpsRTUv2p23195Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 3 is cleared"
	::= { dpsRTUv2 23195 }

dpsRTUv2p22196Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 4 is set"
	::= { dpsRTUv2 22196 }

dpsRTUv2p23196Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 4 is cleared"
	::= { dpsRTUv2 23196 }

dpsRTUv2p22197Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 5 is set"
	::= { dpsRTUv2 22197 }

dpsRTUv2p23197Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 5 is cleared"
	::= { dpsRTUv2 23197 }

dpsRTUv2p22198Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 6 is set"
	::= { dpsRTUv2 22198 }

dpsRTUv2p23198Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 6 is cleared"
	::= { dpsRTUv2 23198 }

dpsRTUv2p22199Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 7 is set"
	::= { dpsRTUv2 22199 }

dpsRTUv2p23199Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 7 is cleared"
	::= { dpsRTUv2 23199 }

dpsRTUv2p22200Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 8 is set"
	::= { dpsRTUv2 22200 }

dpsRTUv2p23200Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 8 is cleared"
	::= { dpsRTUv2 23200 }

dpsRTUv2p22201Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 9 is set"
	::= { dpsRTUv2 22201 }

dpsRTUv2p23201Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 9 is cleared"
	::= { dpsRTUv2 23201 }

dpsRTUv2p22202Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 10 is set"
	::= { dpsRTUv2 22202 }

dpsRTUv2p23202Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 10 is cleared"
	::= { dpsRTUv2 23202 }

dpsRTUv2p22203Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 11 is set"
	::= { dpsRTUv2 22203 }

dpsRTUv2p23203Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 11 is cleared"
	::= { dpsRTUv2 23203 }

dpsRTUv2p22204Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 12 is set"
	::= { dpsRTUv2 22204 }

dpsRTUv2p23204Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 12 is cleared"
	::= { dpsRTUv2 23204 }

dpsRTUv2p22205Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 13 is set"
	::= { dpsRTUv2 22205 }

dpsRTUv2p23205Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 13 is cleared"
	::= { dpsRTUv2 23205 }

dpsRTUv2p22206Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 14 is set"
	::= { dpsRTUv2 22206 }

dpsRTUv2p23206Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 14 is cleared"
	::= { dpsRTUv2 23206 }

dpsRTUv2p22207Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 15 is set"
	::= { dpsRTUv2 22207 }

dpsRTUv2p23207Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 15 is cleared"
	::= { dpsRTUv2 23207 }

dpsRTUv2p22208Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 16 is set"
	::= { dpsRTUv2 22208 }

dpsRTUv2p23208Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 16 is cleared"
	::= { dpsRTUv2 23208 }

dpsRTUv2p22209Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 17 is set"
	::= { dpsRTUv2 22209 }

dpsRTUv2p23209Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 17 is cleared"
	::= { dpsRTUv2 23209 }

dpsRTUv2p22210Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 18 is set"
	::= { dpsRTUv2 22210 }

dpsRTUv2p23210Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 18 is cleared"
	::= { dpsRTUv2 23210 }

dpsRTUv2p22211Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 19 is set"
	::= { dpsRTUv2 22211 }

dpsRTUv2p23211Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 19 is cleared"
	::= { dpsRTUv2 23211 }

dpsRTUv2p22212Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 20 is set"
	::= { dpsRTUv2 22212 }

dpsRTUv2p23212Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 20 is cleared"
	::= { dpsRTUv2 23212 }

dpsRTUv2p22213Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 21 is set"
	::= { dpsRTUv2 22213 }

dpsRTUv2p23213Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 21 is cleared"
	::= { dpsRTUv2 23213 }

dpsRTUv2p22214Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 22 is set"
	::= { dpsRTUv2 22214 }

dpsRTUv2p23214Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 22 is cleared"
	::= { dpsRTUv2 23214 }

dpsRTUv2p22215Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 23 is set"
	::= { dpsRTUv2 22215 }

dpsRTUv2p23215Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 23 is cleared"
	::= { dpsRTUv2 23215 }

dpsRTUv2p22216Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 24 is set"
	::= { dpsRTUv2 22216 }

dpsRTUv2p23216Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 24 is cleared"
	::= { dpsRTUv2 23216 }

dpsRTUv2p22217Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 25 is set"
	::= { dpsRTUv2 22217 }

dpsRTUv2p23217Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 25 is cleared"
	::= { dpsRTUv2 23217 }

dpsRTUv2p22218Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 26 is set"
	::= { dpsRTUv2 22218 }

dpsRTUv2p23218Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 26 is cleared"
	::= { dpsRTUv2 23218 }

dpsRTUv2p22219Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 27 is set"
	::= { dpsRTUv2 22219 }

dpsRTUv2p23219Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 27 is cleared"
	::= { dpsRTUv2 23219 }

dpsRTUv2p22220Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 28 is set"
	::= { dpsRTUv2 22220 }

dpsRTUv2p23220Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 28 is cleared"
	::= { dpsRTUv2 23220 }

dpsRTUv2p22221Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 29 is set"
	::= { dpsRTUv2 22221 }

dpsRTUv2p23221Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 29 is cleared"
	::= { dpsRTUv2 23221 }

dpsRTUv2p22222Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 30 is set"
	::= { dpsRTUv2 22222 }

dpsRTUv2p23222Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 30 is cleared"
	::= { dpsRTUv2 23222 }

dpsRTUv2p22223Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 31 is set"
	::= { dpsRTUv2 22223 }

dpsRTUv2p23223Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 31 is cleared"
	::= { dpsRTUv2 23223 }

dpsRTUv2p22224Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 32 is set"
	::= { dpsRTUv2 22224 }

dpsRTUv2p23224Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 32 is cleared"
	::= { dpsRTUv2 23224 }

dpsRTUv2p22225Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 33 is set"
	::= { dpsRTUv2 22225 }

dpsRTUv2p23225Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 33 is cleared"
	::= { dpsRTUv2 23225 }

dpsRTUv2p22226Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 34 is set"
	::= { dpsRTUv2 22226 }

dpsRTUv2p23226Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 34 is cleared"
	::= { dpsRTUv2 23226 }

dpsRTUv2p22227Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 35 is set"
	::= { dpsRTUv2 22227 }

dpsRTUv2p23227Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 35 is cleared"
	::= { dpsRTUv2 23227 }

dpsRTUv2p22228Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 36 is set"
	::= { dpsRTUv2 22228 }

dpsRTUv2p23228Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 36 is cleared"
	::= { dpsRTUv2 23228 }

dpsRTUv2p22229Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 37 is set"
	::= { dpsRTUv2 22229 }

dpsRTUv2p23229Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 37 is cleared"
	::= { dpsRTUv2 23229 }

dpsRTUv2p22230Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 38 is set"
	::= { dpsRTUv2 22230 }

dpsRTUv2p23230Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 38 is cleared"
	::= { dpsRTUv2 23230 }

dpsRTUv2p22231Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 39 is set"
	::= { dpsRTUv2 22231 }

dpsRTUv2p23231Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 39 is cleared"
	::= { dpsRTUv2 23231 }

dpsRTUv2p22232Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 40 is set"
	::= { dpsRTUv2 22232 }

dpsRTUv2p23232Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 40 is cleared"
	::= { dpsRTUv2 23232 }

dpsRTUv2p22233Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 41 is set"
	::= { dpsRTUv2 22233 }

dpsRTUv2p23233Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 41 is cleared"
	::= { dpsRTUv2 23233 }

dpsRTUv2p22234Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 42 is set"
	::= { dpsRTUv2 22234 }

dpsRTUv2p23234Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 42 is cleared"
	::= { dpsRTUv2 23234 }

dpsRTUv2p22235Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 43 is set"
	::= { dpsRTUv2 22235 }

dpsRTUv2p23235Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 43 is cleared"
	::= { dpsRTUv2 23235 }

dpsRTUv2p22236Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 44 is set"
	::= { dpsRTUv2 22236 }

dpsRTUv2p23236Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 44 is cleared"
	::= { dpsRTUv2 23236 }

dpsRTUv2p22237Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 45 is set"
	::= { dpsRTUv2 22237 }

dpsRTUv2p23237Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 45 is cleared"
	::= { dpsRTUv2 23237 }

dpsRTUv2p22238Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 46 is set"
	::= { dpsRTUv2 22238 }

dpsRTUv2p23238Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 46 is cleared"
	::= { dpsRTUv2 23238 }

dpsRTUv2p22239Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 47 is set"
	::= { dpsRTUv2 22239 }

dpsRTUv2p23239Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 47 is cleared"
	::= { dpsRTUv2 23239 }

dpsRTUv2p22240Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 48 is set"
	::= { dpsRTUv2 22240 }

dpsRTUv2p23240Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 48 is cleared"
	::= { dpsRTUv2 23240 }

dpsRTUv2p22241Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 49 is set"
	::= { dpsRTUv2 22241 }

dpsRTUv2p23241Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 49 is cleared"
	::= { dpsRTUv2 23241 }

dpsRTUv2p22242Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 50 is set"
	::= { dpsRTUv2 22242 }

dpsRTUv2p23242Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 50 is cleared"
	::= { dpsRTUv2 23242 }

dpsRTUv2p22243Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 51 is set"
	::= { dpsRTUv2 22243 }

dpsRTUv2p23243Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 51 is cleared"
	::= { dpsRTUv2 23243 }

dpsRTUv2p22244Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 52 is set"
	::= { dpsRTUv2 22244 }

dpsRTUv2p23244Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 52 is cleared"
	::= { dpsRTUv2 23244 }

dpsRTUv2p22245Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 53 is set"
	::= { dpsRTUv2 22245 }

dpsRTUv2p23245Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 53 is cleared"
	::= { dpsRTUv2 23245 }

dpsRTUv2p22246Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 54 is set"
	::= { dpsRTUv2 22246 }

dpsRTUv2p23246Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 54 is cleared"
	::= { dpsRTUv2 23246 }

dpsRTUv2p22247Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 55 is set"
	::= { dpsRTUv2 22247 }

dpsRTUv2p23247Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 55 is cleared"
	::= { dpsRTUv2 23247 }

dpsRTUv2p22248Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 56 is set"
	::= { dpsRTUv2 22248 }

dpsRTUv2p23248Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 56 is cleared"
	::= { dpsRTUv2 23248 }

dpsRTUv2p22249Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 57 is set"
	::= { dpsRTUv2 22249 }

dpsRTUv2p23249Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 57 is cleared"
	::= { dpsRTUv2 23249 }

dpsRTUv2p22250Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 58 is set"
	::= { dpsRTUv2 22250 }

dpsRTUv2p23250Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 58 is cleared"
	::= { dpsRTUv2 23250 }

dpsRTUv2p22251Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 59 is set"
	::= { dpsRTUv2 22251 }

dpsRTUv2p23251Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 59 is cleared"
	::= { dpsRTUv2 23251 }

dpsRTUv2p22252Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 60 is set"
	::= { dpsRTUv2 22252 }

dpsRTUv2p23252Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 60 is cleared"
	::= { dpsRTUv2 23252 }

dpsRTUv2p22253Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 61 is set"
	::= { dpsRTUv2 22253 }

dpsRTUv2p23253Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 61 is cleared"
	::= { dpsRTUv2 23253 }

dpsRTUv2p22254Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 62 is set"
	::= { dpsRTUv2 22254 }

dpsRTUv2p23254Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 62 is cleared"
	::= { dpsRTUv2 23254 }

dpsRTUv2p22255Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 63 is set"
	::= { dpsRTUv2 22255 }

dpsRTUv2p23255Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 63 is cleared"
	::= { dpsRTUv2 23255 }

dpsRTUv2p22256Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 64 is set"
	::= { dpsRTUv2 22256 }

dpsRTUv2p23256Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 4 point 64 is cleared"
	::= { dpsRTUv2 23256 }

dpsRTUv2p22257Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 1 is set"
	::= { dpsRTUv2 22257 }

dpsRTUv2p23257Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 1 is cleared"
	::= { dpsRTUv2 23257 }

dpsRTUv2p22258Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 2 is set"
	::= { dpsRTUv2 22258 }

dpsRTUv2p23258Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 2 is cleared"
	::= { dpsRTUv2 23258 }

dpsRTUv2p22259Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 3 is set"
	::= { dpsRTUv2 22259 }

dpsRTUv2p23259Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 3 is cleared"
	::= { dpsRTUv2 23259 }

dpsRTUv2p22260Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 4 is set"
	::= { dpsRTUv2 22260 }

dpsRTUv2p23260Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 4 is cleared"
	::= { dpsRTUv2 23260 }

dpsRTUv2p22261Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 5 is set"
	::= { dpsRTUv2 22261 }

dpsRTUv2p23261Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 5 is cleared"
	::= { dpsRTUv2 23261 }

dpsRTUv2p22262Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 6 is set"
	::= { dpsRTUv2 22262 }

dpsRTUv2p23262Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 6 is cleared"
	::= { dpsRTUv2 23262 }

dpsRTUv2p22263Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 7 is set"
	::= { dpsRTUv2 22263 }

dpsRTUv2p23263Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 7 is cleared"
	::= { dpsRTUv2 23263 }

dpsRTUv2p22264Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 8 is set"
	::= { dpsRTUv2 22264 }

dpsRTUv2p23264Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 8 is cleared"
	::= { dpsRTUv2 23264 }

dpsRTUv2p22265Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 9 is set"
	::= { dpsRTUv2 22265 }

dpsRTUv2p23265Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 9 is cleared"
	::= { dpsRTUv2 23265 }

dpsRTUv2p22266Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 10 is set"
	::= { dpsRTUv2 22266 }

dpsRTUv2p23266Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 10 is cleared"
	::= { dpsRTUv2 23266 }

dpsRTUv2p22267Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 11 is set"
	::= { dpsRTUv2 22267 }

dpsRTUv2p23267Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 11 is cleared"
	::= { dpsRTUv2 23267 }

dpsRTUv2p22268Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 12 is set"
	::= { dpsRTUv2 22268 }

dpsRTUv2p23268Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 12 is cleared"
	::= { dpsRTUv2 23268 }

dpsRTUv2p22269Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 13 is set"
	::= { dpsRTUv2 22269 }

dpsRTUv2p23269Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 13 is cleared"
	::= { dpsRTUv2 23269 }

dpsRTUv2p22270Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 14 is set"
	::= { dpsRTUv2 22270 }

dpsRTUv2p23270Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 14 is cleared"
	::= { dpsRTUv2 23270 }

dpsRTUv2p22271Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 15 is set"
	::= { dpsRTUv2 22271 }

dpsRTUv2p23271Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 15 is cleared"
	::= { dpsRTUv2 23271 }

dpsRTUv2p22272Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 16 is set"
	::= { dpsRTUv2 22272 }

dpsRTUv2p23272Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 16 is cleared"
	::= { dpsRTUv2 23272 }

dpsRTUv2p22273Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 17 is set"
	::= { dpsRTUv2 22273 }

dpsRTUv2p23273Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 17 is cleared"
	::= { dpsRTUv2 23273 }

dpsRTUv2p22274Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 18 is set"
	::= { dpsRTUv2 22274 }

dpsRTUv2p23274Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 18 is cleared"
	::= { dpsRTUv2 23274 }

dpsRTUv2p22275Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 19 is set"
	::= { dpsRTUv2 22275 }

dpsRTUv2p23275Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 19 is cleared"
	::= { dpsRTUv2 23275 }

dpsRTUv2p22276Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 20 is set"
	::= { dpsRTUv2 22276 }

dpsRTUv2p23276Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 20 is cleared"
	::= { dpsRTUv2 23276 }

dpsRTUv2p22277Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 21 is set"
	::= { dpsRTUv2 22277 }

dpsRTUv2p23277Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 21 is cleared"
	::= { dpsRTUv2 23277 }

dpsRTUv2p22278Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 22 is set"
	::= { dpsRTUv2 22278 }

dpsRTUv2p23278Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 22 is cleared"
	::= { dpsRTUv2 23278 }

dpsRTUv2p22279Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 23 is set"
	::= { dpsRTUv2 22279 }

dpsRTUv2p23279Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 23 is cleared"
	::= { dpsRTUv2 23279 }

dpsRTUv2p22280Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 24 is set"
	::= { dpsRTUv2 22280 }

dpsRTUv2p23280Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 24 is cleared"
	::= { dpsRTUv2 23280 }

dpsRTUv2p22281Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 25 is set"
	::= { dpsRTUv2 22281 }

dpsRTUv2p23281Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 25 is cleared"
	::= { dpsRTUv2 23281 }

dpsRTUv2p22282Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 26 is set"
	::= { dpsRTUv2 22282 }

dpsRTUv2p23282Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 26 is cleared"
	::= { dpsRTUv2 23282 }

dpsRTUv2p22283Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 27 is set"
	::= { dpsRTUv2 22283 }

dpsRTUv2p23283Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 27 is cleared"
	::= { dpsRTUv2 23283 }

dpsRTUv2p22284Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 28 is set"
	::= { dpsRTUv2 22284 }

dpsRTUv2p23284Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 28 is cleared"
	::= { dpsRTUv2 23284 }

dpsRTUv2p22285Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 29 is set"
	::= { dpsRTUv2 22285 }

dpsRTUv2p23285Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 29 is cleared"
	::= { dpsRTUv2 23285 }

dpsRTUv2p22286Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 30 is set"
	::= { dpsRTUv2 22286 }

dpsRTUv2p23286Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 30 is cleared"
	::= { dpsRTUv2 23286 }

dpsRTUv2p22287Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 31 is set"
	::= { dpsRTUv2 22287 }

dpsRTUv2p23287Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 31 is cleared"
	::= { dpsRTUv2 23287 }

dpsRTUv2p22288Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 32 is set"
	::= { dpsRTUv2 22288 }

dpsRTUv2p23288Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 32 is cleared"
	::= { dpsRTUv2 23288 }

dpsRTUv2p22289Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 33 is set"
	::= { dpsRTUv2 22289 }

dpsRTUv2p23289Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 33 is cleared"
	::= { dpsRTUv2 23289 }

dpsRTUv2p22290Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 34 is set"
	::= { dpsRTUv2 22290 }

dpsRTUv2p23290Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 34 is cleared"
	::= { dpsRTUv2 23290 }

dpsRTUv2p22291Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 35 is set"
	::= { dpsRTUv2 22291 }

dpsRTUv2p23291Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 35 is cleared"
	::= { dpsRTUv2 23291 }

dpsRTUv2p22292Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 36 is set"
	::= { dpsRTUv2 22292 }

dpsRTUv2p23292Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 36 is cleared"
	::= { dpsRTUv2 23292 }

dpsRTUv2p22293Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 37 is set"
	::= { dpsRTUv2 22293 }

dpsRTUv2p23293Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 37 is cleared"
	::= { dpsRTUv2 23293 }

dpsRTUv2p22294Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 38 is set"
	::= { dpsRTUv2 22294 }

dpsRTUv2p23294Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 38 is cleared"
	::= { dpsRTUv2 23294 }

dpsRTUv2p22295Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 39 is set"
	::= { dpsRTUv2 22295 }

dpsRTUv2p23295Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 39 is cleared"
	::= { dpsRTUv2 23295 }

dpsRTUv2p22296Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 40 is set"
	::= { dpsRTUv2 22296 }

dpsRTUv2p23296Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 40 is cleared"
	::= { dpsRTUv2 23296 }

dpsRTUv2p22297Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 41 is set"
	::= { dpsRTUv2 22297 }

dpsRTUv2p23297Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 41 is cleared"
	::= { dpsRTUv2 23297 }

dpsRTUv2p22298Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 42 is set"
	::= { dpsRTUv2 22298 }

dpsRTUv2p23298Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 42 is cleared"
	::= { dpsRTUv2 23298 }

dpsRTUv2p22299Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 43 is set"
	::= { dpsRTUv2 22299 }

dpsRTUv2p23299Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 43 is cleared"
	::= { dpsRTUv2 23299 }

dpsRTUv2p22300Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 44 is set"
	::= { dpsRTUv2 22300 }

dpsRTUv2p23300Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 44 is cleared"
	::= { dpsRTUv2 23300 }

dpsRTUv2p22301Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 45 is set"
	::= { dpsRTUv2 22301 }

dpsRTUv2p23301Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 45 is cleared"
	::= { dpsRTUv2 23301 }

dpsRTUv2p22302Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 46 is set"
	::= { dpsRTUv2 22302 }

dpsRTUv2p23302Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 46 is cleared"
	::= { dpsRTUv2 23302 }

dpsRTUv2p22303Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 47 is set"
	::= { dpsRTUv2 22303 }

dpsRTUv2p23303Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 47 is cleared"
	::= { dpsRTUv2 23303 }

dpsRTUv2p22304Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 48 is set"
	::= { dpsRTUv2 22304 }

dpsRTUv2p23304Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 48 is cleared"
	::= { dpsRTUv2 23304 }

dpsRTUv2p22305Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 49 is set"
	::= { dpsRTUv2 22305 }

dpsRTUv2p23305Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 49 is cleared"
	::= { dpsRTUv2 23305 }

dpsRTUv2p22306Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 50 is set"
	::= { dpsRTUv2 22306 }

dpsRTUv2p23306Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 50 is cleared"
	::= { dpsRTUv2 23306 }

dpsRTUv2p22307Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 51 is set"
	::= { dpsRTUv2 22307 }

dpsRTUv2p23307Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 51 is cleared"
	::= { dpsRTUv2 23307 }

dpsRTUv2p22308Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 52 is set"
	::= { dpsRTUv2 22308 }

dpsRTUv2p23308Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 52 is cleared"
	::= { dpsRTUv2 23308 }

dpsRTUv2p22309Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 53 is set"
	::= { dpsRTUv2 22309 }

dpsRTUv2p23309Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 53 is cleared"
	::= { dpsRTUv2 23309 }

dpsRTUv2p22310Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 54 is set"
	::= { dpsRTUv2 22310 }

dpsRTUv2p23310Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 54 is cleared"
	::= { dpsRTUv2 23310 }

dpsRTUv2p22311Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 55 is set"
	::= { dpsRTUv2 22311 }

dpsRTUv2p23311Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 55 is cleared"
	::= { dpsRTUv2 23311 }

dpsRTUv2p22312Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 56 is set"
	::= { dpsRTUv2 22312 }

dpsRTUv2p23312Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 56 is cleared"
	::= { dpsRTUv2 23312 }

dpsRTUv2p22313Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 57 is set"
	::= { dpsRTUv2 22313 }

dpsRTUv2p23313Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 57 is cleared"
	::= { dpsRTUv2 23313 }

dpsRTUv2p22314Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 58 is set"
	::= { dpsRTUv2 22314 }

dpsRTUv2p23314Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 58 is cleared"
	::= { dpsRTUv2 23314 }

dpsRTUv2p22315Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 59 is set"
	::= { dpsRTUv2 22315 }

dpsRTUv2p23315Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 59 is cleared"
	::= { dpsRTUv2 23315 }

dpsRTUv2p22316Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 60 is set"
	::= { dpsRTUv2 22316 }

dpsRTUv2p23316Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 60 is cleared"
	::= { dpsRTUv2 23316 }

dpsRTUv2p22317Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 61 is set"
	::= { dpsRTUv2 22317 }

dpsRTUv2p23317Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 61 is cleared"
	::= { dpsRTUv2 23317 }

dpsRTUv2p22318Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 62 is set"
	::= { dpsRTUv2 22318 }

dpsRTUv2p23318Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 62 is cleared"
	::= { dpsRTUv2 23318 }

dpsRTUv2p22319Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 63 is set"
	::= { dpsRTUv2 22319 }

dpsRTUv2p23319Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 63 is cleared"
	::= { dpsRTUv2 23319 }

dpsRTUv2p22320Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 64 is set"
	::= { dpsRTUv2 22320 }

dpsRTUv2p23320Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 5 point 64 is cleared"
	::= { dpsRTUv2 23320 }

dpsRTUv2p22321Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 1 is set"
	::= { dpsRTUv2 22321 }

dpsRTUv2p23321Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 1 is cleared"
	::= { dpsRTUv2 23321 }

dpsRTUv2p22322Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 2 is set"
	::= { dpsRTUv2 22322 }

dpsRTUv2p23322Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 2 is cleared"
	::= { dpsRTUv2 23322 }

dpsRTUv2p22323Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 3 is set"
	::= { dpsRTUv2 22323 }

dpsRTUv2p23323Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 3 is cleared"
	::= { dpsRTUv2 23323 }

dpsRTUv2p22324Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 4 is set"
	::= { dpsRTUv2 22324 }

dpsRTUv2p23324Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 4 is cleared"
	::= { dpsRTUv2 23324 }

dpsRTUv2p22325Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 5 is set"
	::= { dpsRTUv2 22325 }

dpsRTUv2p23325Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 5 is cleared"
	::= { dpsRTUv2 23325 }

dpsRTUv2p22326Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 6 is set"
	::= { dpsRTUv2 22326 }

dpsRTUv2p23326Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 6 is cleared"
	::= { dpsRTUv2 23326 }

dpsRTUv2p22327Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 7 is set"
	::= { dpsRTUv2 22327 }

dpsRTUv2p23327Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 7 is cleared"
	::= { dpsRTUv2 23327 }

dpsRTUv2p22328Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 8 is set"
	::= { dpsRTUv2 22328 }

dpsRTUv2p23328Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 8 is cleared"
	::= { dpsRTUv2 23328 }

dpsRTUv2p22329Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 9 is set"
	::= { dpsRTUv2 22329 }

dpsRTUv2p23329Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 9 is cleared"
	::= { dpsRTUv2 23329 }

dpsRTUv2p22330Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 10 is set"
	::= { dpsRTUv2 22330 }

dpsRTUv2p23330Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 10 is cleared"
	::= { dpsRTUv2 23330 }

dpsRTUv2p22331Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 11 is set"
	::= { dpsRTUv2 22331 }

dpsRTUv2p23331Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 11 is cleared"
	::= { dpsRTUv2 23331 }

dpsRTUv2p22332Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 12 is set"
	::= { dpsRTUv2 22332 }

dpsRTUv2p23332Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 12 is cleared"
	::= { dpsRTUv2 23332 }

dpsRTUv2p22333Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 13 is set"
	::= { dpsRTUv2 22333 }

dpsRTUv2p23333Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 13 is cleared"
	::= { dpsRTUv2 23333 }

dpsRTUv2p22334Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 14 is set"
	::= { dpsRTUv2 22334 }

dpsRTUv2p23334Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 14 is cleared"
	::= { dpsRTUv2 23334 }

dpsRTUv2p22335Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 15 is set"
	::= { dpsRTUv2 22335 }

dpsRTUv2p23335Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 15 is cleared"
	::= { dpsRTUv2 23335 }

dpsRTUv2p22336Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 16 is set"
	::= { dpsRTUv2 22336 }

dpsRTUv2p23336Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 16 is cleared"
	::= { dpsRTUv2 23336 }

dpsRTUv2p22337Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 17 is set"
	::= { dpsRTUv2 22337 }

dpsRTUv2p23337Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 17 is cleared"
	::= { dpsRTUv2 23337 }

dpsRTUv2p22338Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 18 is set"
	::= { dpsRTUv2 22338 }

dpsRTUv2p23338Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 18 is cleared"
	::= { dpsRTUv2 23338 }

dpsRTUv2p22339Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 19 is set"
	::= { dpsRTUv2 22339 }

dpsRTUv2p23339Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 19 is cleared"
	::= { dpsRTUv2 23339 }

dpsRTUv2p22340Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 20 is set"
	::= { dpsRTUv2 22340 }

dpsRTUv2p23340Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 20 is cleared"
	::= { dpsRTUv2 23340 }

dpsRTUv2p22341Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 21 is set"
	::= { dpsRTUv2 22341 }

dpsRTUv2p23341Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 21 is cleared"
	::= { dpsRTUv2 23341 }

dpsRTUv2p22342Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 22 is set"
	::= { dpsRTUv2 22342 }

dpsRTUv2p23342Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 22 is cleared"
	::= { dpsRTUv2 23342 }

dpsRTUv2p22343Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 23 is set"
	::= { dpsRTUv2 22343 }

dpsRTUv2p23343Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 23 is cleared"
	::= { dpsRTUv2 23343 }

dpsRTUv2p22344Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 24 is set"
	::= { dpsRTUv2 22344 }

dpsRTUv2p23344Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 24 is cleared"
	::= { dpsRTUv2 23344 }

dpsRTUv2p22345Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 25 is set"
	::= { dpsRTUv2 22345 }

dpsRTUv2p23345Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 25 is cleared"
	::= { dpsRTUv2 23345 }

dpsRTUv2p22346Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 26 is set"
	::= { dpsRTUv2 22346 }

dpsRTUv2p23346Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 26 is cleared"
	::= { dpsRTUv2 23346 }

dpsRTUv2p22347Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 27 is set"
	::= { dpsRTUv2 22347 }

dpsRTUv2p23347Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 27 is cleared"
	::= { dpsRTUv2 23347 }

dpsRTUv2p22348Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 28 is set"
	::= { dpsRTUv2 22348 }

dpsRTUv2p23348Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 28 is cleared"
	::= { dpsRTUv2 23348 }

dpsRTUv2p22349Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 29 is set"
	::= { dpsRTUv2 22349 }

dpsRTUv2p23349Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 29 is cleared"
	::= { dpsRTUv2 23349 }

dpsRTUv2p22350Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 30 is set"
	::= { dpsRTUv2 22350 }

dpsRTUv2p23350Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 30 is cleared"
	::= { dpsRTUv2 23350 }

dpsRTUv2p22351Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 31 is set"
	::= { dpsRTUv2 22351 }

dpsRTUv2p23351Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 31 is cleared"
	::= { dpsRTUv2 23351 }

dpsRTUv2p22352Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 32 is set"
	::= { dpsRTUv2 22352 }

dpsRTUv2p23352Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 32 is cleared"
	::= { dpsRTUv2 23352 }

dpsRTUv2p22353Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 33 is set"
	::= { dpsRTUv2 22353 }

dpsRTUv2p23353Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 33 is cleared"
	::= { dpsRTUv2 23353 }

dpsRTUv2p22354Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 34 is set"
	::= { dpsRTUv2 22354 }

dpsRTUv2p23354Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 34 is cleared"
	::= { dpsRTUv2 23354 }

dpsRTUv2p22355Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 35 is set"
	::= { dpsRTUv2 22355 }

dpsRTUv2p23355Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 35 is cleared"
	::= { dpsRTUv2 23355 }

dpsRTUv2p22356Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 36 is set"
	::= { dpsRTUv2 22356 }

dpsRTUv2p23356Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 36 is cleared"
	::= { dpsRTUv2 23356 }

dpsRTUv2p22357Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 37 is set"
	::= { dpsRTUv2 22357 }

dpsRTUv2p23357Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 37 is cleared"
	::= { dpsRTUv2 23357 }

dpsRTUv2p22358Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 38 is set"
	::= { dpsRTUv2 22358 }

dpsRTUv2p23358Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 38 is cleared"
	::= { dpsRTUv2 23358 }

dpsRTUv2p22359Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 39 is set"
	::= { dpsRTUv2 22359 }

dpsRTUv2p23359Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 39 is cleared"
	::= { dpsRTUv2 23359 }

dpsRTUv2p22360Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 40 is set"
	::= { dpsRTUv2 22360 }

dpsRTUv2p23360Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 40 is cleared"
	::= { dpsRTUv2 23360 }

dpsRTUv2p22361Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 41 is set"
	::= { dpsRTUv2 22361 }

dpsRTUv2p23361Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 41 is cleared"
	::= { dpsRTUv2 23361 }

dpsRTUv2p22362Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 42 is set"
	::= { dpsRTUv2 22362 }

dpsRTUv2p23362Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 42 is cleared"
	::= { dpsRTUv2 23362 }

dpsRTUv2p22363Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 43 is set"
	::= { dpsRTUv2 22363 }

dpsRTUv2p23363Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 43 is cleared"
	::= { dpsRTUv2 23363 }

dpsRTUv2p22364Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 44 is set"
	::= { dpsRTUv2 22364 }

dpsRTUv2p23364Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 44 is cleared"
	::= { dpsRTUv2 23364 }

dpsRTUv2p22365Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 45 is set"
	::= { dpsRTUv2 22365 }

dpsRTUv2p23365Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 45 is cleared"
	::= { dpsRTUv2 23365 }

dpsRTUv2p22366Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 46 is set"
	::= { dpsRTUv2 22366 }

dpsRTUv2p23366Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 46 is cleared"
	::= { dpsRTUv2 23366 }

dpsRTUv2p22367Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 47 is set"
	::= { dpsRTUv2 22367 }

dpsRTUv2p23367Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 47 is cleared"
	::= { dpsRTUv2 23367 }

dpsRTUv2p22368Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 48 is set"
	::= { dpsRTUv2 22368 }

dpsRTUv2p23368Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 48 is cleared"
	::= { dpsRTUv2 23368 }

dpsRTUv2p22369Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 49 is set"
	::= { dpsRTUv2 22369 }

dpsRTUv2p23369Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 49 is cleared"
	::= { dpsRTUv2 23369 }

dpsRTUv2p22370Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 50 is set"
	::= { dpsRTUv2 22370 }

dpsRTUv2p23370Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 50 is cleared"
	::= { dpsRTUv2 23370 }

dpsRTUv2p22371Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 51 is set"
	::= { dpsRTUv2 22371 }

dpsRTUv2p23371Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 51 is cleared"
	::= { dpsRTUv2 23371 }

dpsRTUv2p22372Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 52 is set"
	::= { dpsRTUv2 22372 }

dpsRTUv2p23372Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 52 is cleared"
	::= { dpsRTUv2 23372 }

dpsRTUv2p22373Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 53 is set"
	::= { dpsRTUv2 22373 }

dpsRTUv2p23373Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 53 is cleared"
	::= { dpsRTUv2 23373 }

dpsRTUv2p22374Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 54 is set"
	::= { dpsRTUv2 22374 }

dpsRTUv2p23374Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 54 is cleared"
	::= { dpsRTUv2 23374 }

dpsRTUv2p22375Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 55 is set"
	::= { dpsRTUv2 22375 }

dpsRTUv2p23375Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 55 is cleared"
	::= { dpsRTUv2 23375 }

dpsRTUv2p22376Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 56 is set"
	::= { dpsRTUv2 22376 }

dpsRTUv2p23376Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 56 is cleared"
	::= { dpsRTUv2 23376 }

dpsRTUv2p22377Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 57 is set"
	::= { dpsRTUv2 22377 }

dpsRTUv2p23377Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 57 is cleared"
	::= { dpsRTUv2 23377 }

dpsRTUv2p22378Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 58 is set"
	::= { dpsRTUv2 22378 }

dpsRTUv2p23378Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 58 is cleared"
	::= { dpsRTUv2 23378 }

dpsRTUv2p22379Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 59 is set"
	::= { dpsRTUv2 22379 }

dpsRTUv2p23379Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 59 is cleared"
	::= { dpsRTUv2 23379 }

dpsRTUv2p22380Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 60 is set"
	::= { dpsRTUv2 22380 }

dpsRTUv2p23380Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 60 is cleared"
	::= { dpsRTUv2 23380 }

dpsRTUv2p22381Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 61 is set"
	::= { dpsRTUv2 22381 }

dpsRTUv2p23381Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 61 is cleared"
	::= { dpsRTUv2 23381 }

dpsRTUv2p22382Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 62 is set"
	::= { dpsRTUv2 22382 }

dpsRTUv2p23382Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 62 is cleared"
	::= { dpsRTUv2 23382 }

dpsRTUv2p22383Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 63 is set"
	::= { dpsRTUv2 22383 }

dpsRTUv2p23383Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 63 is cleared"
	::= { dpsRTUv2 23383 }

dpsRTUv2p22384Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 64 is set"
	::= { dpsRTUv2 22384 }

dpsRTUv2p23384Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 6 point 64 is cleared"
	::= { dpsRTUv2 23384 }

dpsRTUv2p22385Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 1 is set"
	::= { dpsRTUv2 22385 }

dpsRTUv2p23385Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 1 is cleared"
	::= { dpsRTUv2 23385 }

dpsRTUv2p22386Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 2 is set"
	::= { dpsRTUv2 22386 }

dpsRTUv2p23386Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 2 is cleared"
	::= { dpsRTUv2 23386 }

dpsRTUv2p22387Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 3 is set"
	::= { dpsRTUv2 22387 }

dpsRTUv2p23387Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 3 is cleared"
	::= { dpsRTUv2 23387 }

dpsRTUv2p22388Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 4 is set"
	::= { dpsRTUv2 22388 }

dpsRTUv2p23388Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 4 is cleared"
	::= { dpsRTUv2 23388 }

dpsRTUv2p22389Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 5 is set"
	::= { dpsRTUv2 22389 }

dpsRTUv2p23389Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 5 is cleared"
	::= { dpsRTUv2 23389 }

dpsRTUv2p22390Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 6 is set"
	::= { dpsRTUv2 22390 }

dpsRTUv2p23390Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 6 is cleared"
	::= { dpsRTUv2 23390 }

dpsRTUv2p22391Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 7 is set"
	::= { dpsRTUv2 22391 }

dpsRTUv2p23391Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 7 is cleared"
	::= { dpsRTUv2 23391 }

dpsRTUv2p22392Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 8 is set"
	::= { dpsRTUv2 22392 }

dpsRTUv2p23392Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 8 is cleared"
	::= { dpsRTUv2 23392 }

dpsRTUv2p22393Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 9 is set"
	::= { dpsRTUv2 22393 }

dpsRTUv2p23393Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 9 is cleared"
	::= { dpsRTUv2 23393 }

dpsRTUv2p22394Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 10 is set"
	::= { dpsRTUv2 22394 }

dpsRTUv2p23394Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 10 is cleared"
	::= { dpsRTUv2 23394 }

dpsRTUv2p22395Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 11 is set"
	::= { dpsRTUv2 22395 }

dpsRTUv2p23395Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 11 is cleared"
	::= { dpsRTUv2 23395 }

dpsRTUv2p22396Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 12 is set"
	::= { dpsRTUv2 22396 }

dpsRTUv2p23396Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 12 is cleared"
	::= { dpsRTUv2 23396 }

dpsRTUv2p22397Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 13 is set"
	::= { dpsRTUv2 22397 }

dpsRTUv2p23397Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 13 is cleared"
	::= { dpsRTUv2 23397 }

dpsRTUv2p22398Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 14 is set"
	::= { dpsRTUv2 22398 }

dpsRTUv2p23398Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 14 is cleared"
	::= { dpsRTUv2 23398 }

dpsRTUv2p22399Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 15 is set"
	::= { dpsRTUv2 22399 }

dpsRTUv2p23399Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 15 is cleared"
	::= { dpsRTUv2 23399 }

dpsRTUv2p22400Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 16 is set"
	::= { dpsRTUv2 22400 }

dpsRTUv2p23400Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 16 is cleared"
	::= { dpsRTUv2 23400 }

dpsRTUv2p22401Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 17 is set"
	::= { dpsRTUv2 22401 }

dpsRTUv2p23401Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 17 is cleared"
	::= { dpsRTUv2 23401 }

dpsRTUv2p22402Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 18 is set"
	::= { dpsRTUv2 22402 }

dpsRTUv2p23402Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 18 is cleared"
	::= { dpsRTUv2 23402 }

dpsRTUv2p22403Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 19 is set"
	::= { dpsRTUv2 22403 }

dpsRTUv2p23403Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 19 is cleared"
	::= { dpsRTUv2 23403 }

dpsRTUv2p22404Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 20 is set"
	::= { dpsRTUv2 22404 }

dpsRTUv2p23404Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 20 is cleared"
	::= { dpsRTUv2 23404 }

dpsRTUv2p22405Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 21 is set"
	::= { dpsRTUv2 22405 }

dpsRTUv2p23405Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 21 is cleared"
	::= { dpsRTUv2 23405 }

dpsRTUv2p22406Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 22 is set"
	::= { dpsRTUv2 22406 }

dpsRTUv2p23406Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 22 is cleared"
	::= { dpsRTUv2 23406 }

dpsRTUv2p22407Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 23 is set"
	::= { dpsRTUv2 22407 }

dpsRTUv2p23407Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 23 is cleared"
	::= { dpsRTUv2 23407 }

dpsRTUv2p22408Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 24 is set"
	::= { dpsRTUv2 22408 }

dpsRTUv2p23408Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 24 is cleared"
	::= { dpsRTUv2 23408 }

dpsRTUv2p22409Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 25 is set"
	::= { dpsRTUv2 22409 }

dpsRTUv2p23409Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 25 is cleared"
	::= { dpsRTUv2 23409 }

dpsRTUv2p22410Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 26 is set"
	::= { dpsRTUv2 22410 }

dpsRTUv2p23410Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 26 is cleared"
	::= { dpsRTUv2 23410 }

dpsRTUv2p22411Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 27 is set"
	::= { dpsRTUv2 22411 }

dpsRTUv2p23411Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 27 is cleared"
	::= { dpsRTUv2 23411 }

dpsRTUv2p22412Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 28 is set"
	::= { dpsRTUv2 22412 }

dpsRTUv2p23412Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 28 is cleared"
	::= { dpsRTUv2 23412 }

dpsRTUv2p22413Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 29 is set"
	::= { dpsRTUv2 22413 }

dpsRTUv2p23413Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 29 is cleared"
	::= { dpsRTUv2 23413 }

dpsRTUv2p22414Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 30 is set"
	::= { dpsRTUv2 22414 }

dpsRTUv2p23414Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 30 is cleared"
	::= { dpsRTUv2 23414 }

dpsRTUv2p22415Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 31 is set"
	::= { dpsRTUv2 22415 }

dpsRTUv2p23415Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 31 is cleared"
	::= { dpsRTUv2 23415 }

dpsRTUv2p22416Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 32 is set"
	::= { dpsRTUv2 22416 }

dpsRTUv2p23416Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 32 is cleared"
	::= { dpsRTUv2 23416 }

dpsRTUv2p22417Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 33 is set"
	::= { dpsRTUv2 22417 }

dpsRTUv2p23417Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 33 is cleared"
	::= { dpsRTUv2 23417 }

dpsRTUv2p22418Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 34 is set"
	::= { dpsRTUv2 22418 }

dpsRTUv2p23418Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 34 is cleared"
	::= { dpsRTUv2 23418 }

dpsRTUv2p22419Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 35 is set"
	::= { dpsRTUv2 22419 }

dpsRTUv2p23419Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 35 is cleared"
	::= { dpsRTUv2 23419 }

dpsRTUv2p22420Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 36 is set"
	::= { dpsRTUv2 22420 }

dpsRTUv2p23420Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 36 is cleared"
	::= { dpsRTUv2 23420 }

dpsRTUv2p22421Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 37 is set"
	::= { dpsRTUv2 22421 }

dpsRTUv2p23421Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 37 is cleared"
	::= { dpsRTUv2 23421 }

dpsRTUv2p22422Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 38 is set"
	::= { dpsRTUv2 22422 }

dpsRTUv2p23422Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 38 is cleared"
	::= { dpsRTUv2 23422 }

dpsRTUv2p22423Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 39 is set"
	::= { dpsRTUv2 22423 }

dpsRTUv2p23423Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 39 is cleared"
	::= { dpsRTUv2 23423 }

dpsRTUv2p22424Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 40 is set"
	::= { dpsRTUv2 22424 }

dpsRTUv2p23424Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 40 is cleared"
	::= { dpsRTUv2 23424 }

dpsRTUv2p22425Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 41 is set"
	::= { dpsRTUv2 22425 }

dpsRTUv2p23425Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 41 is cleared"
	::= { dpsRTUv2 23425 }

dpsRTUv2p22426Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 42 is set"
	::= { dpsRTUv2 22426 }

dpsRTUv2p23426Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 42 is cleared"
	::= { dpsRTUv2 23426 }

dpsRTUv2p22427Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 43 is set"
	::= { dpsRTUv2 22427 }

dpsRTUv2p23427Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 43 is cleared"
	::= { dpsRTUv2 23427 }

dpsRTUv2p22428Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 44 is set"
	::= { dpsRTUv2 22428 }

dpsRTUv2p23428Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 44 is cleared"
	::= { dpsRTUv2 23428 }

dpsRTUv2p22429Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 45 is set"
	::= { dpsRTUv2 22429 }

dpsRTUv2p23429Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 45 is cleared"
	::= { dpsRTUv2 23429 }

dpsRTUv2p22430Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 46 is set"
	::= { dpsRTUv2 22430 }

dpsRTUv2p23430Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 46 is cleared"
	::= { dpsRTUv2 23430 }

dpsRTUv2p22431Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 47 is set"
	::= { dpsRTUv2 22431 }

dpsRTUv2p23431Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 47 is cleared"
	::= { dpsRTUv2 23431 }

dpsRTUv2p22432Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 48 is set"
	::= { dpsRTUv2 22432 }

dpsRTUv2p23432Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 48 is cleared"
	::= { dpsRTUv2 23432 }

dpsRTUv2p22433Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 49 is set"
	::= { dpsRTUv2 22433 }

dpsRTUv2p23433Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 49 is cleared"
	::= { dpsRTUv2 23433 }

dpsRTUv2p22434Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 50 is set"
	::= { dpsRTUv2 22434 }

dpsRTUv2p23434Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 50 is cleared"
	::= { dpsRTUv2 23434 }

dpsRTUv2p22435Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 51 is set"
	::= { dpsRTUv2 22435 }

dpsRTUv2p23435Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 51 is cleared"
	::= { dpsRTUv2 23435 }

dpsRTUv2p22436Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 52 is set"
	::= { dpsRTUv2 22436 }

dpsRTUv2p23436Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 52 is cleared"
	::= { dpsRTUv2 23436 }

dpsRTUv2p22437Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 53 is set"
	::= { dpsRTUv2 22437 }

dpsRTUv2p23437Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 53 is cleared"
	::= { dpsRTUv2 23437 }

dpsRTUv2p22438Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 54 is set"
	::= { dpsRTUv2 22438 }

dpsRTUv2p23438Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 54 is cleared"
	::= { dpsRTUv2 23438 }

dpsRTUv2p22439Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 55 is set"
	::= { dpsRTUv2 22439 }

dpsRTUv2p23439Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 55 is cleared"
	::= { dpsRTUv2 23439 }

dpsRTUv2p22440Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 56 is set"
	::= { dpsRTUv2 22440 }

dpsRTUv2p23440Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 56 is cleared"
	::= { dpsRTUv2 23440 }

dpsRTUv2p22441Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 57 is set"
	::= { dpsRTUv2 22441 }

dpsRTUv2p23441Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 57 is cleared"
	::= { dpsRTUv2 23441 }

dpsRTUv2p22442Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 58 is set"
	::= { dpsRTUv2 22442 }

dpsRTUv2p23442Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 58 is cleared"
	::= { dpsRTUv2 23442 }

dpsRTUv2p22443Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 59 is set"
	::= { dpsRTUv2 22443 }

dpsRTUv2p23443Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 59 is cleared"
	::= { dpsRTUv2 23443 }

dpsRTUv2p22444Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 60 is set"
	::= { dpsRTUv2 22444 }

dpsRTUv2p23444Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 60 is cleared"
	::= { dpsRTUv2 23444 }

dpsRTUv2p22445Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 61 is set"
	::= { dpsRTUv2 22445 }

dpsRTUv2p23445Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 61 is cleared"
	::= { dpsRTUv2 23445 }

dpsRTUv2p22446Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 62 is set"
	::= { dpsRTUv2 22446 }

dpsRTUv2p23446Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 62 is cleared"
	::= { dpsRTUv2 23446 }

dpsRTUv2p22447Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 63 is set"
	::= { dpsRTUv2 22447 }

dpsRTUv2p23447Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 63 is cleared"
	::= { dpsRTUv2 23447 }

dpsRTUv2p22448Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 64 is set"
	::= { dpsRTUv2 22448 }

dpsRTUv2p23448Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 7 point 64 is cleared"
	::= { dpsRTUv2 23448 }

dpsRTUv2p22449Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 1 is set"
	::= { dpsRTUv2 22449 }

dpsRTUv2p23449Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 1 is cleared"
	::= { dpsRTUv2 23449 }

dpsRTUv2p22450Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 2 is set"
	::= { dpsRTUv2 22450 }

dpsRTUv2p23450Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 2 is cleared"
	::= { dpsRTUv2 23450 }

dpsRTUv2p22451Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 3 is set"
	::= { dpsRTUv2 22451 }

dpsRTUv2p23451Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 3 is cleared"
	::= { dpsRTUv2 23451 }

dpsRTUv2p22452Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 4 is set"
	::= { dpsRTUv2 22452 }

dpsRTUv2p23452Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 4 is cleared"
	::= { dpsRTUv2 23452 }

dpsRTUv2p22453Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 5 is set"
	::= { dpsRTUv2 22453 }

dpsRTUv2p23453Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 5 is cleared"
	::= { dpsRTUv2 23453 }

dpsRTUv2p22454Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 6 is set"
	::= { dpsRTUv2 22454 }

dpsRTUv2p23454Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 6 is cleared"
	::= { dpsRTUv2 23454 }

dpsRTUv2p22455Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 7 is set"
	::= { dpsRTUv2 22455 }

dpsRTUv2p23455Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 7 is cleared"
	::= { dpsRTUv2 23455 }

dpsRTUv2p22456Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 8 is set"
	::= { dpsRTUv2 22456 }

dpsRTUv2p23456Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 8 is cleared"
	::= { dpsRTUv2 23456 }

dpsRTUv2p22457Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 9 is set"
	::= { dpsRTUv2 22457 }

dpsRTUv2p23457Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 9 is cleared"
	::= { dpsRTUv2 23457 }

dpsRTUv2p22458Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 10 is set"
	::= { dpsRTUv2 22458 }

dpsRTUv2p23458Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 10 is cleared"
	::= { dpsRTUv2 23458 }

dpsRTUv2p22459Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 11 is set"
	::= { dpsRTUv2 22459 }

dpsRTUv2p23459Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 11 is cleared"
	::= { dpsRTUv2 23459 }

dpsRTUv2p22460Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 12 is set"
	::= { dpsRTUv2 22460 }

dpsRTUv2p23460Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 12 is cleared"
	::= { dpsRTUv2 23460 }

dpsRTUv2p22461Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 13 is set"
	::= { dpsRTUv2 22461 }

dpsRTUv2p23461Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 13 is cleared"
	::= { dpsRTUv2 23461 }

dpsRTUv2p22462Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 14 is set"
	::= { dpsRTUv2 22462 }

dpsRTUv2p23462Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 14 is cleared"
	::= { dpsRTUv2 23462 }

dpsRTUv2p22463Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 15 is set"
	::= { dpsRTUv2 22463 }

dpsRTUv2p23463Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 15 is cleared"
	::= { dpsRTUv2 23463 }

dpsRTUv2p22464Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 16 is set"
	::= { dpsRTUv2 22464 }

dpsRTUv2p23464Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 16 is cleared"
	::= { dpsRTUv2 23464 }

dpsRTUv2p22465Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 17 is set"
	::= { dpsRTUv2 22465 }

dpsRTUv2p23465Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 17 is cleared"
	::= { dpsRTUv2 23465 }

dpsRTUv2p22466Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 18 is set"
	::= { dpsRTUv2 22466 }

dpsRTUv2p23466Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 18 is cleared"
	::= { dpsRTUv2 23466 }

dpsRTUv2p22467Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 19 is set"
	::= { dpsRTUv2 22467 }

dpsRTUv2p23467Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 19 is cleared"
	::= { dpsRTUv2 23467 }

dpsRTUv2p22468Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 20 is set"
	::= { dpsRTUv2 22468 }

dpsRTUv2p23468Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 20 is cleared"
	::= { dpsRTUv2 23468 }

dpsRTUv2p22469Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 21 is set"
	::= { dpsRTUv2 22469 }

dpsRTUv2p23469Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 21 is cleared"
	::= { dpsRTUv2 23469 }

dpsRTUv2p22470Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 22 is set"
	::= { dpsRTUv2 22470 }

dpsRTUv2p23470Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 22 is cleared"
	::= { dpsRTUv2 23470 }

dpsRTUv2p22471Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 23 is set"
	::= { dpsRTUv2 22471 }

dpsRTUv2p23471Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 23 is cleared"
	::= { dpsRTUv2 23471 }

dpsRTUv2p22472Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 24 is set"
	::= { dpsRTUv2 22472 }

dpsRTUv2p23472Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 24 is cleared"
	::= { dpsRTUv2 23472 }

dpsRTUv2p22473Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 25 is set"
	::= { dpsRTUv2 22473 }

dpsRTUv2p23473Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 25 is cleared"
	::= { dpsRTUv2 23473 }

dpsRTUv2p22474Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 26 is set"
	::= { dpsRTUv2 22474 }

dpsRTUv2p23474Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 26 is cleared"
	::= { dpsRTUv2 23474 }

dpsRTUv2p22475Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 27 is set"
	::= { dpsRTUv2 22475 }

dpsRTUv2p23475Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 27 is cleared"
	::= { dpsRTUv2 23475 }

dpsRTUv2p22476Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 28 is set"
	::= { dpsRTUv2 22476 }

dpsRTUv2p23476Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 28 is cleared"
	::= { dpsRTUv2 23476 }

dpsRTUv2p22477Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 29 is set"
	::= { dpsRTUv2 22477 }

dpsRTUv2p23477Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 29 is cleared"
	::= { dpsRTUv2 23477 }

dpsRTUv2p22478Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 30 is set"
	::= { dpsRTUv2 22478 }

dpsRTUv2p23478Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 30 is cleared"
	::= { dpsRTUv2 23478 }

dpsRTUv2p22479Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 31 is set"
	::= { dpsRTUv2 22479 }

dpsRTUv2p23479Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 31 is cleared"
	::= { dpsRTUv2 23479 }

dpsRTUv2p22480Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 32 is set"
	::= { dpsRTUv2 22480 }

dpsRTUv2p23480Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 32 is cleared"
	::= { dpsRTUv2 23480 }

dpsRTUv2p22481Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 33 is set"
	::= { dpsRTUv2 22481 }

dpsRTUv2p23481Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 33 is cleared"
	::= { dpsRTUv2 23481 }

dpsRTUv2p22482Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 34 is set"
	::= { dpsRTUv2 22482 }

dpsRTUv2p23482Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 34 is cleared"
	::= { dpsRTUv2 23482 }

dpsRTUv2p22483Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 35 is set"
	::= { dpsRTUv2 22483 }

dpsRTUv2p23483Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 35 is cleared"
	::= { dpsRTUv2 23483 }

dpsRTUv2p22484Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 36 is set"
	::= { dpsRTUv2 22484 }

dpsRTUv2p23484Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 36 is cleared"
	::= { dpsRTUv2 23484 }

dpsRTUv2p22485Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 37 is set"
	::= { dpsRTUv2 22485 }

dpsRTUv2p23485Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 37 is cleared"
	::= { dpsRTUv2 23485 }

dpsRTUv2p22486Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 38 is set"
	::= { dpsRTUv2 22486 }

dpsRTUv2p23486Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 38 is cleared"
	::= { dpsRTUv2 23486 }

dpsRTUv2p22487Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 39 is set"
	::= { dpsRTUv2 22487 }

dpsRTUv2p23487Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 39 is cleared"
	::= { dpsRTUv2 23487 }

dpsRTUv2p22488Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 40 is set"
	::= { dpsRTUv2 22488 }

dpsRTUv2p23488Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 40 is cleared"
	::= { dpsRTUv2 23488 }

dpsRTUv2p22489Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 41 is set"
	::= { dpsRTUv2 22489 }

dpsRTUv2p23489Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 41 is cleared"
	::= { dpsRTUv2 23489 }

dpsRTUv2p22490Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 42 is set"
	::= { dpsRTUv2 22490 }

dpsRTUv2p23490Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 42 is cleared"
	::= { dpsRTUv2 23490 }

dpsRTUv2p22491Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 43 is set"
	::= { dpsRTUv2 22491 }

dpsRTUv2p23491Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 43 is cleared"
	::= { dpsRTUv2 23491 }

dpsRTUv2p22492Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 44 is set"
	::= { dpsRTUv2 22492 }

dpsRTUv2p23492Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 44 is cleared"
	::= { dpsRTUv2 23492 }

dpsRTUv2p22493Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 45 is set"
	::= { dpsRTUv2 22493 }

dpsRTUv2p23493Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 45 is cleared"
	::= { dpsRTUv2 23493 }

dpsRTUv2p22494Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 46 is set"
	::= { dpsRTUv2 22494 }

dpsRTUv2p23494Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 46 is cleared"
	::= { dpsRTUv2 23494 }

dpsRTUv2p22495Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 47 is set"
	::= { dpsRTUv2 22495 }

dpsRTUv2p23495Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 47 is cleared"
	::= { dpsRTUv2 23495 }

dpsRTUv2p22496Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 48 is set"
	::= { dpsRTUv2 22496 }

dpsRTUv2p23496Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 48 is cleared"
	::= { dpsRTUv2 23496 }

dpsRTUv2p22497Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 49 is set"
	::= { dpsRTUv2 22497 }

dpsRTUv2p23497Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 49 is cleared"
	::= { dpsRTUv2 23497 }

dpsRTUv2p22498Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 50 is set"
	::= { dpsRTUv2 22498 }

dpsRTUv2p23498Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 50 is cleared"
	::= { dpsRTUv2 23498 }

dpsRTUv2p22499Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 51 is set"
	::= { dpsRTUv2 22499 }

dpsRTUv2p23499Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 51 is cleared"
	::= { dpsRTUv2 23499 }

dpsRTUv2p22500Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 52 is set"
	::= { dpsRTUv2 22500 }

dpsRTUv2p23500Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 52 is cleared"
	::= { dpsRTUv2 23500 }

dpsRTUv2p22501Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 53 is set"
	::= { dpsRTUv2 22501 }

dpsRTUv2p23501Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 53 is cleared"
	::= { dpsRTUv2 23501 }

dpsRTUv2p22502Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 54 is set"
	::= { dpsRTUv2 22502 }

dpsRTUv2p23502Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 54 is cleared"
	::= { dpsRTUv2 23502 }

dpsRTUv2p22503Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 55 is set"
	::= { dpsRTUv2 22503 }

dpsRTUv2p23503Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 55 is cleared"
	::= { dpsRTUv2 23503 }

dpsRTUv2p22504Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 56 is set"
	::= { dpsRTUv2 22504 }

dpsRTUv2p23504Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 56 is cleared"
	::= { dpsRTUv2 23504 }

dpsRTUv2p22505Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 57 is set"
	::= { dpsRTUv2 22505 }

dpsRTUv2p23505Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 57 is cleared"
	::= { dpsRTUv2 23505 }

dpsRTUv2p22506Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 58 is set"
	::= { dpsRTUv2 22506 }

dpsRTUv2p23506Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 58 is cleared"
	::= { dpsRTUv2 23506 }

dpsRTUv2p22507Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 59 is set"
	::= { dpsRTUv2 22507 }

dpsRTUv2p23507Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 59 is cleared"
	::= { dpsRTUv2 23507 }

dpsRTUv2p22508Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 60 is set"
	::= { dpsRTUv2 22508 }

dpsRTUv2p23508Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 60 is cleared"
	::= { dpsRTUv2 23508 }

dpsRTUv2p22509Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 61 is set"
	::= { dpsRTUv2 22509 }

dpsRTUv2p23509Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 61 is cleared"
	::= { dpsRTUv2 23509 }

dpsRTUv2p22510Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 62 is set"
	::= { dpsRTUv2 22510 }

dpsRTUv2p23510Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 62 is cleared"
	::= { dpsRTUv2 23510 }

dpsRTUv2p22511Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 63 is set"
	::= { dpsRTUv2 22511 }

dpsRTUv2p23511Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 63 is cleared"
	::= { dpsRTUv2 23511 }

dpsRTUv2p22512Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 64 is set"
	::= { dpsRTUv2 22512 }

dpsRTUv2p23512Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 7 display 8 point 64 is cleared"
	::= { dpsRTUv2 23512 }

dpsRTUv2p24001Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 1 is set"
	::= { dpsRTUv2 24001 }

dpsRTUv2p25001Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 1 is cleared"
	::= { dpsRTUv2 25001 }

dpsRTUv2p24002Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 2 is set"
	::= { dpsRTUv2 24002 }

dpsRTUv2p25002Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 2 is cleared"
	::= { dpsRTUv2 25002 }

dpsRTUv2p24003Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 3 is set"
	::= { dpsRTUv2 24003 }

dpsRTUv2p25003Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 3 is cleared"
	::= { dpsRTUv2 25003 }

dpsRTUv2p24004Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 4 is set"
	::= { dpsRTUv2 24004 }

dpsRTUv2p25004Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 4 is cleared"
	::= { dpsRTUv2 25004 }

dpsRTUv2p24005Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 5 is set"
	::= { dpsRTUv2 24005 }

dpsRTUv2p25005Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 5 is cleared"
	::= { dpsRTUv2 25005 }

dpsRTUv2p24006Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 6 is set"
	::= { dpsRTUv2 24006 }

dpsRTUv2p25006Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 6 is cleared"
	::= { dpsRTUv2 25006 }

dpsRTUv2p24007Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 7 is set"
	::= { dpsRTUv2 24007 }

dpsRTUv2p25007Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 7 is cleared"
	::= { dpsRTUv2 25007 }

dpsRTUv2p24008Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 8 is set"
	::= { dpsRTUv2 24008 }

dpsRTUv2p25008Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 8 is cleared"
	::= { dpsRTUv2 25008 }

dpsRTUv2p24009Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 9 is set"
	::= { dpsRTUv2 24009 }

dpsRTUv2p25009Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 9 is cleared"
	::= { dpsRTUv2 25009 }

dpsRTUv2p24010Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 10 is set"
	::= { dpsRTUv2 24010 }

dpsRTUv2p25010Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 10 is cleared"
	::= { dpsRTUv2 25010 }

dpsRTUv2p24011Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 11 is set"
	::= { dpsRTUv2 24011 }

dpsRTUv2p25011Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 11 is cleared"
	::= { dpsRTUv2 25011 }

dpsRTUv2p24012Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 12 is set"
	::= { dpsRTUv2 24012 }

dpsRTUv2p25012Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 12 is cleared"
	::= { dpsRTUv2 25012 }

dpsRTUv2p24013Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 13 is set"
	::= { dpsRTUv2 24013 }

dpsRTUv2p25013Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 13 is cleared"
	::= { dpsRTUv2 25013 }

dpsRTUv2p24014Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 14 is set"
	::= { dpsRTUv2 24014 }

dpsRTUv2p25014Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 14 is cleared"
	::= { dpsRTUv2 25014 }

dpsRTUv2p24015Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 15 is set"
	::= { dpsRTUv2 24015 }

dpsRTUv2p25015Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 15 is cleared"
	::= { dpsRTUv2 25015 }

dpsRTUv2p24016Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 16 is set"
	::= { dpsRTUv2 24016 }

dpsRTUv2p25016Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 16 is cleared"
	::= { dpsRTUv2 25016 }

dpsRTUv2p24017Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 17 is set"
	::= { dpsRTUv2 24017 }

dpsRTUv2p25017Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 17 is cleared"
	::= { dpsRTUv2 25017 }

dpsRTUv2p24018Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 18 is set"
	::= { dpsRTUv2 24018 }

dpsRTUv2p25018Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 18 is cleared"
	::= { dpsRTUv2 25018 }

dpsRTUv2p24019Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 19 is set"
	::= { dpsRTUv2 24019 }

dpsRTUv2p25019Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 19 is cleared"
	::= { dpsRTUv2 25019 }

dpsRTUv2p24020Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 20 is set"
	::= { dpsRTUv2 24020 }

dpsRTUv2p25020Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 20 is cleared"
	::= { dpsRTUv2 25020 }

dpsRTUv2p24021Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 21 is set"
	::= { dpsRTUv2 24021 }

dpsRTUv2p25021Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 21 is cleared"
	::= { dpsRTUv2 25021 }

dpsRTUv2p24022Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 22 is set"
	::= { dpsRTUv2 24022 }

dpsRTUv2p25022Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 22 is cleared"
	::= { dpsRTUv2 25022 }

dpsRTUv2p24023Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 23 is set"
	::= { dpsRTUv2 24023 }

dpsRTUv2p25023Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 23 is cleared"
	::= { dpsRTUv2 25023 }

dpsRTUv2p24024Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 24 is set"
	::= { dpsRTUv2 24024 }

dpsRTUv2p25024Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 24 is cleared"
	::= { dpsRTUv2 25024 }

dpsRTUv2p24025Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 25 is set"
	::= { dpsRTUv2 24025 }

dpsRTUv2p25025Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 25 is cleared"
	::= { dpsRTUv2 25025 }

dpsRTUv2p24026Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 26 is set"
	::= { dpsRTUv2 24026 }

dpsRTUv2p25026Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 26 is cleared"
	::= { dpsRTUv2 25026 }

dpsRTUv2p24027Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 27 is set"
	::= { dpsRTUv2 24027 }

dpsRTUv2p25027Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 27 is cleared"
	::= { dpsRTUv2 25027 }

dpsRTUv2p24028Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 28 is set"
	::= { dpsRTUv2 24028 }

dpsRTUv2p25028Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 28 is cleared"
	::= { dpsRTUv2 25028 }

dpsRTUv2p24029Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 29 is set"
	::= { dpsRTUv2 24029 }

dpsRTUv2p25029Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 29 is cleared"
	::= { dpsRTUv2 25029 }

dpsRTUv2p24030Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 30 is set"
	::= { dpsRTUv2 24030 }

dpsRTUv2p25030Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 30 is cleared"
	::= { dpsRTUv2 25030 }

dpsRTUv2p24031Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 31 is set"
	::= { dpsRTUv2 24031 }

dpsRTUv2p25031Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 31 is cleared"
	::= { dpsRTUv2 25031 }

dpsRTUv2p24032Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 32 is set"
	::= { dpsRTUv2 24032 }

dpsRTUv2p25032Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 32 is cleared"
	::= { dpsRTUv2 25032 }

dpsRTUv2p24033Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 33 is set"
	::= { dpsRTUv2 24033 }

dpsRTUv2p25033Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 33 is cleared"
	::= { dpsRTUv2 25033 }

dpsRTUv2p24034Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 34 is set"
	::= { dpsRTUv2 24034 }

dpsRTUv2p25034Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 34 is cleared"
	::= { dpsRTUv2 25034 }

dpsRTUv2p24035Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 35 is set"
	::= { dpsRTUv2 24035 }

dpsRTUv2p25035Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 35 is cleared"
	::= { dpsRTUv2 25035 }

dpsRTUv2p24036Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 36 is set"
	::= { dpsRTUv2 24036 }

dpsRTUv2p25036Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 36 is cleared"
	::= { dpsRTUv2 25036 }

dpsRTUv2p24037Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 37 is set"
	::= { dpsRTUv2 24037 }

dpsRTUv2p25037Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 37 is cleared"
	::= { dpsRTUv2 25037 }

dpsRTUv2p24038Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 38 is set"
	::= { dpsRTUv2 24038 }

dpsRTUv2p25038Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 38 is cleared"
	::= { dpsRTUv2 25038 }

dpsRTUv2p24039Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 39 is set"
	::= { dpsRTUv2 24039 }

dpsRTUv2p25039Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 39 is cleared"
	::= { dpsRTUv2 25039 }

dpsRTUv2p24040Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 40 is set"
	::= { dpsRTUv2 24040 }

dpsRTUv2p25040Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 40 is cleared"
	::= { dpsRTUv2 25040 }

dpsRTUv2p24041Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 41 is set"
	::= { dpsRTUv2 24041 }

dpsRTUv2p25041Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 41 is cleared"
	::= { dpsRTUv2 25041 }

dpsRTUv2p24042Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 42 is set"
	::= { dpsRTUv2 24042 }

dpsRTUv2p25042Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 42 is cleared"
	::= { dpsRTUv2 25042 }

dpsRTUv2p24043Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 43 is set"
	::= { dpsRTUv2 24043 }

dpsRTUv2p25043Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 43 is cleared"
	::= { dpsRTUv2 25043 }

dpsRTUv2p24044Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 44 is set"
	::= { dpsRTUv2 24044 }

dpsRTUv2p25044Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 44 is cleared"
	::= { dpsRTUv2 25044 }

dpsRTUv2p24045Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 45 is set"
	::= { dpsRTUv2 24045 }

dpsRTUv2p25045Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 45 is cleared"
	::= { dpsRTUv2 25045 }

dpsRTUv2p24046Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 46 is set"
	::= { dpsRTUv2 24046 }

dpsRTUv2p25046Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 46 is cleared"
	::= { dpsRTUv2 25046 }

dpsRTUv2p24047Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 47 is set"
	::= { dpsRTUv2 24047 }

dpsRTUv2p25047Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 47 is cleared"
	::= { dpsRTUv2 25047 }

dpsRTUv2p24048Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 48 is set"
	::= { dpsRTUv2 24048 }

dpsRTUv2p25048Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 48 is cleared"
	::= { dpsRTUv2 25048 }

dpsRTUv2p24049Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 49 is set"
	::= { dpsRTUv2 24049 }

dpsRTUv2p25049Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 49 is cleared"
	::= { dpsRTUv2 25049 }

dpsRTUv2p24050Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 50 is set"
	::= { dpsRTUv2 24050 }

dpsRTUv2p25050Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 50 is cleared"
	::= { dpsRTUv2 25050 }

dpsRTUv2p24051Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 51 is set"
	::= { dpsRTUv2 24051 }

dpsRTUv2p25051Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 51 is cleared"
	::= { dpsRTUv2 25051 }

dpsRTUv2p24052Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 52 is set"
	::= { dpsRTUv2 24052 }

dpsRTUv2p25052Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 52 is cleared"
	::= { dpsRTUv2 25052 }

dpsRTUv2p24053Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 53 is set"
	::= { dpsRTUv2 24053 }

dpsRTUv2p25053Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 53 is cleared"
	::= { dpsRTUv2 25053 }

dpsRTUv2p24054Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 54 is set"
	::= { dpsRTUv2 24054 }

dpsRTUv2p25054Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 54 is cleared"
	::= { dpsRTUv2 25054 }

dpsRTUv2p24055Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 55 is set"
	::= { dpsRTUv2 24055 }

dpsRTUv2p25055Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 55 is cleared"
	::= { dpsRTUv2 25055 }

dpsRTUv2p24056Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 56 is set"
	::= { dpsRTUv2 24056 }

dpsRTUv2p25056Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 56 is cleared"
	::= { dpsRTUv2 25056 }

dpsRTUv2p24057Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 57 is set"
	::= { dpsRTUv2 24057 }

dpsRTUv2p25057Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 57 is cleared"
	::= { dpsRTUv2 25057 }

dpsRTUv2p24058Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 58 is set"
	::= { dpsRTUv2 24058 }

dpsRTUv2p25058Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 58 is cleared"
	::= { dpsRTUv2 25058 }

dpsRTUv2p24059Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 59 is set"
	::= { dpsRTUv2 24059 }

dpsRTUv2p25059Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 59 is cleared"
	::= { dpsRTUv2 25059 }

dpsRTUv2p24060Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 60 is set"
	::= { dpsRTUv2 24060 }

dpsRTUv2p25060Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 60 is cleared"
	::= { dpsRTUv2 25060 }

dpsRTUv2p24061Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 61 is set"
	::= { dpsRTUv2 24061 }

dpsRTUv2p25061Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 61 is cleared"
	::= { dpsRTUv2 25061 }

dpsRTUv2p24062Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 62 is set"
	::= { dpsRTUv2 24062 }

dpsRTUv2p25062Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 62 is cleared"
	::= { dpsRTUv2 25062 }

dpsRTUv2p24063Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 63 is set"
	::= { dpsRTUv2 24063 }

dpsRTUv2p25063Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 63 is cleared"
	::= { dpsRTUv2 25063 }

dpsRTUv2p24064Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 64 is set"
	::= { dpsRTUv2 24064 }

dpsRTUv2p25064Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 1 point 64 is cleared"
	::= { dpsRTUv2 25064 }

dpsRTUv2p24065Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 1 is set"
	::= { dpsRTUv2 24065 }

dpsRTUv2p25065Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 1 is cleared"
	::= { dpsRTUv2 25065 }

dpsRTUv2p24066Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 2 is set"
	::= { dpsRTUv2 24066 }

dpsRTUv2p25066Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 2 is cleared"
	::= { dpsRTUv2 25066 }

dpsRTUv2p24067Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 3 is set"
	::= { dpsRTUv2 24067 }

dpsRTUv2p25067Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 3 is cleared"
	::= { dpsRTUv2 25067 }

dpsRTUv2p24068Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 4 is set"
	::= { dpsRTUv2 24068 }

dpsRTUv2p25068Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 4 is cleared"
	::= { dpsRTUv2 25068 }

dpsRTUv2p24069Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 5 is set"
	::= { dpsRTUv2 24069 }

dpsRTUv2p25069Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 5 is cleared"
	::= { dpsRTUv2 25069 }

dpsRTUv2p24070Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 6 is set"
	::= { dpsRTUv2 24070 }

dpsRTUv2p25070Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 6 is cleared"
	::= { dpsRTUv2 25070 }

dpsRTUv2p24071Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 7 is set"
	::= { dpsRTUv2 24071 }

dpsRTUv2p25071Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 7 is cleared"
	::= { dpsRTUv2 25071 }

dpsRTUv2p24072Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 8 is set"
	::= { dpsRTUv2 24072 }

dpsRTUv2p25072Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 8 is cleared"
	::= { dpsRTUv2 25072 }

dpsRTUv2p24073Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 9 is set"
	::= { dpsRTUv2 24073 }

dpsRTUv2p25073Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 9 is cleared"
	::= { dpsRTUv2 25073 }

dpsRTUv2p24074Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 10 is set"
	::= { dpsRTUv2 24074 }

dpsRTUv2p25074Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 10 is cleared"
	::= { dpsRTUv2 25074 }

dpsRTUv2p24075Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 11 is set"
	::= { dpsRTUv2 24075 }

dpsRTUv2p25075Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 11 is cleared"
	::= { dpsRTUv2 25075 }

dpsRTUv2p24076Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 12 is set"
	::= { dpsRTUv2 24076 }

dpsRTUv2p25076Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 12 is cleared"
	::= { dpsRTUv2 25076 }

dpsRTUv2p24077Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 13 is set"
	::= { dpsRTUv2 24077 }

dpsRTUv2p25077Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 13 is cleared"
	::= { dpsRTUv2 25077 }

dpsRTUv2p24078Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 14 is set"
	::= { dpsRTUv2 24078 }

dpsRTUv2p25078Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 14 is cleared"
	::= { dpsRTUv2 25078 }

dpsRTUv2p24079Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 15 is set"
	::= { dpsRTUv2 24079 }

dpsRTUv2p25079Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 15 is cleared"
	::= { dpsRTUv2 25079 }

dpsRTUv2p24080Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 16 is set"
	::= { dpsRTUv2 24080 }

dpsRTUv2p25080Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 16 is cleared"
	::= { dpsRTUv2 25080 }

dpsRTUv2p24081Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 17 is set"
	::= { dpsRTUv2 24081 }

dpsRTUv2p25081Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 17 is cleared"
	::= { dpsRTUv2 25081 }

dpsRTUv2p24082Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 18 is set"
	::= { dpsRTUv2 24082 }

dpsRTUv2p25082Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 18 is cleared"
	::= { dpsRTUv2 25082 }

dpsRTUv2p24083Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 19 is set"
	::= { dpsRTUv2 24083 }

dpsRTUv2p25083Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 19 is cleared"
	::= { dpsRTUv2 25083 }

dpsRTUv2p24084Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 20 is set"
	::= { dpsRTUv2 24084 }

dpsRTUv2p25084Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 20 is cleared"
	::= { dpsRTUv2 25084 }

dpsRTUv2p24085Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 21 is set"
	::= { dpsRTUv2 24085 }

dpsRTUv2p25085Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 21 is cleared"
	::= { dpsRTUv2 25085 }

dpsRTUv2p24086Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 22 is set"
	::= { dpsRTUv2 24086 }

dpsRTUv2p25086Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 22 is cleared"
	::= { dpsRTUv2 25086 }

dpsRTUv2p24087Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 23 is set"
	::= { dpsRTUv2 24087 }

dpsRTUv2p25087Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 23 is cleared"
	::= { dpsRTUv2 25087 }

dpsRTUv2p24088Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 24 is set"
	::= { dpsRTUv2 24088 }

dpsRTUv2p25088Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 24 is cleared"
	::= { dpsRTUv2 25088 }

dpsRTUv2p24089Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 25 is set"
	::= { dpsRTUv2 24089 }

dpsRTUv2p25089Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 25 is cleared"
	::= { dpsRTUv2 25089 }

dpsRTUv2p24090Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 26 is set"
	::= { dpsRTUv2 24090 }

dpsRTUv2p25090Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 26 is cleared"
	::= { dpsRTUv2 25090 }

dpsRTUv2p24091Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 27 is set"
	::= { dpsRTUv2 24091 }

dpsRTUv2p25091Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 27 is cleared"
	::= { dpsRTUv2 25091 }

dpsRTUv2p24092Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 28 is set"
	::= { dpsRTUv2 24092 }

dpsRTUv2p25092Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 28 is cleared"
	::= { dpsRTUv2 25092 }

dpsRTUv2p24093Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 29 is set"
	::= { dpsRTUv2 24093 }

dpsRTUv2p25093Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 29 is cleared"
	::= { dpsRTUv2 25093 }

dpsRTUv2p24094Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 30 is set"
	::= { dpsRTUv2 24094 }

dpsRTUv2p25094Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 30 is cleared"
	::= { dpsRTUv2 25094 }

dpsRTUv2p24095Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 31 is set"
	::= { dpsRTUv2 24095 }

dpsRTUv2p25095Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 31 is cleared"
	::= { dpsRTUv2 25095 }

dpsRTUv2p24096Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 32 is set"
	::= { dpsRTUv2 24096 }

dpsRTUv2p25096Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 32 is cleared"
	::= { dpsRTUv2 25096 }

dpsRTUv2p24097Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 33 is set"
	::= { dpsRTUv2 24097 }

dpsRTUv2p25097Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 33 is cleared"
	::= { dpsRTUv2 25097 }

dpsRTUv2p24098Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 34 is set"
	::= { dpsRTUv2 24098 }

dpsRTUv2p25098Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 34 is cleared"
	::= { dpsRTUv2 25098 }

dpsRTUv2p24099Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 35 is set"
	::= { dpsRTUv2 24099 }

dpsRTUv2p25099Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 35 is cleared"
	::= { dpsRTUv2 25099 }

dpsRTUv2p24100Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 36 is set"
	::= { dpsRTUv2 24100 }

dpsRTUv2p25100Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 36 is cleared"
	::= { dpsRTUv2 25100 }

dpsRTUv2p24101Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 37 is set"
	::= { dpsRTUv2 24101 }

dpsRTUv2p25101Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 37 is cleared"
	::= { dpsRTUv2 25101 }

dpsRTUv2p24102Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 38 is set"
	::= { dpsRTUv2 24102 }

dpsRTUv2p25102Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 38 is cleared"
	::= { dpsRTUv2 25102 }

dpsRTUv2p24103Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 39 is set"
	::= { dpsRTUv2 24103 }

dpsRTUv2p25103Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 39 is cleared"
	::= { dpsRTUv2 25103 }

dpsRTUv2p24104Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 40 is set"
	::= { dpsRTUv2 24104 }

dpsRTUv2p25104Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 40 is cleared"
	::= { dpsRTUv2 25104 }

dpsRTUv2p24105Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 41 is set"
	::= { dpsRTUv2 24105 }

dpsRTUv2p25105Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 41 is cleared"
	::= { dpsRTUv2 25105 }

dpsRTUv2p24106Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 42 is set"
	::= { dpsRTUv2 24106 }

dpsRTUv2p25106Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 42 is cleared"
	::= { dpsRTUv2 25106 }

dpsRTUv2p24107Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 43 is set"
	::= { dpsRTUv2 24107 }

dpsRTUv2p25107Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 43 is cleared"
	::= { dpsRTUv2 25107 }

dpsRTUv2p24108Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 44 is set"
	::= { dpsRTUv2 24108 }

dpsRTUv2p25108Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 44 is cleared"
	::= { dpsRTUv2 25108 }

dpsRTUv2p24109Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 45 is set"
	::= { dpsRTUv2 24109 }

dpsRTUv2p25109Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 45 is cleared"
	::= { dpsRTUv2 25109 }

dpsRTUv2p24110Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 46 is set"
	::= { dpsRTUv2 24110 }

dpsRTUv2p25110Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 46 is cleared"
	::= { dpsRTUv2 25110 }

dpsRTUv2p24111Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 47 is set"
	::= { dpsRTUv2 24111 }

dpsRTUv2p25111Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 47 is cleared"
	::= { dpsRTUv2 25111 }

dpsRTUv2p24112Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 48 is set"
	::= { dpsRTUv2 24112 }

dpsRTUv2p25112Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 48 is cleared"
	::= { dpsRTUv2 25112 }

dpsRTUv2p24113Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 49 is set"
	::= { dpsRTUv2 24113 }

dpsRTUv2p25113Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 49 is cleared"
	::= { dpsRTUv2 25113 }

dpsRTUv2p24114Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 50 is set"
	::= { dpsRTUv2 24114 }

dpsRTUv2p25114Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 50 is cleared"
	::= { dpsRTUv2 25114 }

dpsRTUv2p24115Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 51 is set"
	::= { dpsRTUv2 24115 }

dpsRTUv2p25115Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 51 is cleared"
	::= { dpsRTUv2 25115 }

dpsRTUv2p24116Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 52 is set"
	::= { dpsRTUv2 24116 }

dpsRTUv2p25116Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 52 is cleared"
	::= { dpsRTUv2 25116 }

dpsRTUv2p24117Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 53 is set"
	::= { dpsRTUv2 24117 }

dpsRTUv2p25117Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 53 is cleared"
	::= { dpsRTUv2 25117 }

dpsRTUv2p24118Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 54 is set"
	::= { dpsRTUv2 24118 }

dpsRTUv2p25118Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 54 is cleared"
	::= { dpsRTUv2 25118 }

dpsRTUv2p24119Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 55 is set"
	::= { dpsRTUv2 24119 }

dpsRTUv2p25119Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 55 is cleared"
	::= { dpsRTUv2 25119 }

dpsRTUv2p24120Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 56 is set"
	::= { dpsRTUv2 24120 }

dpsRTUv2p25120Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 56 is cleared"
	::= { dpsRTUv2 25120 }

dpsRTUv2p24121Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 57 is set"
	::= { dpsRTUv2 24121 }

dpsRTUv2p25121Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 57 is cleared"
	::= { dpsRTUv2 25121 }

dpsRTUv2p24122Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 58 is set"
	::= { dpsRTUv2 24122 }

dpsRTUv2p25122Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 58 is cleared"
	::= { dpsRTUv2 25122 }

dpsRTUv2p24123Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 59 is set"
	::= { dpsRTUv2 24123 }

dpsRTUv2p25123Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 59 is cleared"
	::= { dpsRTUv2 25123 }

dpsRTUv2p24124Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 60 is set"
	::= { dpsRTUv2 24124 }

dpsRTUv2p25124Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 60 is cleared"
	::= { dpsRTUv2 25124 }

dpsRTUv2p24125Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 61 is set"
	::= { dpsRTUv2 24125 }

dpsRTUv2p25125Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 61 is cleared"
	::= { dpsRTUv2 25125 }

dpsRTUv2p24126Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 62 is set"
	::= { dpsRTUv2 24126 }

dpsRTUv2p25126Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 62 is cleared"
	::= { dpsRTUv2 25126 }

dpsRTUv2p24127Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 63 is set"
	::= { dpsRTUv2 24127 }

dpsRTUv2p25127Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 63 is cleared"
	::= { dpsRTUv2 25127 }

dpsRTUv2p24128Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 64 is set"
	::= { dpsRTUv2 24128 }

dpsRTUv2p25128Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 2 point 64 is cleared"
	::= { dpsRTUv2 25128 }

dpsRTUv2p24129Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 1 is set"
	::= { dpsRTUv2 24129 }

dpsRTUv2p25129Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 1 is cleared"
	::= { dpsRTUv2 25129 }

dpsRTUv2p24130Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 2 is set"
	::= { dpsRTUv2 24130 }

dpsRTUv2p25130Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 2 is cleared"
	::= { dpsRTUv2 25130 }

dpsRTUv2p24131Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 3 is set"
	::= { dpsRTUv2 24131 }

dpsRTUv2p25131Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 3 is cleared"
	::= { dpsRTUv2 25131 }

dpsRTUv2p24132Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 4 is set"
	::= { dpsRTUv2 24132 }

dpsRTUv2p25132Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 4 is cleared"
	::= { dpsRTUv2 25132 }

dpsRTUv2p24133Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 5 is set"
	::= { dpsRTUv2 24133 }

dpsRTUv2p25133Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 5 is cleared"
	::= { dpsRTUv2 25133 }

dpsRTUv2p24134Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 6 is set"
	::= { dpsRTUv2 24134 }

dpsRTUv2p25134Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 6 is cleared"
	::= { dpsRTUv2 25134 }

dpsRTUv2p24135Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 7 is set"
	::= { dpsRTUv2 24135 }

dpsRTUv2p25135Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 7 is cleared"
	::= { dpsRTUv2 25135 }

dpsRTUv2p24136Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 8 is set"
	::= { dpsRTUv2 24136 }

dpsRTUv2p25136Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 8 is cleared"
	::= { dpsRTUv2 25136 }

dpsRTUv2p24137Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 9 is set"
	::= { dpsRTUv2 24137 }

dpsRTUv2p25137Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 9 is cleared"
	::= { dpsRTUv2 25137 }

dpsRTUv2p24138Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 10 is set"
	::= { dpsRTUv2 24138 }

dpsRTUv2p25138Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 10 is cleared"
	::= { dpsRTUv2 25138 }

dpsRTUv2p24139Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 11 is set"
	::= { dpsRTUv2 24139 }

dpsRTUv2p25139Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 11 is cleared"
	::= { dpsRTUv2 25139 }

dpsRTUv2p24140Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 12 is set"
	::= { dpsRTUv2 24140 }

dpsRTUv2p25140Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 12 is cleared"
	::= { dpsRTUv2 25140 }

dpsRTUv2p24141Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 13 is set"
	::= { dpsRTUv2 24141 }

dpsRTUv2p25141Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 13 is cleared"
	::= { dpsRTUv2 25141 }

dpsRTUv2p24142Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 14 is set"
	::= { dpsRTUv2 24142 }

dpsRTUv2p25142Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 14 is cleared"
	::= { dpsRTUv2 25142 }

dpsRTUv2p24143Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 15 is set"
	::= { dpsRTUv2 24143 }

dpsRTUv2p25143Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 15 is cleared"
	::= { dpsRTUv2 25143 }

dpsRTUv2p24144Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 16 is set"
	::= { dpsRTUv2 24144 }

dpsRTUv2p25144Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 16 is cleared"
	::= { dpsRTUv2 25144 }

dpsRTUv2p24145Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 17 is set"
	::= { dpsRTUv2 24145 }

dpsRTUv2p25145Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 17 is cleared"
	::= { dpsRTUv2 25145 }

dpsRTUv2p24146Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 18 is set"
	::= { dpsRTUv2 24146 }

dpsRTUv2p25146Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 18 is cleared"
	::= { dpsRTUv2 25146 }

dpsRTUv2p24147Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 19 is set"
	::= { dpsRTUv2 24147 }

dpsRTUv2p25147Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 19 is cleared"
	::= { dpsRTUv2 25147 }

dpsRTUv2p24148Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 20 is set"
	::= { dpsRTUv2 24148 }

dpsRTUv2p25148Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 20 is cleared"
	::= { dpsRTUv2 25148 }

dpsRTUv2p24149Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 21 is set"
	::= { dpsRTUv2 24149 }

dpsRTUv2p25149Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 21 is cleared"
	::= { dpsRTUv2 25149 }

dpsRTUv2p24150Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 22 is set"
	::= { dpsRTUv2 24150 }

dpsRTUv2p25150Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 22 is cleared"
	::= { dpsRTUv2 25150 }

dpsRTUv2p24151Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 23 is set"
	::= { dpsRTUv2 24151 }

dpsRTUv2p25151Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 23 is cleared"
	::= { dpsRTUv2 25151 }

dpsRTUv2p24152Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 24 is set"
	::= { dpsRTUv2 24152 }

dpsRTUv2p25152Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 24 is cleared"
	::= { dpsRTUv2 25152 }

dpsRTUv2p24153Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 25 is set"
	::= { dpsRTUv2 24153 }

dpsRTUv2p25153Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 25 is cleared"
	::= { dpsRTUv2 25153 }

dpsRTUv2p24154Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 26 is set"
	::= { dpsRTUv2 24154 }

dpsRTUv2p25154Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 26 is cleared"
	::= { dpsRTUv2 25154 }

dpsRTUv2p24155Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 27 is set"
	::= { dpsRTUv2 24155 }

dpsRTUv2p25155Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 27 is cleared"
	::= { dpsRTUv2 25155 }

dpsRTUv2p24156Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 28 is set"
	::= { dpsRTUv2 24156 }

dpsRTUv2p25156Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 28 is cleared"
	::= { dpsRTUv2 25156 }

dpsRTUv2p24157Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 29 is set"
	::= { dpsRTUv2 24157 }

dpsRTUv2p25157Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 29 is cleared"
	::= { dpsRTUv2 25157 }

dpsRTUv2p24158Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 30 is set"
	::= { dpsRTUv2 24158 }

dpsRTUv2p25158Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 30 is cleared"
	::= { dpsRTUv2 25158 }

dpsRTUv2p24159Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 31 is set"
	::= { dpsRTUv2 24159 }

dpsRTUv2p25159Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 31 is cleared"
	::= { dpsRTUv2 25159 }

dpsRTUv2p24160Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 32 is set"
	::= { dpsRTUv2 24160 }

dpsRTUv2p25160Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 32 is cleared"
	::= { dpsRTUv2 25160 }

dpsRTUv2p24161Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 33 is set"
	::= { dpsRTUv2 24161 }

dpsRTUv2p25161Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 33 is cleared"
	::= { dpsRTUv2 25161 }

dpsRTUv2p24162Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 34 is set"
	::= { dpsRTUv2 24162 }

dpsRTUv2p25162Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 34 is cleared"
	::= { dpsRTUv2 25162 }

dpsRTUv2p24163Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 35 is set"
	::= { dpsRTUv2 24163 }

dpsRTUv2p25163Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 35 is cleared"
	::= { dpsRTUv2 25163 }

dpsRTUv2p24164Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 36 is set"
	::= { dpsRTUv2 24164 }

dpsRTUv2p25164Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 36 is cleared"
	::= { dpsRTUv2 25164 }

dpsRTUv2p24165Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 37 is set"
	::= { dpsRTUv2 24165 }

dpsRTUv2p25165Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 37 is cleared"
	::= { dpsRTUv2 25165 }

dpsRTUv2p24166Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 38 is set"
	::= { dpsRTUv2 24166 }

dpsRTUv2p25166Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 38 is cleared"
	::= { dpsRTUv2 25166 }

dpsRTUv2p24167Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 39 is set"
	::= { dpsRTUv2 24167 }

dpsRTUv2p25167Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 39 is cleared"
	::= { dpsRTUv2 25167 }

dpsRTUv2p24168Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 40 is set"
	::= { dpsRTUv2 24168 }

dpsRTUv2p25168Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 40 is cleared"
	::= { dpsRTUv2 25168 }

dpsRTUv2p24169Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 41 is set"
	::= { dpsRTUv2 24169 }

dpsRTUv2p25169Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 41 is cleared"
	::= { dpsRTUv2 25169 }

dpsRTUv2p24170Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 42 is set"
	::= { dpsRTUv2 24170 }

dpsRTUv2p25170Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 42 is cleared"
	::= { dpsRTUv2 25170 }

dpsRTUv2p24171Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 43 is set"
	::= { dpsRTUv2 24171 }

dpsRTUv2p25171Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 43 is cleared"
	::= { dpsRTUv2 25171 }

dpsRTUv2p24172Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 44 is set"
	::= { dpsRTUv2 24172 }

dpsRTUv2p25172Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 44 is cleared"
	::= { dpsRTUv2 25172 }

dpsRTUv2p24173Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 45 is set"
	::= { dpsRTUv2 24173 }

dpsRTUv2p25173Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 45 is cleared"
	::= { dpsRTUv2 25173 }

dpsRTUv2p24174Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 46 is set"
	::= { dpsRTUv2 24174 }

dpsRTUv2p25174Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 46 is cleared"
	::= { dpsRTUv2 25174 }

dpsRTUv2p24175Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 47 is set"
	::= { dpsRTUv2 24175 }

dpsRTUv2p25175Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 47 is cleared"
	::= { dpsRTUv2 25175 }

dpsRTUv2p24176Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 48 is set"
	::= { dpsRTUv2 24176 }

dpsRTUv2p25176Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 48 is cleared"
	::= { dpsRTUv2 25176 }

dpsRTUv2p24177Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 49 is set"
	::= { dpsRTUv2 24177 }

dpsRTUv2p25177Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 49 is cleared"
	::= { dpsRTUv2 25177 }

dpsRTUv2p24178Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 50 is set"
	::= { dpsRTUv2 24178 }

dpsRTUv2p25178Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 50 is cleared"
	::= { dpsRTUv2 25178 }

dpsRTUv2p24179Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 51 is set"
	::= { dpsRTUv2 24179 }

dpsRTUv2p25179Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 51 is cleared"
	::= { dpsRTUv2 25179 }

dpsRTUv2p24180Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 52 is set"
	::= { dpsRTUv2 24180 }

dpsRTUv2p25180Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 52 is cleared"
	::= { dpsRTUv2 25180 }

dpsRTUv2p24181Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 53 is set"
	::= { dpsRTUv2 24181 }

dpsRTUv2p25181Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 53 is cleared"
	::= { dpsRTUv2 25181 }

dpsRTUv2p24182Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 54 is set"
	::= { dpsRTUv2 24182 }

dpsRTUv2p25182Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 54 is cleared"
	::= { dpsRTUv2 25182 }

dpsRTUv2p24183Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 55 is set"
	::= { dpsRTUv2 24183 }

dpsRTUv2p25183Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 55 is cleared"
	::= { dpsRTUv2 25183 }

dpsRTUv2p24184Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 56 is set"
	::= { dpsRTUv2 24184 }

dpsRTUv2p25184Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 56 is cleared"
	::= { dpsRTUv2 25184 }

dpsRTUv2p24185Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 57 is set"
	::= { dpsRTUv2 24185 }

dpsRTUv2p25185Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 57 is cleared"
	::= { dpsRTUv2 25185 }

dpsRTUv2p24186Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 58 is set"
	::= { dpsRTUv2 24186 }

dpsRTUv2p25186Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 58 is cleared"
	::= { dpsRTUv2 25186 }

dpsRTUv2p24187Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 59 is set"
	::= { dpsRTUv2 24187 }

dpsRTUv2p25187Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 59 is cleared"
	::= { dpsRTUv2 25187 }

dpsRTUv2p24188Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 60 is set"
	::= { dpsRTUv2 24188 }

dpsRTUv2p25188Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 60 is cleared"
	::= { dpsRTUv2 25188 }

dpsRTUv2p24189Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 61 is set"
	::= { dpsRTUv2 24189 }

dpsRTUv2p25189Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 61 is cleared"
	::= { dpsRTUv2 25189 }

dpsRTUv2p24190Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 62 is set"
	::= { dpsRTUv2 24190 }

dpsRTUv2p25190Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 62 is cleared"
	::= { dpsRTUv2 25190 }

dpsRTUv2p24191Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 63 is set"
	::= { dpsRTUv2 24191 }

dpsRTUv2p25191Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 63 is cleared"
	::= { dpsRTUv2 25191 }

dpsRTUv2p24192Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 64 is set"
	::= { dpsRTUv2 24192 }

dpsRTUv2p25192Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 3 point 64 is cleared"
	::= { dpsRTUv2 25192 }

dpsRTUv2p24193Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 1 is set"
	::= { dpsRTUv2 24193 }

dpsRTUv2p25193Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 1 is cleared"
	::= { dpsRTUv2 25193 }

dpsRTUv2p24194Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 2 is set"
	::= { dpsRTUv2 24194 }

dpsRTUv2p25194Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 2 is cleared"
	::= { dpsRTUv2 25194 }

dpsRTUv2p24195Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 3 is set"
	::= { dpsRTUv2 24195 }

dpsRTUv2p25195Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 3 is cleared"
	::= { dpsRTUv2 25195 }

dpsRTUv2p24196Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 4 is set"
	::= { dpsRTUv2 24196 }

dpsRTUv2p25196Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 4 is cleared"
	::= { dpsRTUv2 25196 }

dpsRTUv2p24197Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 5 is set"
	::= { dpsRTUv2 24197 }

dpsRTUv2p25197Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 5 is cleared"
	::= { dpsRTUv2 25197 }

dpsRTUv2p24198Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 6 is set"
	::= { dpsRTUv2 24198 }

dpsRTUv2p25198Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 6 is cleared"
	::= { dpsRTUv2 25198 }

dpsRTUv2p24199Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 7 is set"
	::= { dpsRTUv2 24199 }

dpsRTUv2p25199Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 7 is cleared"
	::= { dpsRTUv2 25199 }

dpsRTUv2p24200Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 8 is set"
	::= { dpsRTUv2 24200 }

dpsRTUv2p25200Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 8 is cleared"
	::= { dpsRTUv2 25200 }

dpsRTUv2p24201Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 9 is set"
	::= { dpsRTUv2 24201 }

dpsRTUv2p25201Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 9 is cleared"
	::= { dpsRTUv2 25201 }

dpsRTUv2p24202Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 10 is set"
	::= { dpsRTUv2 24202 }

dpsRTUv2p25202Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 10 is cleared"
	::= { dpsRTUv2 25202 }

dpsRTUv2p24203Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 11 is set"
	::= { dpsRTUv2 24203 }

dpsRTUv2p25203Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 11 is cleared"
	::= { dpsRTUv2 25203 }

dpsRTUv2p24204Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 12 is set"
	::= { dpsRTUv2 24204 }

dpsRTUv2p25204Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 12 is cleared"
	::= { dpsRTUv2 25204 }

dpsRTUv2p24205Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 13 is set"
	::= { dpsRTUv2 24205 }

dpsRTUv2p25205Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 13 is cleared"
	::= { dpsRTUv2 25205 }

dpsRTUv2p24206Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 14 is set"
	::= { dpsRTUv2 24206 }

dpsRTUv2p25206Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 14 is cleared"
	::= { dpsRTUv2 25206 }

dpsRTUv2p24207Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 15 is set"
	::= { dpsRTUv2 24207 }

dpsRTUv2p25207Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 15 is cleared"
	::= { dpsRTUv2 25207 }

dpsRTUv2p24208Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 16 is set"
	::= { dpsRTUv2 24208 }

dpsRTUv2p25208Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 16 is cleared"
	::= { dpsRTUv2 25208 }

dpsRTUv2p24209Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 17 is set"
	::= { dpsRTUv2 24209 }

dpsRTUv2p25209Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 17 is cleared"
	::= { dpsRTUv2 25209 }

dpsRTUv2p24210Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 18 is set"
	::= { dpsRTUv2 24210 }

dpsRTUv2p25210Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 18 is cleared"
	::= { dpsRTUv2 25210 }

dpsRTUv2p24211Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 19 is set"
	::= { dpsRTUv2 24211 }

dpsRTUv2p25211Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 19 is cleared"
	::= { dpsRTUv2 25211 }

dpsRTUv2p24212Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 20 is set"
	::= { dpsRTUv2 24212 }

dpsRTUv2p25212Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 20 is cleared"
	::= { dpsRTUv2 25212 }

dpsRTUv2p24213Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 21 is set"
	::= { dpsRTUv2 24213 }

dpsRTUv2p25213Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 21 is cleared"
	::= { dpsRTUv2 25213 }

dpsRTUv2p24214Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 22 is set"
	::= { dpsRTUv2 24214 }

dpsRTUv2p25214Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 22 is cleared"
	::= { dpsRTUv2 25214 }

dpsRTUv2p24215Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 23 is set"
	::= { dpsRTUv2 24215 }

dpsRTUv2p25215Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 23 is cleared"
	::= { dpsRTUv2 25215 }

dpsRTUv2p24216Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 24 is set"
	::= { dpsRTUv2 24216 }

dpsRTUv2p25216Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 24 is cleared"
	::= { dpsRTUv2 25216 }

dpsRTUv2p24217Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 25 is set"
	::= { dpsRTUv2 24217 }

dpsRTUv2p25217Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 25 is cleared"
	::= { dpsRTUv2 25217 }

dpsRTUv2p24218Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 26 is set"
	::= { dpsRTUv2 24218 }

dpsRTUv2p25218Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 26 is cleared"
	::= { dpsRTUv2 25218 }

dpsRTUv2p24219Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 27 is set"
	::= { dpsRTUv2 24219 }

dpsRTUv2p25219Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 27 is cleared"
	::= { dpsRTUv2 25219 }

dpsRTUv2p24220Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 28 is set"
	::= { dpsRTUv2 24220 }

dpsRTUv2p25220Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 28 is cleared"
	::= { dpsRTUv2 25220 }

dpsRTUv2p24221Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 29 is set"
	::= { dpsRTUv2 24221 }

dpsRTUv2p25221Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 29 is cleared"
	::= { dpsRTUv2 25221 }

dpsRTUv2p24222Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 30 is set"
	::= { dpsRTUv2 24222 }

dpsRTUv2p25222Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 30 is cleared"
	::= { dpsRTUv2 25222 }

dpsRTUv2p24223Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 31 is set"
	::= { dpsRTUv2 24223 }

dpsRTUv2p25223Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 31 is cleared"
	::= { dpsRTUv2 25223 }

dpsRTUv2p24224Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 32 is set"
	::= { dpsRTUv2 24224 }

dpsRTUv2p25224Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 32 is cleared"
	::= { dpsRTUv2 25224 }

dpsRTUv2p24225Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 33 is set"
	::= { dpsRTUv2 24225 }

dpsRTUv2p25225Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 33 is cleared"
	::= { dpsRTUv2 25225 }

dpsRTUv2p24226Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 34 is set"
	::= { dpsRTUv2 24226 }

dpsRTUv2p25226Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 34 is cleared"
	::= { dpsRTUv2 25226 }

dpsRTUv2p24227Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 35 is set"
	::= { dpsRTUv2 24227 }

dpsRTUv2p25227Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 35 is cleared"
	::= { dpsRTUv2 25227 }

dpsRTUv2p24228Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 36 is set"
	::= { dpsRTUv2 24228 }

dpsRTUv2p25228Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 36 is cleared"
	::= { dpsRTUv2 25228 }

dpsRTUv2p24229Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 37 is set"
	::= { dpsRTUv2 24229 }

dpsRTUv2p25229Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 37 is cleared"
	::= { dpsRTUv2 25229 }

dpsRTUv2p24230Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 38 is set"
	::= { dpsRTUv2 24230 }

dpsRTUv2p25230Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 38 is cleared"
	::= { dpsRTUv2 25230 }

dpsRTUv2p24231Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 39 is set"
	::= { dpsRTUv2 24231 }

dpsRTUv2p25231Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 39 is cleared"
	::= { dpsRTUv2 25231 }

dpsRTUv2p24232Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 40 is set"
	::= { dpsRTUv2 24232 }

dpsRTUv2p25232Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 40 is cleared"
	::= { dpsRTUv2 25232 }

dpsRTUv2p24233Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 41 is set"
	::= { dpsRTUv2 24233 }

dpsRTUv2p25233Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 41 is cleared"
	::= { dpsRTUv2 25233 }

dpsRTUv2p24234Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 42 is set"
	::= { dpsRTUv2 24234 }

dpsRTUv2p25234Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 42 is cleared"
	::= { dpsRTUv2 25234 }

dpsRTUv2p24235Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 43 is set"
	::= { dpsRTUv2 24235 }

dpsRTUv2p25235Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 43 is cleared"
	::= { dpsRTUv2 25235 }

dpsRTUv2p24236Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 44 is set"
	::= { dpsRTUv2 24236 }

dpsRTUv2p25236Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 44 is cleared"
	::= { dpsRTUv2 25236 }

dpsRTUv2p24237Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 45 is set"
	::= { dpsRTUv2 24237 }

dpsRTUv2p25237Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 45 is cleared"
	::= { dpsRTUv2 25237 }

dpsRTUv2p24238Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 46 is set"
	::= { dpsRTUv2 24238 }

dpsRTUv2p25238Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 46 is cleared"
	::= { dpsRTUv2 25238 }

dpsRTUv2p24239Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 47 is set"
	::= { dpsRTUv2 24239 }

dpsRTUv2p25239Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 47 is cleared"
	::= { dpsRTUv2 25239 }

dpsRTUv2p24240Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 48 is set"
	::= { dpsRTUv2 24240 }

dpsRTUv2p25240Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 48 is cleared"
	::= { dpsRTUv2 25240 }

dpsRTUv2p24241Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 49 is set"
	::= { dpsRTUv2 24241 }

dpsRTUv2p25241Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 49 is cleared"
	::= { dpsRTUv2 25241 }

dpsRTUv2p24242Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 50 is set"
	::= { dpsRTUv2 24242 }

dpsRTUv2p25242Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 50 is cleared"
	::= { dpsRTUv2 25242 }

dpsRTUv2p24243Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 51 is set"
	::= { dpsRTUv2 24243 }

dpsRTUv2p25243Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 51 is cleared"
	::= { dpsRTUv2 25243 }

dpsRTUv2p24244Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 52 is set"
	::= { dpsRTUv2 24244 }

dpsRTUv2p25244Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 52 is cleared"
	::= { dpsRTUv2 25244 }

dpsRTUv2p24245Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 53 is set"
	::= { dpsRTUv2 24245 }

dpsRTUv2p25245Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 53 is cleared"
	::= { dpsRTUv2 25245 }

dpsRTUv2p24246Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 54 is set"
	::= { dpsRTUv2 24246 }

dpsRTUv2p25246Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 54 is cleared"
	::= { dpsRTUv2 25246 }

dpsRTUv2p24247Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 55 is set"
	::= { dpsRTUv2 24247 }

dpsRTUv2p25247Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 55 is cleared"
	::= { dpsRTUv2 25247 }

dpsRTUv2p24248Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 56 is set"
	::= { dpsRTUv2 24248 }

dpsRTUv2p25248Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 56 is cleared"
	::= { dpsRTUv2 25248 }

dpsRTUv2p24249Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 57 is set"
	::= { dpsRTUv2 24249 }

dpsRTUv2p25249Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 57 is cleared"
	::= { dpsRTUv2 25249 }

dpsRTUv2p24250Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 58 is set"
	::= { dpsRTUv2 24250 }

dpsRTUv2p25250Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 58 is cleared"
	::= { dpsRTUv2 25250 }

dpsRTUv2p24251Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 59 is set"
	::= { dpsRTUv2 24251 }

dpsRTUv2p25251Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 59 is cleared"
	::= { dpsRTUv2 25251 }

dpsRTUv2p24252Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 60 is set"
	::= { dpsRTUv2 24252 }

dpsRTUv2p25252Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 60 is cleared"
	::= { dpsRTUv2 25252 }

dpsRTUv2p24253Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 61 is set"
	::= { dpsRTUv2 24253 }

dpsRTUv2p25253Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 61 is cleared"
	::= { dpsRTUv2 25253 }

dpsRTUv2p24254Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 62 is set"
	::= { dpsRTUv2 24254 }

dpsRTUv2p25254Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 62 is cleared"
	::= { dpsRTUv2 25254 }

dpsRTUv2p24255Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 63 is set"
	::= { dpsRTUv2 24255 }

dpsRTUv2p25255Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 63 is cleared"
	::= { dpsRTUv2 25255 }

dpsRTUv2p24256Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 64 is set"
	::= { dpsRTUv2 24256 }

dpsRTUv2p25256Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 4 point 64 is cleared"
	::= { dpsRTUv2 25256 }

dpsRTUv2p24257Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 1 is set"
	::= { dpsRTUv2 24257 }

dpsRTUv2p25257Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 1 is cleared"
	::= { dpsRTUv2 25257 }

dpsRTUv2p24258Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 2 is set"
	::= { dpsRTUv2 24258 }

dpsRTUv2p25258Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 2 is cleared"
	::= { dpsRTUv2 25258 }

dpsRTUv2p24259Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 3 is set"
	::= { dpsRTUv2 24259 }

dpsRTUv2p25259Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 3 is cleared"
	::= { dpsRTUv2 25259 }

dpsRTUv2p24260Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 4 is set"
	::= { dpsRTUv2 24260 }

dpsRTUv2p25260Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 4 is cleared"
	::= { dpsRTUv2 25260 }

dpsRTUv2p24261Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 5 is set"
	::= { dpsRTUv2 24261 }

dpsRTUv2p25261Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 5 is cleared"
	::= { dpsRTUv2 25261 }

dpsRTUv2p24262Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 6 is set"
	::= { dpsRTUv2 24262 }

dpsRTUv2p25262Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 6 is cleared"
	::= { dpsRTUv2 25262 }

dpsRTUv2p24263Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 7 is set"
	::= { dpsRTUv2 24263 }

dpsRTUv2p25263Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 7 is cleared"
	::= { dpsRTUv2 25263 }

dpsRTUv2p24264Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 8 is set"
	::= { dpsRTUv2 24264 }

dpsRTUv2p25264Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 8 is cleared"
	::= { dpsRTUv2 25264 }

dpsRTUv2p24265Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 9 is set"
	::= { dpsRTUv2 24265 }

dpsRTUv2p25265Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 9 is cleared"
	::= { dpsRTUv2 25265 }

dpsRTUv2p24266Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 10 is set"
	::= { dpsRTUv2 24266 }

dpsRTUv2p25266Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 10 is cleared"
	::= { dpsRTUv2 25266 }

dpsRTUv2p24267Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 11 is set"
	::= { dpsRTUv2 24267 }

dpsRTUv2p25267Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 11 is cleared"
	::= { dpsRTUv2 25267 }

dpsRTUv2p24268Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 12 is set"
	::= { dpsRTUv2 24268 }

dpsRTUv2p25268Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 12 is cleared"
	::= { dpsRTUv2 25268 }

dpsRTUv2p24269Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 13 is set"
	::= { dpsRTUv2 24269 }

dpsRTUv2p25269Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 13 is cleared"
	::= { dpsRTUv2 25269 }

dpsRTUv2p24270Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 14 is set"
	::= { dpsRTUv2 24270 }

dpsRTUv2p25270Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 14 is cleared"
	::= { dpsRTUv2 25270 }

dpsRTUv2p24271Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 15 is set"
	::= { dpsRTUv2 24271 }

dpsRTUv2p25271Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 15 is cleared"
	::= { dpsRTUv2 25271 }

dpsRTUv2p24272Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 16 is set"
	::= { dpsRTUv2 24272 }

dpsRTUv2p25272Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 16 is cleared"
	::= { dpsRTUv2 25272 }

dpsRTUv2p24273Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 17 is set"
	::= { dpsRTUv2 24273 }

dpsRTUv2p25273Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 17 is cleared"
	::= { dpsRTUv2 25273 }

dpsRTUv2p24274Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 18 is set"
	::= { dpsRTUv2 24274 }

dpsRTUv2p25274Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 18 is cleared"
	::= { dpsRTUv2 25274 }

dpsRTUv2p24275Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 19 is set"
	::= { dpsRTUv2 24275 }

dpsRTUv2p25275Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 19 is cleared"
	::= { dpsRTUv2 25275 }

dpsRTUv2p24276Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 20 is set"
	::= { dpsRTUv2 24276 }

dpsRTUv2p25276Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 20 is cleared"
	::= { dpsRTUv2 25276 }

dpsRTUv2p24277Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 21 is set"
	::= { dpsRTUv2 24277 }

dpsRTUv2p25277Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 21 is cleared"
	::= { dpsRTUv2 25277 }

dpsRTUv2p24278Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 22 is set"
	::= { dpsRTUv2 24278 }

dpsRTUv2p25278Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 22 is cleared"
	::= { dpsRTUv2 25278 }

dpsRTUv2p24279Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 23 is set"
	::= { dpsRTUv2 24279 }

dpsRTUv2p25279Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 23 is cleared"
	::= { dpsRTUv2 25279 }

dpsRTUv2p24280Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 24 is set"
	::= { dpsRTUv2 24280 }

dpsRTUv2p25280Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 24 is cleared"
	::= { dpsRTUv2 25280 }

dpsRTUv2p24281Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 25 is set"
	::= { dpsRTUv2 24281 }

dpsRTUv2p25281Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 25 is cleared"
	::= { dpsRTUv2 25281 }

dpsRTUv2p24282Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 26 is set"
	::= { dpsRTUv2 24282 }

dpsRTUv2p25282Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 26 is cleared"
	::= { dpsRTUv2 25282 }

dpsRTUv2p24283Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 27 is set"
	::= { dpsRTUv2 24283 }

dpsRTUv2p25283Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 27 is cleared"
	::= { dpsRTUv2 25283 }

dpsRTUv2p24284Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 28 is set"
	::= { dpsRTUv2 24284 }

dpsRTUv2p25284Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 28 is cleared"
	::= { dpsRTUv2 25284 }

dpsRTUv2p24285Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 29 is set"
	::= { dpsRTUv2 24285 }

dpsRTUv2p25285Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 29 is cleared"
	::= { dpsRTUv2 25285 }

dpsRTUv2p24286Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 30 is set"
	::= { dpsRTUv2 24286 }

dpsRTUv2p25286Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 30 is cleared"
	::= { dpsRTUv2 25286 }

dpsRTUv2p24287Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 31 is set"
	::= { dpsRTUv2 24287 }

dpsRTUv2p25287Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 31 is cleared"
	::= { dpsRTUv2 25287 }

dpsRTUv2p24288Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 32 is set"
	::= { dpsRTUv2 24288 }

dpsRTUv2p25288Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 32 is cleared"
	::= { dpsRTUv2 25288 }

dpsRTUv2p24289Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 33 is set"
	::= { dpsRTUv2 24289 }

dpsRTUv2p25289Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 33 is cleared"
	::= { dpsRTUv2 25289 }

dpsRTUv2p24290Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 34 is set"
	::= { dpsRTUv2 24290 }

dpsRTUv2p25290Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 34 is cleared"
	::= { dpsRTUv2 25290 }

dpsRTUv2p24291Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 35 is set"
	::= { dpsRTUv2 24291 }

dpsRTUv2p25291Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 35 is cleared"
	::= { dpsRTUv2 25291 }

dpsRTUv2p24292Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 36 is set"
	::= { dpsRTUv2 24292 }

dpsRTUv2p25292Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 36 is cleared"
	::= { dpsRTUv2 25292 }

dpsRTUv2p24293Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 37 is set"
	::= { dpsRTUv2 24293 }

dpsRTUv2p25293Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 37 is cleared"
	::= { dpsRTUv2 25293 }

dpsRTUv2p24294Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 38 is set"
	::= { dpsRTUv2 24294 }

dpsRTUv2p25294Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 38 is cleared"
	::= { dpsRTUv2 25294 }

dpsRTUv2p24295Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 39 is set"
	::= { dpsRTUv2 24295 }

dpsRTUv2p25295Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 39 is cleared"
	::= { dpsRTUv2 25295 }

dpsRTUv2p24296Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 40 is set"
	::= { dpsRTUv2 24296 }

dpsRTUv2p25296Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 40 is cleared"
	::= { dpsRTUv2 25296 }

dpsRTUv2p24297Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 41 is set"
	::= { dpsRTUv2 24297 }

dpsRTUv2p25297Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 41 is cleared"
	::= { dpsRTUv2 25297 }

dpsRTUv2p24298Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 42 is set"
	::= { dpsRTUv2 24298 }

dpsRTUv2p25298Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 42 is cleared"
	::= { dpsRTUv2 25298 }

dpsRTUv2p24299Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 43 is set"
	::= { dpsRTUv2 24299 }

dpsRTUv2p25299Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 43 is cleared"
	::= { dpsRTUv2 25299 }

dpsRTUv2p24300Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 44 is set"
	::= { dpsRTUv2 24300 }

dpsRTUv2p25300Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 44 is cleared"
	::= { dpsRTUv2 25300 }

dpsRTUv2p24301Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 45 is set"
	::= { dpsRTUv2 24301 }

dpsRTUv2p25301Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 45 is cleared"
	::= { dpsRTUv2 25301 }

dpsRTUv2p24302Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 46 is set"
	::= { dpsRTUv2 24302 }

dpsRTUv2p25302Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 46 is cleared"
	::= { dpsRTUv2 25302 }

dpsRTUv2p24303Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 47 is set"
	::= { dpsRTUv2 24303 }

dpsRTUv2p25303Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 47 is cleared"
	::= { dpsRTUv2 25303 }

dpsRTUv2p24304Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 48 is set"
	::= { dpsRTUv2 24304 }

dpsRTUv2p25304Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 48 is cleared"
	::= { dpsRTUv2 25304 }

dpsRTUv2p24305Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 49 is set"
	::= { dpsRTUv2 24305 }

dpsRTUv2p25305Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 49 is cleared"
	::= { dpsRTUv2 25305 }

dpsRTUv2p24306Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 50 is set"
	::= { dpsRTUv2 24306 }

dpsRTUv2p25306Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 50 is cleared"
	::= { dpsRTUv2 25306 }

dpsRTUv2p24307Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 51 is set"
	::= { dpsRTUv2 24307 }

dpsRTUv2p25307Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 51 is cleared"
	::= { dpsRTUv2 25307 }

dpsRTUv2p24308Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 52 is set"
	::= { dpsRTUv2 24308 }

dpsRTUv2p25308Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 52 is cleared"
	::= { dpsRTUv2 25308 }

dpsRTUv2p24309Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 53 is set"
	::= { dpsRTUv2 24309 }

dpsRTUv2p25309Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 53 is cleared"
	::= { dpsRTUv2 25309 }

dpsRTUv2p24310Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 54 is set"
	::= { dpsRTUv2 24310 }

dpsRTUv2p25310Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 54 is cleared"
	::= { dpsRTUv2 25310 }

dpsRTUv2p24311Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 55 is set"
	::= { dpsRTUv2 24311 }

dpsRTUv2p25311Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 55 is cleared"
	::= { dpsRTUv2 25311 }

dpsRTUv2p24312Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 56 is set"
	::= { dpsRTUv2 24312 }

dpsRTUv2p25312Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 56 is cleared"
	::= { dpsRTUv2 25312 }

dpsRTUv2p24313Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 57 is set"
	::= { dpsRTUv2 24313 }

dpsRTUv2p25313Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 57 is cleared"
	::= { dpsRTUv2 25313 }

dpsRTUv2p24314Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 58 is set"
	::= { dpsRTUv2 24314 }

dpsRTUv2p25314Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 58 is cleared"
	::= { dpsRTUv2 25314 }

dpsRTUv2p24315Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 59 is set"
	::= { dpsRTUv2 24315 }

dpsRTUv2p25315Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 59 is cleared"
	::= { dpsRTUv2 25315 }

dpsRTUv2p24316Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 60 is set"
	::= { dpsRTUv2 24316 }

dpsRTUv2p25316Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 60 is cleared"
	::= { dpsRTUv2 25316 }

dpsRTUv2p24317Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 61 is set"
	::= { dpsRTUv2 24317 }

dpsRTUv2p25317Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 61 is cleared"
	::= { dpsRTUv2 25317 }

dpsRTUv2p24318Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 62 is set"
	::= { dpsRTUv2 24318 }

dpsRTUv2p25318Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 62 is cleared"
	::= { dpsRTUv2 25318 }

dpsRTUv2p24319Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 63 is set"
	::= { dpsRTUv2 24319 }

dpsRTUv2p25319Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 63 is cleared"
	::= { dpsRTUv2 25319 }

dpsRTUv2p24320Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 64 is set"
	::= { dpsRTUv2 24320 }

dpsRTUv2p25320Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 5 point 64 is cleared"
	::= { dpsRTUv2 25320 }

dpsRTUv2p24321Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 1 is set"
	::= { dpsRTUv2 24321 }

dpsRTUv2p25321Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 1 is cleared"
	::= { dpsRTUv2 25321 }

dpsRTUv2p24322Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 2 is set"
	::= { dpsRTUv2 24322 }

dpsRTUv2p25322Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 2 is cleared"
	::= { dpsRTUv2 25322 }

dpsRTUv2p24323Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 3 is set"
	::= { dpsRTUv2 24323 }

dpsRTUv2p25323Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 3 is cleared"
	::= { dpsRTUv2 25323 }

dpsRTUv2p24324Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 4 is set"
	::= { dpsRTUv2 24324 }

dpsRTUv2p25324Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 4 is cleared"
	::= { dpsRTUv2 25324 }

dpsRTUv2p24325Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 5 is set"
	::= { dpsRTUv2 24325 }

dpsRTUv2p25325Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 5 is cleared"
	::= { dpsRTUv2 25325 }

dpsRTUv2p24326Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 6 is set"
	::= { dpsRTUv2 24326 }

dpsRTUv2p25326Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 6 is cleared"
	::= { dpsRTUv2 25326 }

dpsRTUv2p24327Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 7 is set"
	::= { dpsRTUv2 24327 }

dpsRTUv2p25327Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 7 is cleared"
	::= { dpsRTUv2 25327 }

dpsRTUv2p24328Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 8 is set"
	::= { dpsRTUv2 24328 }

dpsRTUv2p25328Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 8 is cleared"
	::= { dpsRTUv2 25328 }

dpsRTUv2p24329Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 9 is set"
	::= { dpsRTUv2 24329 }

dpsRTUv2p25329Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 9 is cleared"
	::= { dpsRTUv2 25329 }

dpsRTUv2p24330Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 10 is set"
	::= { dpsRTUv2 24330 }

dpsRTUv2p25330Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 10 is cleared"
	::= { dpsRTUv2 25330 }

dpsRTUv2p24331Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 11 is set"
	::= { dpsRTUv2 24331 }

dpsRTUv2p25331Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 11 is cleared"
	::= { dpsRTUv2 25331 }

dpsRTUv2p24332Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 12 is set"
	::= { dpsRTUv2 24332 }

dpsRTUv2p25332Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 12 is cleared"
	::= { dpsRTUv2 25332 }

dpsRTUv2p24333Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 13 is set"
	::= { dpsRTUv2 24333 }

dpsRTUv2p25333Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 13 is cleared"
	::= { dpsRTUv2 25333 }

dpsRTUv2p24334Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 14 is set"
	::= { dpsRTUv2 24334 }

dpsRTUv2p25334Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 14 is cleared"
	::= { dpsRTUv2 25334 }

dpsRTUv2p24335Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 15 is set"
	::= { dpsRTUv2 24335 }

dpsRTUv2p25335Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 15 is cleared"
	::= { dpsRTUv2 25335 }

dpsRTUv2p24336Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 16 is set"
	::= { dpsRTUv2 24336 }

dpsRTUv2p25336Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 16 is cleared"
	::= { dpsRTUv2 25336 }

dpsRTUv2p24337Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 17 is set"
	::= { dpsRTUv2 24337 }

dpsRTUv2p25337Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 17 is cleared"
	::= { dpsRTUv2 25337 }

dpsRTUv2p24338Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 18 is set"
	::= { dpsRTUv2 24338 }

dpsRTUv2p25338Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 18 is cleared"
	::= { dpsRTUv2 25338 }

dpsRTUv2p24339Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 19 is set"
	::= { dpsRTUv2 24339 }

dpsRTUv2p25339Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 19 is cleared"
	::= { dpsRTUv2 25339 }

dpsRTUv2p24340Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 20 is set"
	::= { dpsRTUv2 24340 }

dpsRTUv2p25340Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 20 is cleared"
	::= { dpsRTUv2 25340 }

dpsRTUv2p24341Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 21 is set"
	::= { dpsRTUv2 24341 }

dpsRTUv2p25341Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 21 is cleared"
	::= { dpsRTUv2 25341 }

dpsRTUv2p24342Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 22 is set"
	::= { dpsRTUv2 24342 }

dpsRTUv2p25342Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 22 is cleared"
	::= { dpsRTUv2 25342 }

dpsRTUv2p24343Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 23 is set"
	::= { dpsRTUv2 24343 }

dpsRTUv2p25343Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 23 is cleared"
	::= { dpsRTUv2 25343 }

dpsRTUv2p24344Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 24 is set"
	::= { dpsRTUv2 24344 }

dpsRTUv2p25344Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 24 is cleared"
	::= { dpsRTUv2 25344 }

dpsRTUv2p24345Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 25 is set"
	::= { dpsRTUv2 24345 }

dpsRTUv2p25345Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 25 is cleared"
	::= { dpsRTUv2 25345 }

dpsRTUv2p24346Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 26 is set"
	::= { dpsRTUv2 24346 }

dpsRTUv2p25346Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 26 is cleared"
	::= { dpsRTUv2 25346 }

dpsRTUv2p24347Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 27 is set"
	::= { dpsRTUv2 24347 }

dpsRTUv2p25347Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 27 is cleared"
	::= { dpsRTUv2 25347 }

dpsRTUv2p24348Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 28 is set"
	::= { dpsRTUv2 24348 }

dpsRTUv2p25348Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 28 is cleared"
	::= { dpsRTUv2 25348 }

dpsRTUv2p24349Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 29 is set"
	::= { dpsRTUv2 24349 }

dpsRTUv2p25349Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 29 is cleared"
	::= { dpsRTUv2 25349 }

dpsRTUv2p24350Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 30 is set"
	::= { dpsRTUv2 24350 }

dpsRTUv2p25350Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 30 is cleared"
	::= { dpsRTUv2 25350 }

dpsRTUv2p24351Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 31 is set"
	::= { dpsRTUv2 24351 }

dpsRTUv2p25351Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 31 is cleared"
	::= { dpsRTUv2 25351 }

dpsRTUv2p24352Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 32 is set"
	::= { dpsRTUv2 24352 }

dpsRTUv2p25352Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 32 is cleared"
	::= { dpsRTUv2 25352 }

dpsRTUv2p24353Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 33 is set"
	::= { dpsRTUv2 24353 }

dpsRTUv2p25353Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 33 is cleared"
	::= { dpsRTUv2 25353 }

dpsRTUv2p24354Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 34 is set"
	::= { dpsRTUv2 24354 }

dpsRTUv2p25354Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 34 is cleared"
	::= { dpsRTUv2 25354 }

dpsRTUv2p24355Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 35 is set"
	::= { dpsRTUv2 24355 }

dpsRTUv2p25355Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 35 is cleared"
	::= { dpsRTUv2 25355 }

dpsRTUv2p24356Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 36 is set"
	::= { dpsRTUv2 24356 }

dpsRTUv2p25356Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 36 is cleared"
	::= { dpsRTUv2 25356 }

dpsRTUv2p24357Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 37 is set"
	::= { dpsRTUv2 24357 }

dpsRTUv2p25357Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 37 is cleared"
	::= { dpsRTUv2 25357 }

dpsRTUv2p24358Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 38 is set"
	::= { dpsRTUv2 24358 }

dpsRTUv2p25358Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 38 is cleared"
	::= { dpsRTUv2 25358 }

dpsRTUv2p24359Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 39 is set"
	::= { dpsRTUv2 24359 }

dpsRTUv2p25359Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 39 is cleared"
	::= { dpsRTUv2 25359 }

dpsRTUv2p24360Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 40 is set"
	::= { dpsRTUv2 24360 }

dpsRTUv2p25360Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 40 is cleared"
	::= { dpsRTUv2 25360 }

dpsRTUv2p24361Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 41 is set"
	::= { dpsRTUv2 24361 }

dpsRTUv2p25361Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 41 is cleared"
	::= { dpsRTUv2 25361 }

dpsRTUv2p24362Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 42 is set"
	::= { dpsRTUv2 24362 }

dpsRTUv2p25362Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 42 is cleared"
	::= { dpsRTUv2 25362 }

dpsRTUv2p24363Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 43 is set"
	::= { dpsRTUv2 24363 }

dpsRTUv2p25363Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 43 is cleared"
	::= { dpsRTUv2 25363 }

dpsRTUv2p24364Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 44 is set"
	::= { dpsRTUv2 24364 }

dpsRTUv2p25364Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 44 is cleared"
	::= { dpsRTUv2 25364 }

dpsRTUv2p24365Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 45 is set"
	::= { dpsRTUv2 24365 }

dpsRTUv2p25365Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 45 is cleared"
	::= { dpsRTUv2 25365 }

dpsRTUv2p24366Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 46 is set"
	::= { dpsRTUv2 24366 }

dpsRTUv2p25366Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 46 is cleared"
	::= { dpsRTUv2 25366 }

dpsRTUv2p24367Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 47 is set"
	::= { dpsRTUv2 24367 }

dpsRTUv2p25367Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 47 is cleared"
	::= { dpsRTUv2 25367 }

dpsRTUv2p24368Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 48 is set"
	::= { dpsRTUv2 24368 }

dpsRTUv2p25368Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 48 is cleared"
	::= { dpsRTUv2 25368 }

dpsRTUv2p24369Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 49 is set"
	::= { dpsRTUv2 24369 }

dpsRTUv2p25369Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 49 is cleared"
	::= { dpsRTUv2 25369 }

dpsRTUv2p24370Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 50 is set"
	::= { dpsRTUv2 24370 }

dpsRTUv2p25370Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 50 is cleared"
	::= { dpsRTUv2 25370 }

dpsRTUv2p24371Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 51 is set"
	::= { dpsRTUv2 24371 }

dpsRTUv2p25371Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 51 is cleared"
	::= { dpsRTUv2 25371 }

dpsRTUv2p24372Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 52 is set"
	::= { dpsRTUv2 24372 }

dpsRTUv2p25372Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 52 is cleared"
	::= { dpsRTUv2 25372 }

dpsRTUv2p24373Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 53 is set"
	::= { dpsRTUv2 24373 }

dpsRTUv2p25373Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 53 is cleared"
	::= { dpsRTUv2 25373 }

dpsRTUv2p24374Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 54 is set"
	::= { dpsRTUv2 24374 }

dpsRTUv2p25374Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 54 is cleared"
	::= { dpsRTUv2 25374 }

dpsRTUv2p24375Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 55 is set"
	::= { dpsRTUv2 24375 }

dpsRTUv2p25375Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 55 is cleared"
	::= { dpsRTUv2 25375 }

dpsRTUv2p24376Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 56 is set"
	::= { dpsRTUv2 24376 }

dpsRTUv2p25376Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 56 is cleared"
	::= { dpsRTUv2 25376 }

dpsRTUv2p24377Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 57 is set"
	::= { dpsRTUv2 24377 }

dpsRTUv2p25377Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 57 is cleared"
	::= { dpsRTUv2 25377 }

dpsRTUv2p24378Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 58 is set"
	::= { dpsRTUv2 24378 }

dpsRTUv2p25378Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 58 is cleared"
	::= { dpsRTUv2 25378 }

dpsRTUv2p24379Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 59 is set"
	::= { dpsRTUv2 24379 }

dpsRTUv2p25379Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 59 is cleared"
	::= { dpsRTUv2 25379 }

dpsRTUv2p24380Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 60 is set"
	::= { dpsRTUv2 24380 }

dpsRTUv2p25380Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 60 is cleared"
	::= { dpsRTUv2 25380 }

dpsRTUv2p24381Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 61 is set"
	::= { dpsRTUv2 24381 }

dpsRTUv2p25381Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 61 is cleared"
	::= { dpsRTUv2 25381 }

dpsRTUv2p24382Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 62 is set"
	::= { dpsRTUv2 24382 }

dpsRTUv2p25382Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 62 is cleared"
	::= { dpsRTUv2 25382 }

dpsRTUv2p24383Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 63 is set"
	::= { dpsRTUv2 24383 }

dpsRTUv2p25383Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 63 is cleared"
	::= { dpsRTUv2 25383 }

dpsRTUv2p24384Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 64 is set"
	::= { dpsRTUv2 24384 }

dpsRTUv2p25384Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 6 point 64 is cleared"
	::= { dpsRTUv2 25384 }

dpsRTUv2p24385Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 1 is set"
	::= { dpsRTUv2 24385 }

dpsRTUv2p25385Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 1 is cleared"
	::= { dpsRTUv2 25385 }

dpsRTUv2p24386Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 2 is set"
	::= { dpsRTUv2 24386 }

dpsRTUv2p25386Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 2 is cleared"
	::= { dpsRTUv2 25386 }

dpsRTUv2p24387Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 3 is set"
	::= { dpsRTUv2 24387 }

dpsRTUv2p25387Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 3 is cleared"
	::= { dpsRTUv2 25387 }

dpsRTUv2p24388Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 4 is set"
	::= { dpsRTUv2 24388 }

dpsRTUv2p25388Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 4 is cleared"
	::= { dpsRTUv2 25388 }

dpsRTUv2p24389Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 5 is set"
	::= { dpsRTUv2 24389 }

dpsRTUv2p25389Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 5 is cleared"
	::= { dpsRTUv2 25389 }

dpsRTUv2p24390Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 6 is set"
	::= { dpsRTUv2 24390 }

dpsRTUv2p25390Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 6 is cleared"
	::= { dpsRTUv2 25390 }

dpsRTUv2p24391Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 7 is set"
	::= { dpsRTUv2 24391 }

dpsRTUv2p25391Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 7 is cleared"
	::= { dpsRTUv2 25391 }

dpsRTUv2p24392Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 8 is set"
	::= { dpsRTUv2 24392 }

dpsRTUv2p25392Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 8 is cleared"
	::= { dpsRTUv2 25392 }

dpsRTUv2p24393Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 9 is set"
	::= { dpsRTUv2 24393 }

dpsRTUv2p25393Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 9 is cleared"
	::= { dpsRTUv2 25393 }

dpsRTUv2p24394Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 10 is set"
	::= { dpsRTUv2 24394 }

dpsRTUv2p25394Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 10 is cleared"
	::= { dpsRTUv2 25394 }

dpsRTUv2p24395Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 11 is set"
	::= { dpsRTUv2 24395 }

dpsRTUv2p25395Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 11 is cleared"
	::= { dpsRTUv2 25395 }

dpsRTUv2p24396Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 12 is set"
	::= { dpsRTUv2 24396 }

dpsRTUv2p25396Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 12 is cleared"
	::= { dpsRTUv2 25396 }

dpsRTUv2p24397Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 13 is set"
	::= { dpsRTUv2 24397 }

dpsRTUv2p25397Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 13 is cleared"
	::= { dpsRTUv2 25397 }

dpsRTUv2p24398Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 14 is set"
	::= { dpsRTUv2 24398 }

dpsRTUv2p25398Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 14 is cleared"
	::= { dpsRTUv2 25398 }

dpsRTUv2p24399Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 15 is set"
	::= { dpsRTUv2 24399 }

dpsRTUv2p25399Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 15 is cleared"
	::= { dpsRTUv2 25399 }

dpsRTUv2p24400Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 16 is set"
	::= { dpsRTUv2 24400 }

dpsRTUv2p25400Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 16 is cleared"
	::= { dpsRTUv2 25400 }

dpsRTUv2p24401Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 17 is set"
	::= { dpsRTUv2 24401 }

dpsRTUv2p25401Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 17 is cleared"
	::= { dpsRTUv2 25401 }

dpsRTUv2p24402Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 18 is set"
	::= { dpsRTUv2 24402 }

dpsRTUv2p25402Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 18 is cleared"
	::= { dpsRTUv2 25402 }

dpsRTUv2p24403Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 19 is set"
	::= { dpsRTUv2 24403 }

dpsRTUv2p25403Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 19 is cleared"
	::= { dpsRTUv2 25403 }

dpsRTUv2p24404Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 20 is set"
	::= { dpsRTUv2 24404 }

dpsRTUv2p25404Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 20 is cleared"
	::= { dpsRTUv2 25404 }

dpsRTUv2p24405Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 21 is set"
	::= { dpsRTUv2 24405 }

dpsRTUv2p25405Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 21 is cleared"
	::= { dpsRTUv2 25405 }

dpsRTUv2p24406Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 22 is set"
	::= { dpsRTUv2 24406 }

dpsRTUv2p25406Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 22 is cleared"
	::= { dpsRTUv2 25406 }

dpsRTUv2p24407Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 23 is set"
	::= { dpsRTUv2 24407 }

dpsRTUv2p25407Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 23 is cleared"
	::= { dpsRTUv2 25407 }

dpsRTUv2p24408Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 24 is set"
	::= { dpsRTUv2 24408 }

dpsRTUv2p25408Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 24 is cleared"
	::= { dpsRTUv2 25408 }

dpsRTUv2p24409Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 25 is set"
	::= { dpsRTUv2 24409 }

dpsRTUv2p25409Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 25 is cleared"
	::= { dpsRTUv2 25409 }

dpsRTUv2p24410Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 26 is set"
	::= { dpsRTUv2 24410 }

dpsRTUv2p25410Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 26 is cleared"
	::= { dpsRTUv2 25410 }

dpsRTUv2p24411Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 27 is set"
	::= { dpsRTUv2 24411 }

dpsRTUv2p25411Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 27 is cleared"
	::= { dpsRTUv2 25411 }

dpsRTUv2p24412Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 28 is set"
	::= { dpsRTUv2 24412 }

dpsRTUv2p25412Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 28 is cleared"
	::= { dpsRTUv2 25412 }

dpsRTUv2p24413Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 29 is set"
	::= { dpsRTUv2 24413 }

dpsRTUv2p25413Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 29 is cleared"
	::= { dpsRTUv2 25413 }

dpsRTUv2p24414Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 30 is set"
	::= { dpsRTUv2 24414 }

dpsRTUv2p25414Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 30 is cleared"
	::= { dpsRTUv2 25414 }

dpsRTUv2p24415Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 31 is set"
	::= { dpsRTUv2 24415 }

dpsRTUv2p25415Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 31 is cleared"
	::= { dpsRTUv2 25415 }

dpsRTUv2p24416Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 32 is set"
	::= { dpsRTUv2 24416 }

dpsRTUv2p25416Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 32 is cleared"
	::= { dpsRTUv2 25416 }

dpsRTUv2p24417Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 33 is set"
	::= { dpsRTUv2 24417 }

dpsRTUv2p25417Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 33 is cleared"
	::= { dpsRTUv2 25417 }

dpsRTUv2p24418Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 34 is set"
	::= { dpsRTUv2 24418 }

dpsRTUv2p25418Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 34 is cleared"
	::= { dpsRTUv2 25418 }

dpsRTUv2p24419Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 35 is set"
	::= { dpsRTUv2 24419 }

dpsRTUv2p25419Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 35 is cleared"
	::= { dpsRTUv2 25419 }

dpsRTUv2p24420Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 36 is set"
	::= { dpsRTUv2 24420 }

dpsRTUv2p25420Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 36 is cleared"
	::= { dpsRTUv2 25420 }

dpsRTUv2p24421Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 37 is set"
	::= { dpsRTUv2 24421 }

dpsRTUv2p25421Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 37 is cleared"
	::= { dpsRTUv2 25421 }

dpsRTUv2p24422Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 38 is set"
	::= { dpsRTUv2 24422 }

dpsRTUv2p25422Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 38 is cleared"
	::= { dpsRTUv2 25422 }

dpsRTUv2p24423Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 39 is set"
	::= { dpsRTUv2 24423 }

dpsRTUv2p25423Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 39 is cleared"
	::= { dpsRTUv2 25423 }

dpsRTUv2p24424Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 40 is set"
	::= { dpsRTUv2 24424 }

dpsRTUv2p25424Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 40 is cleared"
	::= { dpsRTUv2 25424 }

dpsRTUv2p24425Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 41 is set"
	::= { dpsRTUv2 24425 }

dpsRTUv2p25425Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 41 is cleared"
	::= { dpsRTUv2 25425 }

dpsRTUv2p24426Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 42 is set"
	::= { dpsRTUv2 24426 }

dpsRTUv2p25426Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 42 is cleared"
	::= { dpsRTUv2 25426 }

dpsRTUv2p24427Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 43 is set"
	::= { dpsRTUv2 24427 }

dpsRTUv2p25427Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 43 is cleared"
	::= { dpsRTUv2 25427 }

dpsRTUv2p24428Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 44 is set"
	::= { dpsRTUv2 24428 }

dpsRTUv2p25428Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 44 is cleared"
	::= { dpsRTUv2 25428 }

dpsRTUv2p24429Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 45 is set"
	::= { dpsRTUv2 24429 }

dpsRTUv2p25429Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 45 is cleared"
	::= { dpsRTUv2 25429 }

dpsRTUv2p24430Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 46 is set"
	::= { dpsRTUv2 24430 }

dpsRTUv2p25430Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 46 is cleared"
	::= { dpsRTUv2 25430 }

dpsRTUv2p24431Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 47 is set"
	::= { dpsRTUv2 24431 }

dpsRTUv2p25431Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 47 is cleared"
	::= { dpsRTUv2 25431 }

dpsRTUv2p24432Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 48 is set"
	::= { dpsRTUv2 24432 }

dpsRTUv2p25432Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 48 is cleared"
	::= { dpsRTUv2 25432 }

dpsRTUv2p24433Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 49 is set"
	::= { dpsRTUv2 24433 }

dpsRTUv2p25433Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 49 is cleared"
	::= { dpsRTUv2 25433 }

dpsRTUv2p24434Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 50 is set"
	::= { dpsRTUv2 24434 }

dpsRTUv2p25434Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 50 is cleared"
	::= { dpsRTUv2 25434 }

dpsRTUv2p24435Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 51 is set"
	::= { dpsRTUv2 24435 }

dpsRTUv2p25435Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 51 is cleared"
	::= { dpsRTUv2 25435 }

dpsRTUv2p24436Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 52 is set"
	::= { dpsRTUv2 24436 }

dpsRTUv2p25436Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 52 is cleared"
	::= { dpsRTUv2 25436 }

dpsRTUv2p24437Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 53 is set"
	::= { dpsRTUv2 24437 }

dpsRTUv2p25437Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 53 is cleared"
	::= { dpsRTUv2 25437 }

dpsRTUv2p24438Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 54 is set"
	::= { dpsRTUv2 24438 }

dpsRTUv2p25438Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 54 is cleared"
	::= { dpsRTUv2 25438 }

dpsRTUv2p24439Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 55 is set"
	::= { dpsRTUv2 24439 }

dpsRTUv2p25439Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 55 is cleared"
	::= { dpsRTUv2 25439 }

dpsRTUv2p24440Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 56 is set"
	::= { dpsRTUv2 24440 }

dpsRTUv2p25440Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 56 is cleared"
	::= { dpsRTUv2 25440 }

dpsRTUv2p24441Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 57 is set"
	::= { dpsRTUv2 24441 }

dpsRTUv2p25441Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 57 is cleared"
	::= { dpsRTUv2 25441 }

dpsRTUv2p24442Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 58 is set"
	::= { dpsRTUv2 24442 }

dpsRTUv2p25442Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 58 is cleared"
	::= { dpsRTUv2 25442 }

dpsRTUv2p24443Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 59 is set"
	::= { dpsRTUv2 24443 }

dpsRTUv2p25443Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 59 is cleared"
	::= { dpsRTUv2 25443 }

dpsRTUv2p24444Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 60 is set"
	::= { dpsRTUv2 24444 }

dpsRTUv2p25444Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 60 is cleared"
	::= { dpsRTUv2 25444 }

dpsRTUv2p24445Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 61 is set"
	::= { dpsRTUv2 24445 }

dpsRTUv2p25445Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 61 is cleared"
	::= { dpsRTUv2 25445 }

dpsRTUv2p24446Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 62 is set"
	::= { dpsRTUv2 24446 }

dpsRTUv2p25446Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 62 is cleared"
	::= { dpsRTUv2 25446 }

dpsRTUv2p24447Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 63 is set"
	::= { dpsRTUv2 24447 }

dpsRTUv2p25447Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 63 is cleared"
	::= { dpsRTUv2 25447 }

dpsRTUv2p24448Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 64 is set"
	::= { dpsRTUv2 24448 }

dpsRTUv2p25448Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 7 point 64 is cleared"
	::= { dpsRTUv2 25448 }

dpsRTUv2p24449Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 1 is set"
	::= { dpsRTUv2 24449 }

dpsRTUv2p25449Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 1 is cleared"
	::= { dpsRTUv2 25449 }

dpsRTUv2p24450Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 2 is set"
	::= { dpsRTUv2 24450 }

dpsRTUv2p25450Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 2 is cleared"
	::= { dpsRTUv2 25450 }

dpsRTUv2p24451Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 3 is set"
	::= { dpsRTUv2 24451 }

dpsRTUv2p25451Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 3 is cleared"
	::= { dpsRTUv2 25451 }

dpsRTUv2p24452Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 4 is set"
	::= { dpsRTUv2 24452 }

dpsRTUv2p25452Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 4 is cleared"
	::= { dpsRTUv2 25452 }

dpsRTUv2p24453Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 5 is set"
	::= { dpsRTUv2 24453 }

dpsRTUv2p25453Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 5 is cleared"
	::= { dpsRTUv2 25453 }

dpsRTUv2p24454Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 6 is set"
	::= { dpsRTUv2 24454 }

dpsRTUv2p25454Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 6 is cleared"
	::= { dpsRTUv2 25454 }

dpsRTUv2p24455Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 7 is set"
	::= { dpsRTUv2 24455 }

dpsRTUv2p25455Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 7 is cleared"
	::= { dpsRTUv2 25455 }

dpsRTUv2p24456Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 8 is set"
	::= { dpsRTUv2 24456 }

dpsRTUv2p25456Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 8 is cleared"
	::= { dpsRTUv2 25456 }

dpsRTUv2p24457Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 9 is set"
	::= { dpsRTUv2 24457 }

dpsRTUv2p25457Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 9 is cleared"
	::= { dpsRTUv2 25457 }

dpsRTUv2p24458Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 10 is set"
	::= { dpsRTUv2 24458 }

dpsRTUv2p25458Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 10 is cleared"
	::= { dpsRTUv2 25458 }

dpsRTUv2p24459Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 11 is set"
	::= { dpsRTUv2 24459 }

dpsRTUv2p25459Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 11 is cleared"
	::= { dpsRTUv2 25459 }

dpsRTUv2p24460Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 12 is set"
	::= { dpsRTUv2 24460 }

dpsRTUv2p25460Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 12 is cleared"
	::= { dpsRTUv2 25460 }

dpsRTUv2p24461Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 13 is set"
	::= { dpsRTUv2 24461 }

dpsRTUv2p25461Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 13 is cleared"
	::= { dpsRTUv2 25461 }

dpsRTUv2p24462Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 14 is set"
	::= { dpsRTUv2 24462 }

dpsRTUv2p25462Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 14 is cleared"
	::= { dpsRTUv2 25462 }

dpsRTUv2p24463Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 15 is set"
	::= { dpsRTUv2 24463 }

dpsRTUv2p25463Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 15 is cleared"
	::= { dpsRTUv2 25463 }

dpsRTUv2p24464Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 16 is set"
	::= { dpsRTUv2 24464 }

dpsRTUv2p25464Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 16 is cleared"
	::= { dpsRTUv2 25464 }

dpsRTUv2p24465Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 17 is set"
	::= { dpsRTUv2 24465 }

dpsRTUv2p25465Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 17 is cleared"
	::= { dpsRTUv2 25465 }

dpsRTUv2p24466Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 18 is set"
	::= { dpsRTUv2 24466 }

dpsRTUv2p25466Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 18 is cleared"
	::= { dpsRTUv2 25466 }

dpsRTUv2p24467Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 19 is set"
	::= { dpsRTUv2 24467 }

dpsRTUv2p25467Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 19 is cleared"
	::= { dpsRTUv2 25467 }

dpsRTUv2p24468Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 20 is set"
	::= { dpsRTUv2 24468 }

dpsRTUv2p25468Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 20 is cleared"
	::= { dpsRTUv2 25468 }

dpsRTUv2p24469Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 21 is set"
	::= { dpsRTUv2 24469 }

dpsRTUv2p25469Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 21 is cleared"
	::= { dpsRTUv2 25469 }

dpsRTUv2p24470Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 22 is set"
	::= { dpsRTUv2 24470 }

dpsRTUv2p25470Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 22 is cleared"
	::= { dpsRTUv2 25470 }

dpsRTUv2p24471Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 23 is set"
	::= { dpsRTUv2 24471 }

dpsRTUv2p25471Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 23 is cleared"
	::= { dpsRTUv2 25471 }

dpsRTUv2p24472Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 24 is set"
	::= { dpsRTUv2 24472 }

dpsRTUv2p25472Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 24 is cleared"
	::= { dpsRTUv2 25472 }

dpsRTUv2p24473Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 25 is set"
	::= { dpsRTUv2 24473 }

dpsRTUv2p25473Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 25 is cleared"
	::= { dpsRTUv2 25473 }

dpsRTUv2p24474Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 26 is set"
	::= { dpsRTUv2 24474 }

dpsRTUv2p25474Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 26 is cleared"
	::= { dpsRTUv2 25474 }

dpsRTUv2p24475Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 27 is set"
	::= { dpsRTUv2 24475 }

dpsRTUv2p25475Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 27 is cleared"
	::= { dpsRTUv2 25475 }

dpsRTUv2p24476Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 28 is set"
	::= { dpsRTUv2 24476 }

dpsRTUv2p25476Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 28 is cleared"
	::= { dpsRTUv2 25476 }

dpsRTUv2p24477Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 29 is set"
	::= { dpsRTUv2 24477 }

dpsRTUv2p25477Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 29 is cleared"
	::= { dpsRTUv2 25477 }

dpsRTUv2p24478Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 30 is set"
	::= { dpsRTUv2 24478 }

dpsRTUv2p25478Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 30 is cleared"
	::= { dpsRTUv2 25478 }

dpsRTUv2p24479Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 31 is set"
	::= { dpsRTUv2 24479 }

dpsRTUv2p25479Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 31 is cleared"
	::= { dpsRTUv2 25479 }

dpsRTUv2p24480Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 32 is set"
	::= { dpsRTUv2 24480 }

dpsRTUv2p25480Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 32 is cleared"
	::= { dpsRTUv2 25480 }

dpsRTUv2p24481Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 33 is set"
	::= { dpsRTUv2 24481 }

dpsRTUv2p25481Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 33 is cleared"
	::= { dpsRTUv2 25481 }

dpsRTUv2p24482Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 34 is set"
	::= { dpsRTUv2 24482 }

dpsRTUv2p25482Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 34 is cleared"
	::= { dpsRTUv2 25482 }

dpsRTUv2p24483Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 35 is set"
	::= { dpsRTUv2 24483 }

dpsRTUv2p25483Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 35 is cleared"
	::= { dpsRTUv2 25483 }

dpsRTUv2p24484Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 36 is set"
	::= { dpsRTUv2 24484 }

dpsRTUv2p25484Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 36 is cleared"
	::= { dpsRTUv2 25484 }

dpsRTUv2p24485Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 37 is set"
	::= { dpsRTUv2 24485 }

dpsRTUv2p25485Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 37 is cleared"
	::= { dpsRTUv2 25485 }

dpsRTUv2p24486Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 38 is set"
	::= { dpsRTUv2 24486 }

dpsRTUv2p25486Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 38 is cleared"
	::= { dpsRTUv2 25486 }

dpsRTUv2p24487Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 39 is set"
	::= { dpsRTUv2 24487 }

dpsRTUv2p25487Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 39 is cleared"
	::= { dpsRTUv2 25487 }

dpsRTUv2p24488Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 40 is set"
	::= { dpsRTUv2 24488 }

dpsRTUv2p25488Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 40 is cleared"
	::= { dpsRTUv2 25488 }

dpsRTUv2p24489Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 41 is set"
	::= { dpsRTUv2 24489 }

dpsRTUv2p25489Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 41 is cleared"
	::= { dpsRTUv2 25489 }

dpsRTUv2p24490Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 42 is set"
	::= { dpsRTUv2 24490 }

dpsRTUv2p25490Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 42 is cleared"
	::= { dpsRTUv2 25490 }

dpsRTUv2p24491Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 43 is set"
	::= { dpsRTUv2 24491 }

dpsRTUv2p25491Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 43 is cleared"
	::= { dpsRTUv2 25491 }

dpsRTUv2p24492Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 44 is set"
	::= { dpsRTUv2 24492 }

dpsRTUv2p25492Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 44 is cleared"
	::= { dpsRTUv2 25492 }

dpsRTUv2p24493Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 45 is set"
	::= { dpsRTUv2 24493 }

dpsRTUv2p25493Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 45 is cleared"
	::= { dpsRTUv2 25493 }

dpsRTUv2p24494Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 46 is set"
	::= { dpsRTUv2 24494 }

dpsRTUv2p25494Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 46 is cleared"
	::= { dpsRTUv2 25494 }

dpsRTUv2p24495Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 47 is set"
	::= { dpsRTUv2 24495 }

dpsRTUv2p25495Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 47 is cleared"
	::= { dpsRTUv2 25495 }

dpsRTUv2p24496Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 48 is set"
	::= { dpsRTUv2 24496 }

dpsRTUv2p25496Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 48 is cleared"
	::= { dpsRTUv2 25496 }

dpsRTUv2p24497Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 49 is set"
	::= { dpsRTUv2 24497 }

dpsRTUv2p25497Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 49 is cleared"
	::= { dpsRTUv2 25497 }

dpsRTUv2p24498Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 50 is set"
	::= { dpsRTUv2 24498 }

dpsRTUv2p25498Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 50 is cleared"
	::= { dpsRTUv2 25498 }

dpsRTUv2p24499Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 51 is set"
	::= { dpsRTUv2 24499 }

dpsRTUv2p25499Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 51 is cleared"
	::= { dpsRTUv2 25499 }

dpsRTUv2p24500Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 52 is set"
	::= { dpsRTUv2 24500 }

dpsRTUv2p25500Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 52 is cleared"
	::= { dpsRTUv2 25500 }

dpsRTUv2p24501Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 53 is set"
	::= { dpsRTUv2 24501 }

dpsRTUv2p25501Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 53 is cleared"
	::= { dpsRTUv2 25501 }

dpsRTUv2p24502Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 54 is set"
	::= { dpsRTUv2 24502 }

dpsRTUv2p25502Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 54 is cleared"
	::= { dpsRTUv2 25502 }

dpsRTUv2p24503Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 55 is set"
	::= { dpsRTUv2 24503 }

dpsRTUv2p25503Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 55 is cleared"
	::= { dpsRTUv2 25503 }

dpsRTUv2p24504Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 56 is set"
	::= { dpsRTUv2 24504 }

dpsRTUv2p25504Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 56 is cleared"
	::= { dpsRTUv2 25504 }

dpsRTUv2p24505Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 57 is set"
	::= { dpsRTUv2 24505 }

dpsRTUv2p25505Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 57 is cleared"
	::= { dpsRTUv2 25505 }

dpsRTUv2p24506Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 58 is set"
	::= { dpsRTUv2 24506 }

dpsRTUv2p25506Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 58 is cleared"
	::= { dpsRTUv2 25506 }

dpsRTUv2p24507Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 59 is set"
	::= { dpsRTUv2 24507 }

dpsRTUv2p25507Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 59 is cleared"
	::= { dpsRTUv2 25507 }

dpsRTUv2p24508Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 60 is set"
	::= { dpsRTUv2 24508 }

dpsRTUv2p25508Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 60 is cleared"
	::= { dpsRTUv2 25508 }

dpsRTUv2p24509Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 61 is set"
	::= { dpsRTUv2 24509 }

dpsRTUv2p25509Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 61 is cleared"
	::= { dpsRTUv2 25509 }

dpsRTUv2p24510Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 62 is set"
	::= { dpsRTUv2 24510 }

dpsRTUv2p25510Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 62 is cleared"
	::= { dpsRTUv2 25510 }

dpsRTUv2p24511Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 63 is set"
	::= { dpsRTUv2 24511 }

dpsRTUv2p25511Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 63 is cleared"
	::= { dpsRTUv2 25511 }

dpsRTUv2p24512Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 64 is set"
	::= { dpsRTUv2 24512 }

dpsRTUv2p25512Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 8 display 8 point 64 is cleared"
	::= { dpsRTUv2 25512 }
 
 END
