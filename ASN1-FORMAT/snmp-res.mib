SNMP-RESEARCH-MIB DEFINITIONS ::= BEGIN

-- The top node
snmpResearch  OBJECT IDENTIFIER ::= { 1 3 6 1 4 1 99 }

--
-- snmpResearch.1:  SNMP Research Products
--
snmpResearchNode  OBJECT IDENTIFIER ::= { 1 3 6 1 4 1 99 1 }

-- SNMP Research Agents
snmpResearchAgent OBJECT IDENTIFIER ::= { 1 3 6 1 4 1 99 1 1 }

-- UNIX
snmpResearchUNIXAgent OBJECT IDENTIFIER ::= { 1 3 6 1 4 1 99 1 1 1 }
snmpResearchSnmpd OBJECT IDENTIFIER ::= { 1 3 6 1 4 1 99 1 1 1 1 }

-- Proxies
snmpResearchProxyAgent  OBJECT IDENTIFIER ::= { 1 3 6 1 4 1 99 1 1 2 }
snmpResearchLb100Proxy  OBJECT IDENTIFIER ::= { 1 3 6 1 4 1 99 1 1 2 1 }

-- All of the snmpResearchDogProxy and snmpResearchTcuProxy objects
-- removed.  Do not use these branch of the tree.
-- snmpResearchDogProxy OBJECT IDENTIFIER ::= { 1 3 6 1 4 1 99 1 1 2 2 }
-- snmpResearchTcuProxy OBJECT IDENTIFIER ::= { 1 3 6 1 4 1 99 1 1 2 3 }

-- EMANATE Master Agent
snmpResearchEMANATEMasterAgent OBJECT IDENTIFIER ::= { 1 3 6 1 4 1 99 1 1 3 }

-- EMANATE Master Agents on Various OSs
solarisEMANATEMasterAgent      OBJECT IDENTIFIER ::= { 1 3 6 1 4 1 99 1 1 3 1 }
solarisTCPEMANATEMasterAgent   OBJECT IDENTIFIER ::= { 1 3 6 1 4 1 99 1 1 3 2 }
solarisx86TCPEMANATEMasterAgent OBJECT IDENTIFIER ::= { 1 3 6 1 4 1 99 1 1 3 3 }
sunosEMANATEMasterAgent        OBJECT IDENTIFIER ::= { 1 3 6 1 4 1 99 1 1 3 4 }
dguxEMANATEMasterAgent         OBJECT IDENTIFIER ::= { 1 3 6 1 4 1 99 1 1 3 5 }
hpuxEMANATEMasterAgent         OBJECT IDENTIFIER ::= { 1 3 6 1 4 1 99 1 1 3 6 }
vxworksEMANATEMasterAgent      OBJECT IDENTIFIER ::= { 1 3 6 1 4 1 99 1 1 3 7 }
hprtEMANATEMasterAgent         OBJECT IDENTIFIER ::= { 1 3 6 1 4 1 99 1 1 3 8 }
aixEMANATEMasterAgent          OBJECT IDENTIFIER ::= { 1 3 6 1 4 1 99 1 1 3 9 }
sco3EMANATEMasterAgent         OBJECT IDENTIFIER ::= { 1 3 6 1 4 1 99 1 1 3 10 }
ntEMANATEMasterAgent           OBJECT IDENTIFIER ::= { 1 3 6 1 4 1 99 1 1 3 11 }
win31EMANATEMasterAgent        OBJECT IDENTIFIER ::= { 1 3 6 1 4 1 99 1 1 3 12 }
dynixEMANATEMasterAgent        OBJECT IDENTIFIER ::= { 1 3 6 1 4 1 99 1 1 3 13 }
osf1EMANATEMasterAgent         OBJECT IDENTIFIER ::= { 1 3 6 1 4 1 99 1 1 3 14 }
ncrEMANATEMasterAgent          OBJECT IDENTIFIER ::= { 1 3 6 1 4 1 99 1 1 3 15 }
sco5EMANATEMasterAgent         OBJECT IDENTIFIER ::= { 1 3 6 1 4 1 99 1 1 3 16 }
solarisx86EMANATEMasterAgent   OBJECT IDENTIFIER ::= { 1 3 6 1 4 1 99 1 1 3 17 }
irixEMANATEMasterAgent         OBJECT IDENTIFIER ::= { 1 3 6 1 4 1 99 1 1 3 19 }
os2EMANATEMasterAgent          OBJECT IDENTIFIER ::= { 1 3 6 1 4 1 99 1 1 3 20 }
unixwareEMANATEMasterAgent     OBJECT IDENTIFIER ::= { 1 3 6 1 4 1 99 1 1 3 21 }
bsdiEMANATEMasterAgent         OBJECT IDENTIFIER ::= { 1 3 6 1 4 1 99 1 1 3 22 }
sinixEMANATEMasterAgent        OBJECT IDENTIFIER ::= { 1 3 6 1 4 1 99 1 1 3 23 }
ftxEMANATEMasterAgent          OBJECT IDENTIFIER ::= { 1 3 6 1 4 1 99 1 1 3 24 }
hpux10EMANATEMasterAgent       OBJECT IDENTIFIER ::= { 1 3 6 1 4 1 99 1 1 3 25 }
-- BlueCoatEMANATEMasterAgent    OBJECT IDENTIFIER ::= { 1 3 6 1 4 1 99 1 1 3 26 }

-- LATIN Agents
snmpResearchLTxxxAgent       OBJECT IDENTIFIER ::= { 1 3 6 1 4 1 99 1 1 4 }
snmpResearchLT301Agent       OBJECT IDENTIFIER ::= { 1 3 6 1 4 1 99 1 1 4 1 }
-- snmpResearchLT301AgentE   OBJECT IDENTIFIER ::= { 1 3 6 1 4 1 99 1 1 4 1 1 }
-- snmpResearchLT301AgentW   OBJECT IDENTIFIER ::= { 1 3 6 1 4 1 99 1 1 4 1 2 }
-- snmpResearchLT301AgentEW  OBJECT IDENTIFIER ::= { 1 3 6 1 4 1 99 1 1 4 1 3 }
-- snmpResearchLT301AgentM   OBJECT IDENTIFIER ::= { 1 3 6 1 4 1 99 1 1 4 1 4 }
-- snmpResearchLT301AgentME  OBJECT IDENTIFIER ::= { 1 3 6 1 4 1 99 1 1 4 1 5 }
-- snmpResearchLT301AgentMW  OBJECT IDENTIFIER ::= { 1 3 6 1 4 1 99 1 1 4 1 6 }
-- snmpResearchLT301AgentMEW OBJECT IDENTIFIER ::= { 1 3 6 1 4 1 99 1 1 4 1 7 }

--
-- snmpResearch.2:  SNMP Research MIBs
--
snmpResearchVarVersion OBJECT IDENTIFIER ::= { 1 3 6 1 4 1 99 2 }

-- Nothing under the first branch of the SNMP Research MIBs tree
-- is used at all.
snmpResearchVarVer1 OBJECT IDENTIFIER ::= { 1 3 6 1 4 1 99 2 1 }
snmpResearchVarLb100 OBJECT IDENTIFIER ::= { 1 3 6 1 4 1 99 2 1 1 }
lb100PktTrans  OBJECT IDENTIFIER ::= { 1 3 6 1 4 1 99 2 1 1 1 }
lb100PktRecv  OBJECT IDENTIFIER ::= { 1 3 6 1 4 1 99 2 1 1 2 }
lb100Seconds  OBJECT IDENTIFIER ::= { 1 3 6 1 4 1 99 2 1 1 3 }

--
-- snmpResearch.3:  historic and not reusable
--
--snmpResearchFunctions OBJECT IDENTIFIER ::= { 1 3 6 1 4 1 99 3 }
--functAdd  OBJECT IDENTIFIER ::= { 1 3 6 1 4 1 99 3 1 }
--functSub  OBJECT IDENTIFIER ::= { 1 3 6 1 4 1 99 3 2 }
--functMul  OBJECT IDENTIFIER ::= { 1 3 6 1 4 1 99 3 3 }
--functIdiv  OBJECT IDENTIFIER ::= { 1 3 6 1 4 1 99 3 4 }
--functMod  OBJECT IDENTIFIER ::= { 1 3 6 1 4 1 99 3 5 }
--functNeg  OBJECT IDENTIFIER ::= { 1 3 6 1 4 1 99 3 6 }
--functAbs  OBJECT IDENTIFIER ::= { 1 3 6 1 4 1 99 3 7 }
--functSgn  OBJECT IDENTIFIER ::= { 1 3 6 1 4 1 99 3 8 }
--functMax  OBJECT IDENTIFIER ::= { 1 3 6 1 4 1 99 3 9 }
--functMin  OBJECT IDENTIFIER ::= { 1 3 6 1 4 1 99 3 10 }
--functAnd  OBJECT IDENTIFIER ::= { 1 3 6 1 4 1 99 3 11 }
--functOr   OBJECT IDENTIFIER ::= { 1 3 6 1 4 1 99 3 12 }
--functNot  OBJECT IDENTIFIER ::= { 1 3 6 1 4 1 99 3 13 }
--functExch  OBJECT IDENTIFIER ::= { 1 3 6 1 4 1 99 3 14 }
--functClear  OBJECT IDENTIFIER ::= { 1 3 6 1 4 1 99 3 15 }
--functDup  OBJECT IDENTIFIER ::= { 1 3 6 1 4 1 99 3 16 }
--functPop  OBJECT IDENTIFIER ::= { 1 3 6 1 4 1 99 3 17 }

--
-- snmpResearch.4:  historic and not reusable
--
--expressions  OBJECT IDENTIFIER ::= { 1 3 6 1 4 1 99 4 }
--expressionNumber OBJECT IDENTIFIER ::= { 1 3 6 1 4 1 99 4 1 }
--expressionTable  OBJECT IDENTIFIER ::= { 1 3 6 1 4 1 99 4 2 }
--expressionEntry  OBJECT IDENTIFIER ::= { 1 3 6 1 4 1 99 4 2 1 }
--expressionIndex  OBJECT IDENTIFIER ::= { 1 3 6 1 4 1 99 4 2 1 1 }
--expressionEval  OBJECT IDENTIFIER ::= { 1 3 6 1 4 1 99 4 2 1 2 }
--expressionExpression OBJECT IDENTIFIER ::= { 1 3 6 1 4 1 99 4 2 1 3 }
--expressionStatus OBJECT IDENTIFIER ::= { 1 3 6 1 4 1 99 4 2 1 4 }
--expressionHint  OBJECT IDENTIFIER ::= { 1 3 6 1 4 1 99 4 2 1 5 }

--
-- snmpResearch.5:  unused
--

--
-- snmpResearch.6:  unused
--

--
-- snmpResearch.7:  unused
--

--
-- snmpResearch.8:  unused
--

--
-- snmpResearch.9:  unused
--

--
-- snmpResearch.10:  used in the past and not reusable
--
-- These OIDs were used in conjunction with the now historic
-- party-based SNMPv2.
--jmka1  OBJECT IDENTIFIER ::= { 1 3 6 1 4 1 99 10 1 4 45 113 10 1 1 }
--kajm2  OBJECT IDENTIFIER ::= { 1 3 6 1 4 1 99 10 1 4 45 113 10 1 2 }
--jmka3  OBJECT IDENTIFIER ::= { 1 3 6 1 4 1 99 10 1 4 45 113 10 1 3 }
--kajm4  OBJECT IDENTIFIER ::= { 1 3 6 1 4 1 99 10 1 4 45 113 10 1 4 }
--jmka5  OBJECT IDENTIFIER ::= { 1 3 6 1 4 1 99 10 1 4 45 113 10 1 5 }
--kajm6  OBJECT IDENTIFIER ::= { 1 3 6 1 4 1 99 10 1 4 45 113 10 1 6 }
--smja1  OBJECT IDENTIFIER ::= { 1 3 6 1 4 1 99 10 1 4 128 169 4 4 1 1 }
--jasm2  OBJECT IDENTIFIER ::= { 1 3 6 1 4 1 99 10 1 4 128 169 4 4 1 2 }
--smja3  OBJECT IDENTIFIER ::= { 1 3 6 1 4 1 99 10 1 4 128 169 4 4 1 3 }
--jasm4  OBJECT IDENTIFIER ::= { 1 3 6 1 4 1 99 10 1 4 128 169 4 4 1 4 }
--smja5  OBJECT IDENTIFIER ::= { 1 3 6 1 4 1 99 10 1 4 128 169 4 4 1 5 }
--jasm6  OBJECT IDENTIFIER ::= { 1 3 6 1 4 1 99 10 1 4 128 169 4 4 1 6 }
--mmja1  OBJECT IDENTIFIER ::= { 1 3 6 1 4 1 99 10 1 4 128 169 4 4 2 1 }
--jamm2  OBJECT IDENTIFIER ::= { 1 3 6 1 4 1 99 10 1 4 128 169 4 4 2 2 }
--mmja3  OBJECT IDENTIFIER ::= { 1 3 6 1 4 1 99 10 1 4 128 169 4 4 2 3 }
--jamm4  OBJECT IDENTIFIER ::= { 1 3 6 1 4 1 99 10 1 4 128 169 4 4 2 4 }
--mmja5  OBJECT IDENTIFIER ::= { 1 3 6 1 4 1 99 10 1 4 128 169 4 4 2 5 }
--jamm6  OBJECT IDENTIFIER ::= { 1 3 6 1 4 1 99 10 1 4 128 169 4 4 2 6 }
--kmja1  OBJECT IDENTIFIER ::= { 1 3 6 1 4 1 99 10 1 4 128 169 4 4 3 1 }
--jakm2  OBJECT IDENTIFIER ::= { 1 3 6 1 4 1 99 10 1 4 128 169 4 4 3 2 }
--kmja3  OBJECT IDENTIFIER ::= { 1 3 6 1 4 1 99 10 1 4 128 169 4 4 3 3 }
--jakm4  OBJECT IDENTIFIER ::= { 1 3 6 1 4 1 99 10 1 4 128 169 4 4 3 4 }
--kmja5  OBJECT IDENTIFIER ::= { 1 3 6 1 4 1 99 10 1 4 128 169 4 4 3 5 }
--jakm6  OBJECT IDENTIFIER ::= { 1 3 6 1 4 1 99 10 1 4 128 169 4 4 3 6 }
--jmja1  OBJECT IDENTIFIER ::= { 1 3 6 1 4 1 99 10 1 4 128 169 4 4 4 1 }
--jajm2  OBJECT IDENTIFIER ::= { 1 3 6 1 4 1 99 10 1 4 128 169 4 4 4 2 }
--jmja3  OBJECT IDENTIFIER ::= { 1 3 6 1 4 1 99 10 1 4 128 169 4 4 4 3 }
--jajm4  OBJECT IDENTIFIER ::= { 1 3 6 1 4 1 99 10 1 4 128 169 4 4 4 4 }
--jmja5  OBJECT IDENTIFIER ::= { 1 3 6 1 4 1 99 10 1 4 128 169 4 4 4 5 }
--jajm6  OBJECT IDENTIFIER ::= { 1 3 6 1 4 1 99 10 1 4 128 169 4 4 4 6 }
--jmma1  OBJECT IDENTIFIER ::= { 1 3 6 1 4 1 99 10 1 4 192 103 140 1 1 }
--majm2  OBJECT IDENTIFIER ::= { 1 3 6 1 4 1 99 10 1 4 192 103 140 1 2 }
--jmma3  OBJECT IDENTIFIER ::= { 1 3 6 1 4 1 99 10 1 4 192 103 140 1 3 }
--majm4  OBJECT IDENTIFIER ::= { 1 3 6 1 4 1 99 10 1 4 192 103 140 1 4 }
--jmma5  OBJECT IDENTIFIER ::= { 1 3 6 1 4 1 99 10 1 4 192 103 140 1 5 }
--majm6  OBJECT IDENTIFIER ::= { 1 3 6 1 4 1 99 10 1 4 192 103 140 1 6 }

--
-- snmpResearch.11:  unused
--

--
-- snmpResearch.12:  branch in which we register all of our MIBs
--
snmpResearchMIBs OBJECT IDENTIFIER ::= { 1 3 6 1 4 1 99 12 }

psMIB            OBJECT IDENTIFIER ::= { 1 3 6 1 4 1 99 12 2 }
testMIB          OBJECT IDENTIFIER ::= { 1 3 6 1 4 1 99 12 3 }
snmpResearchload OBJECT IDENTIFIER ::= { 1 3 6 1 4 1 99 12 4 }
oldExamples      OBJECT IDENTIFIER ::= { 1 3 6 1 4 1 99 12 5 }
instregExample   OBJECT IDENTIFIER ::= { 1 3 6 1 4 1 99 12 5 1}
dmiTestMIB       OBJECT IDENTIFIER ::= { 1 3 6 1 4 1 99 12 6 }
emacs2           OBJECT IDENTIFIER ::= { 1 3 6 1 4 1 99 12 7 }
sample           OBJECT IDENTIFIER ::= { 1 3 6 1 4 1 99 12 8 }
etc              OBJECT IDENTIFIER ::= { 1 3 6 1 4 1 99 12 9 }

-- Private:  Do not use.
spakes           OBJECT IDENTIFIER ::= { 1 3 6 1 4 1 99 12 10 }

demo             OBJECT IDENTIFIER ::= { 1 3 6 1 4 1 99 12 12 }
newV2ip          OBJECT IDENTIFIER ::= { 1 3 6 1 4 1 99 12 13 }
newV2udp         OBJECT IDENTIFIER ::= { 1 3 6 1 4 1 99 12 14 }
newV2tcp         OBJECT IDENTIFIER ::= { 1 3 6 1 4 1 99 12 15 }
clusterMIB       OBJECT IDENTIFIER ::= { 1 3 6 1 4 1 99 12 16 }

-- Top levels in instance-level reservation objects
instanceRep          OBJECT IDENTIFIER ::= { 1 3 6 1 4 1 99 12 17 }
instance             OBJECT IDENTIFIER ::= { 1 3 6 1 4 1 99 12 17 1 }
instanceInstanceBase OBJECT IDENTIFIER ::= { 1 3 6 1 4 1 99 12 17 2 }
instanceTypeBase     OBJECT IDENTIFIER ::= { 1 3 6 1 4 1 99 12 17 3 }

-- Very basic BRASS OIDs
brassMIB               OBJECT IDENTIFIER ::= { 1 3 6 1 4 1 99 12 18 }
brassDefaultDefaultsExpiry OBJECT IDENTIFIER ::= { 1 3 6 1 4 1 99 12 18 1 }
brassTransportsTable   OBJECT IDENTIFIER ::= { 1 3 6 1 4 1 99 12 18 2 }
brassDefaultsTable     OBJECT IDENTIFIER ::= { 1 3 6 1 4 1 99 12 18 3 }

--
-- snmpResearch.12.19:  branch in which we register all of our MIBs
--
-- the SNMP Research example MIBs for showing product capabilities
-- are found in this branch
srExamples       OBJECT IDENTIFIER ::= { 1 3 6 1 4 1 99 12 19 }

-- MIBs showing general (basic) product capabilities
srBasics         OBJECT IDENTIFIER ::= { 1 3 6 1 4 1 99 12 19 1 }

srScalars        OBJECT IDENTIFIER ::= { 1 3 6 1 4 1 99 12 19 1 1 }

srScalarGet      OBJECT IDENTIFIER ::= { 1 3 6 1 4 1 99 12 19 1 1 1 }
srInteger        OBJECT IDENTIFIER ::= { 1 3 6 1 4 1 99 12 19 1 1 1 1 }
thermometer      OBJECT IDENTIFIER ::= { 1 3 6 1 4 1 99 12 19 1 1 1 1 1 }
srOctetString    OBJECT IDENTIFIER ::= { 1 3 6 1 4 1 99 12 19 1 1 1 2 }
typesetter       OBJECT IDENTIFIER ::= { 1 3 6 1 4 1 99 12 19 1 1 1 2 1 }
srOID            OBJECT IDENTIFIER ::= { 1 3 6 1 4 1 99 12 19 1 1 1 3 }
trapMonitor      OBJECT IDENTIFIER ::= { 1 3 6 1 4 1 99 12 19 1 1 1 3 1 }
srDateAndTime    OBJECT IDENTIFIER ::= { 1 3 6 1 4 1 99 12 19 1 1 1 23 }
chronometer      OBJECT IDENTIFIER ::= { 1 3 6 1 4 1 99 12 19 1 1 1 23 1 }

srScalarSet         OBJECT IDENTIFIER ::= { 1 3 6 1 4 1 99 12 19 1 1 2 }
thermostat          OBJECT IDENTIFIER ::= { 1 3 6 1 4 1 99 12 19 1 1 2 1 }

srTables            OBJECT IDENTIFIER ::= { 1 3 6 1 4 1 99 12 19 1 2 }
srTableRowCreation  OBJECT IDENTIFIER ::= { 1 3 6 1 4 1 99 12 19 1 2 3 }
vcr                 OBJECT IDENTIFIER ::= { 1 3 6 1 4 1 99 12 19 1 2 3 1 }

srTraps             OBJECT IDENTIFIER ::= { 1 3 6 1 4 1 99 12 19 1 3 }
surgeProtector      OBJECT IDENTIFIER ::= { 1 3 6 1 4 1 99 12 19 1 3 1 }
srTrapDestinationMIB OBJECT IDENTIFIER ::= { 1 3 6 1 4 1 99 12 19 1 3 2 }
srTrapObjectReadTrap OBJECT IDENTIFIER ::= { 1 3 6 1 4 1 99 12 19 1 3 2 1 3 1 }
srTrapObjectWrittenTrap OBJECT IDENTIFIER ::= { 1 3 6 1 4 1 99 12 19 1 3 2 1 3 2
}

-- MIBs showing product-specific capabilities
srProductFeatures OBJECT IDENTIFIER ::= { 1 3 6 1 4 1 99 12 19 2 }

srGetVar           OBJECT IDENTIFIER ::= { 1 3 6 1 4 1 99 12 19 2 1 }
mirror             OBJECT IDENTIFIER ::= { 1 3 6 1 4 1 99 12 19 2 1 1 }
srFd               OBJECT IDENTIFIER ::= { 1 3 6 1 4 1 99 12 19 2 2 }
stream             OBJECT IDENTIFIER ::= { 1 3 6 1 4 1 99 12 19 2 2 1 }
srSignal           OBJECT IDENTIFIER ::= { 1 3 6 1 4 1 99 12 19 2 3 }
signalCounter      OBJECT IDENTIFIER ::= { 1 3 6 1 4 1 99 12 19 2 3 1 }
srInstance         OBJECT IDENTIFIER ::= { 1 3 6 1 4 1 99 12 19 2 4 }
card               OBJECT IDENTIFIER ::= { 1 3 6 1 4 1 99 12 19 2 4 1 }
srLateRegistration OBJECT IDENTIFIER ::= { 1 3 6 1 4 1 99 12 19 2 5 }
addOn              OBJECT IDENTIFIER ::= { 1 3 6 1 4 1 99 12 19 2 5 1 }

--
-- snmpResearch.12.19.3 should no longer be used
--
srOldStuff         OBJECT IDENTIFIER ::= { 1 3 6 1 4 1 99 12 19 3 }

-- Private:  Do not use.
moulton          OBJECT IDENTIFIER ::= { 1 3 6 1 4 1 99 12 20 }

-- various product MIBs
latin            OBJECT IDENTIFIER ::= { 1 3 6 1 4 1 99 12 21 }
latinGeneralInfo OBJECT IDENTIFIER ::= { 1 3 6 1 4 1 99 12 21 1 }
latinRecord      OBJECT IDENTIFIER ::= { 1 3 6 1 4 1 99 12 21 2 }
latinFilter      OBJECT IDENTIFIER ::= { 1 3 6 1 4 1 99 12 21 3 }
latinEvent       OBJECT IDENTIFIER ::= { 1 3 6 1 4 1 99 12 21 4 }
latinTraps       OBJECT IDENTIFIER ::= { 1 3 6 1 4 1 99 12 21 5 }

-- the Windows 95/NT Subagent Adapter
msnsa            OBJECT IDENTIFIER ::= { 1 3 6 1 4 1 99 12 22 }

processControl   OBJECT IDENTIFIER ::= { 1 3 6 1 4 1 99 12 23 }
-- retired:  htmlPage       OBJECT IDENTIFIER ::= { 1 3 6 1 4 1 99 12 24 }
ltHardware       OBJECT IDENTIFIER ::= { 1 3 6 1 4 1 99 12 25 }

-- Private:  Do not use.
larsViklund      OBJECT IDENTIFIER ::= { 1 3 6 1 4 1 99 12 26 }

alias            OBJECT IDENTIFIER ::= { 1 3 6 1 4 1 99 12 27 }
softTrap         OBJECT IDENTIFIER ::= { 1 3 6 1 4 1 99 12 28 }

-- Critical Application MIB
critApp          OBJECT IDENTIFIER ::= { 1 3 6 1 4 1 99 12 29 }
critAppTable     OBJECT IDENTIFIER ::= { 1 3 6 1 4 1 99 12 29 1 }
critAppProcTable OBJECT IDENTIFIER ::= { 1 3 6 1 4 1 99 12 29 1 1 }
critAppGlobals   OBJECT IDENTIFIER ::= { 1 3 6 1 4 1 99 12 29 2 }
critAppTraps     OBJECT IDENTIFIER ::= { 1 3 6 1 4 1 99 12 29 3 }

-- DR-Web HTML Custom page MIB
htmlpage         OBJECT IDENTIFIER ::= { 1 3 6 1 4 1 99 12 30 }
htmlGlobals            OBJECT IDENTIFIER ::= { 1 3 6 1 4 1 99 12 30 1 }
htmlPages              OBJECT IDENTIFIER ::= { 1 3 6 1 4 1 99 12 30 2 }
htmlParameters         OBJECT IDENTIFIER ::= { 1 3 6 1 4 1 99 12 30 3 }
htmlContents           OBJECT IDENTIFIER ::= { 1 3 6 1 4 1 99 12 30 4 }

-- MIB used for a demo
phoneSwitch      OBJECT IDENTIFIER ::= { 1 3 6 1 4 1 99 12 31 }

-- MIB for mapping from HTTP users to SNMP authentication information
httpToSnmpAuthMappingMIB  OBJECT IDENTIFIER ::= { 1 3 6 1 4 1 99 12 32 }
httpToSnmpMappingGlobals OBJECT IDENTIFIER ::= { 1 3 6 1 4 1 99 12 32 1 }
httpToSnmpMappingObjects OBJECT IDENTIFIER ::= { 1 3 6 1 4 1 99 12 32 2 }
httpToSnmpMappingTable OBJECT IDENTIFIER ::= { 1 3 6 1 4 1 99 12 32 2 1 }

-- This is the re-mapped SNMPv2* communityMIB, now called srCommunityMIB
srCommunityMIB OBJECT IDENTIFIER ::= { 1 3 6 1 4 1 99 12 33 }

-- MIB for testing SNMP agents.
srAgtTest OBJECT IDENTIFIER ::= { 1 3 6 1 4 1 99 12 34 }

-- This MIB augments the usmUserTable with an SnmpTagValue
usmTargetTagMIB OBJECT IDENTIFIER ::= { 1 3 6 1 4 1 99 12 35 }

-- This MIB augments the snmpTargetAddrTable with an address mask
tgtAddressMaskMIB OBJECT IDENTIFIER ::= { 1 3 6 1 4 1 99 12 36 }

--
-- snmpResearch.12.37 was used for a "trap MIB" temporarily
-- and has been put in as the softtrap MIB.  This branch should
-- not be used!
-- trap                   OBJECT IDENTIFIER ::= { 1 3 6 1 4 1 99 12 37 }

--
-- snmpResearch.13:  branch in which we register our "programs"
--
srPrograms  OBJECT IDENTIFIER ::= { 1 3 6 1 4 1 99 13 }
srUnixPrograms   OBJECT IDENTIFIER ::= { 1 3 6 1 4 1 99 13 1 }

--
-- snmpResearch.14:  historic, but not reusable
--
rptrGroup  OBJECT IDENTIFIER ::= { 1 3 6 1 4 1 99 14 }

--
-- snmpResearch.15:  registration of experimental MIBs and names.
--
-- This branch is particularly used for MIBs that we hope will move to
-- more permanent locations by publication.  Includes a branch for MIBs
-- and domains
srExperimental         OBJECT IDENTIFIER ::= { 1 3 6 1 4 1 99 15 }

srExperimentalMIBs     OBJECT IDENTIFIER ::= { 1 3 6 1 4 1 99 15 1 }

httpSecurityMIB        OBJECT IDENTIFIER ::= { 1 3 6 1 4 1 99 15 1 1 }

reconfigMIB            OBJECT IDENTIFIER ::= { 1 3 6 1 4 1 99 15 1 2 }
reconfigAgent          OBJECT IDENTIFIER ::= { 1 3 6 1 4 1 99 15 1 2 1 }
loadSubagent           OBJECT IDENTIFIER ::= { 1 3 6 1 4 1 99 15 1 2 2 }

srSmExt                OBJECT IDENTIFIER ::= { 1 3 6 1 4 1 99 15 1 3 }
srSmExtFunc            OBJECT IDENTIFIER ::= { 1 3 6 1 4 1 99 15 1 3 1 }
srSmExtFuncTimeWait    OBJECT IDENTIFIER ::= { 1 3 6 1 4 1 99 15 1 3 1 1 }
srSmExtFuncGetCompileIndex OBJECT IDENTIFIER ::= { 1 3 6 1 4 1 99 15 1 3 1 2 }
srSmExtFuncGetRetList  OBJECT IDENTIFIER ::= { 1 3 6 1 4 1 99 15 1 3 1 3 }
srSmExtFuncSetExecutionPeriod OBJECT IDENTIFIER ::= { 1 3 6 1 4 1 99 15 1 3 1 4 }
srSmExtBASE            OBJECT IDENTIFIER ::= { 1 3 6 1 4 1 99 15 1 3 2 }
srSmExtFILE            OBJECT IDENTIFIER ::= { 1 3 6 1 4 1 99 15 1 3 3 }
srSmExtOID             OBJECT IDENTIFIER ::= { 1 3 6 1 4 1 99 15 1 3 4 }
srSmExtTRAP            OBJECT IDENTIFIER ::= { 1 3 6 1 4 1 99 15 1 3 5 }

srExperimentalDomains  OBJECT IDENTIFIER ::= { 1 3 6 1 4 1 99 15 2 }
httpTCPIPDomain        OBJECT IDENTIFIER ::= { 1 3 6 1 4 1 99 15 2 1 }

-- Mid-Level Manager MIB
mlmMIB                 OBJECT IDENTIFIER ::= { 1 3 6 1 4 1 99 42 }
mlmMIBObjects          OBJECT IDENTIFIER ::= { 1 3 6 1 4 1 99 42 1 }
mlmMIBConformance      OBJECT IDENTIFIER ::= { 1 3 6 1 4 1 99 42 2 }

END
