--  Title:    DPS_V41v2.MIB
--  Version:  v4.1 for SNMPv2c
--
--  Copyright @ 2005 DPS Inc. All Rights Reserved
--
--  This MIB defines objects for the DPS products.
--
--

DPS-MIB-V38-V2 DEFINITIONS ::= BEGIN

IMPORTS
	DisplayString
		FROM RFC1213-MIB
	OBJECT-TYPE
		FROM SNMPv2-SMI
	dpsAlarmControl
		FROM DPS-MIB-V38;

tmonV2XM OBJECT IDENTIFIER ::= {dpsAlarmControl 3}
					  
tmonV2Ident OBJECT IDENTIFIER ::= {tmonV2XM 1}

tmonV2IdentManufacturer OBJECT-TYPE
	SYNTAX  DisplayString
	MAX-ACCESS  read-only
	STATUS  current
	DESCRIPTION "The TMON/XM Unit manufacturer."
	::= {tmonV2Ident  1}

tmonV2IdentModel OBJECT-TYPE
	SYNTAX  DisplayString
	MAX-ACCESS  read-only
	STATUS  current
	DESCRIPTION "The TMON/XM model designation."
	::= {tmonV2Ident  2}

tmonV2IdentSoftwareVersion OBJECT-TYPE
	SYNTAX  DisplayString
	MAX-ACCESS  read-only
	STATUS  current
	DESCRIPTION "The TMON/XM SNMP Agent software version."
	::= {tmonV2Ident  3}

tmonV2AlarmTable OBJECT-TYPE
	SYNTAX  SEQUENCE OF TMonV2AlarmEntry
	MAX-ACCESS  not-accessible
	STATUS  current
	DESCRIPTION "A table of TMonV2 Alarm-specific information."
	::= {tmonV2XM 2}

tmonV2AlarmEntry OBJECT-TYPE
	SYNTAX  TMonV2AlarmEntry
	MAX-ACCESS  not-accessible
	STATUS  current
	DESCRIPTION "Information about a particular TMonV2 alarm."
	INDEX   {tmonV2AIndex}
	::= {tmonV2AlarmTable 1}

TMonV2AlarmEntry ::= SEQUENCE  {tmonV2AIndex		INTEGER32,
										tmonV2ASite		DisplayString,
										tmonV2ADesc		DisplayString,
										tmonV2AState		DisplayString,
										tmonV2ASeverity	DisplayString,
										tmonV2AChgDate	DisplayString,
										tmonV2AChgTime	DisplayString,
										tmonV2AAuxDesc   DisplayString,
										tmonV2ADispDesc  DisplayString,
										tmonV2APntType	INTEGER32,
										tmonV2APort		INTEGER32,
										tmonV2AAddress	INTEGER32,
										tmonV2ADisplay	INTEGER32,
										tmonV2APoint		INTEGER32}

tmonV2AIndex OBJECT-TYPE
	SYNTAX  INTEGER
	MAX-ACCESS  read-only
	STATUS  current
	DESCRIPTION "Tmon alarm table index (1..NumberOfAlarms)."
	::={tmonV2AlarmEntry 1}

tmonV2ASite OBJECT-TYPE
	SYNTAX  DisplayString (SIZE (30))
	MAX-ACCESS  read-only
	STATUS  current
	DESCRIPTION "The site of the alarm (i.e. Atlanta Hub, Sub-Station H32)."
	::= {tmonV2AlarmEntry 2}

tmonV2ADesc OBJECT-TYPE
	SYNTAX  DisplayString (SIZE (40))
	MAX-ACCESS  read-only
	STATUS  current
	DESCRIPTION "A user-defined text string associated with the alarm 
					 (i.e. South Door, Generator, Power Grid 1)."
	::= {tmonV2AlarmEntry 3}

tmonV2AState OBJECT-TYPE
	SYNTAX  DisplayString (SIZE (8))
	MAX-ACCESS  read-only
	STATUS  current
	DESCRIPTION "The current alarm state."
	::= {tmonV2AlarmEntry 4}

tmonV2ASeverity OBJECT-TYPE
	SYNTAX  DisplayString (SIZE (8))
	MAX-ACCESS  read-only
	STATUS  current
	DESCRIPTION "The severity of the last alarm event."
	::= {tmonV2AlarmEntry 5}

tmonV2AChgDate OBJECT-TYPE
	SYNTAX  DisplayString (SIZE (8))
	MAX-ACCESS  read-only
	STATUS  current
	DESCRIPTION "The date (mm/dd/yy) of the last alarm event."
	::= {tmonV2AlarmEntry 6}

tmonV2AChgTime OBJECT-TYPE
	SYNTAX  DisplayString (SIZE (8))
	MAX-ACCESS  read-only
	STATUS  current
	DESCRIPTION "The time (hh:mm:ss) of the last alarm event."
	::= {tmonV2AlarmEntry 7}

tmonV2AAuxDesc OBJECT-TYPE
	SYNTAX  DisplayString (SIZE (30))
	MAX-ACCESS  read-only
	STATUS  current
	DESCRIPTION "An auxiliary user-defined text string associated with the
					 alarm (i.e. This remote needs servicing)."
	::= {tmonV2AlarmEntry 8}

tmonV2ADispDesc OBJECT-TYPE
	SYNTAX  DisplayString (SIZE (14))
	MAX-ACCESS  read-only
	STATUS  current
	DESCRIPTION "A description of the display on which this point appears."
	::= {tmonV2AlarmEntry 9}

tmonV2APntType OBJECT-TYPE
	SYNTAX  INTEGER
	MAX-ACCESS  read-only
	STATUS  current
	DESCRIPTION "Type of this point."
	::={tmonV2AlarmEntry 10}

tmonV2APort OBJECT-TYPE
	SYNTAX  INTEGER
	MAX-ACCESS  read-only
	STATUS  current
	DESCRIPTION "Port on which this point is reported."
	::={tmonV2AlarmEntry 11}

tmonV2AAddress OBJECT-TYPE
	SYNTAX  INTEGER
	MAX-ACCESS  read-only
	STATUS  current
	DESCRIPTION "Address of unit reporting this point."
	::={tmonV2AlarmEntry 12}

tmonV2ADisplay OBJECT-TYPE
	SYNTAX  INTEGER
	MAX-ACCESS  read-only
	STATUS  current
	DESCRIPTION "Display on which this point appears."
	::={tmonV2AlarmEntry 13}

tmonV2APoint OBJECT-TYPE
	SYNTAX  INTEGER
	MAX-ACCESS  read-only
	STATUS  current
	DESCRIPTION "Index into display of this point."
	::={tmonV2AlarmEntry 14}


-- structure used to issue a command to tmonV2XM element

tmonV2CommandGrid OBJECT IDENTIFIER ::= {tmonV2XM 3}

tmonV2CPType OBJECT-TYPE
	SYNTAX  INTEGER
	MAX-ACCESS  read-write
	STATUS  current
	DESCRIPTION "Tmon point type."
	::= {tmonV2CommandGrid 1}

tmonV2CPort OBJECT-TYPE
	SYNTAX  INTEGER
	MAX-ACCESS  read-write
	STATUS  current
	DESCRIPTION "Tmon port number."
	::= {tmonV2CommandGrid 2}

tmonV2CAddress OBJECT-TYPE
	SYNTAX  INTEGER
	MAX-ACCESS  read-write
	STATUS  current
	DESCRIPTION "Tmon_port address number."
	::= {tmonV2CommandGrid 3}

tmonV2CDisplay OBJECT-TYPE
	SYNTAX  INTEGER
	MAX-ACCESS  read-write
	STATUS  current
	DESCRIPTION "Tmon_port_address display number."
	::= {tmonV2CommandGrid 4}

tmonV2CPoint OBJECT-TYPE
	SYNTAX  INTEGER (1..64)
	MAX-ACCESS  read-write
	STATUS  current
	DESCRIPTION "Tmon_port_display point number (1-64)."
	::= {tmonV2CommandGrid 5}

tmonV2CEvent OBJECT-TYPE
	SYNTAX  INTEGER
	MAX-ACCESS  read-write
	STATUS  current
	DESCRIPTION "Tmon event ID."
	::= {tmonV2CommandGrid 6}

tmonV2CAction OBJECT-TYPE
	SYNTAX  INTEGER {	latch(1),
							release(2),
							momentary(3),
							ack(17),
							tag(18),
							untag(19)
						 }
	MAX-ACCESS  read-write
	STATUS  current
	DESCRIPTION "Requested command action (tmonV2XM will ignore if invalid)."
	::= {tmonV2CommandGrid 7}

tmonV2CAuxText OBJECT-TYPE
	SYNTAX  DisplayString (SIZE (30))
	MAX-ACCESS  read-write
	STATUS  current
	DESCRIPTION "An auxiliary user-defined text string associated with the
					 command (i.e. User_initials)."
	::= {tmonV2CommandGrid 8}

tmonV2CResult OBJECT-TYPE
	SYNTAX  INTEGER { success(1),
							failure(2),
							pending(3)
						 }
	MAX-ACCESS  read-only
	STATUS  current
	DESCRIPTION "Command result."
	::= {tmonV2CommandGrid 9}



dpsRTUv2 OBJECT IDENTIFIER ::= {dpsAlarmControl 4}

dpsRTUv2Ident OBJECT IDENTIFIER ::= {dpsRTUv2 1}

dpsRTUv2Manufacturer OBJECT-TYPE
	SYNTAX  DisplayString (SIZE (30))
	MAX-ACCESS  read-only
	STATUS  current
	DESCRIPTION "The Remote Telemetry Unit manufacturer."
	::= {dpsRTUv2Ident  1}

dpsRTUv2Model OBJECT-TYPE
	SYNTAX  DisplayString (SIZE (30))
	MAX-ACCESS  read-only
	STATUS  current
	DESCRIPTION "The RTU model designation."
	::= {dpsRTUv2Ident  2}

dpsRTUv2FirmwareVersion OBJECT-TYPE
	SYNTAX  DisplayString (SIZE (20))
	MAX-ACCESS  read-only
	STATUS  current
	DESCRIPTION "The RTU firmware version."
	::= {dpsRTUv2Ident  3}

dpsRTUv2DateTime OBJECT-TYPE
	SYNTAX  DisplayString (SIZE (23))
	MAX-ACCESS  read-write
	STATUS  current
	DESCRIPTION "The RTU system date and time."
	::= {dpsRTUv2Ident  4}

dpsRTUv2SyncReq OBJECT-TYPE
	SYNTAX  INTEGER {	sync(1) }
	MAX-ACCESS  read-write
	STATUS  current
	DESCRIPTION "Caution: SETting this object initiates traps for all
					 standing alarms."
	::= {dpsRTUv2Ident  5}


-- structure used to access displays managed by this RTU

dpsRTUv2DisplayGrid OBJECT-TYPE
	SYNTAX  SEQUENCE OF DPSrtuV2DispEntry
	MAX-ACCESS  not-accessible
	STATUS  current
	DESCRIPTION "Holds information on displays managed by the RTU."
	::= {dpsRTUv2 2}

dpsRTUv2DisplayEntry OBJECT-TYPE
	SYNTAX  DPSrtuV2DispEntry
	MAX-ACCESS  not-accessible
	STATUS  current
	DESCRIPTION "Information about a particular RTU display."
	INDEX   {dpsRTUv2Port, dpsRTUv2Address, dpsRTUv2Display}
	::= {dpsRTUv2DisplayGrid 1}

DPSrtuV2DispEntry ::= SEQUENCE 	{	dpsRTUv2Port			INTEGER32,
											dpsRTUv2Address		INTEGER32,
											dpsRTUv2Display		INTEGER32,
											dpsRTUv2DispDesc		DisplayString,
											dpsRTUv2PntMap		DisplayString}

dpsRTUv2Port OBJECT-TYPE
	SYNTAX  INTEGER
	MAX-ACCESS  read-only
	STATUS  current
	DESCRIPTION "RTU port number."
	::= {dpsRTUv2DisplayEntry 1}

dpsRTUv2Address OBJECT-TYPE
	SYNTAX  INTEGER
	MAX-ACCESS  read-only
	STATUS  current
	DESCRIPTION "RTU_port address number."
	::= {dpsRTUv2DisplayEntry 2}

dpsRTUv2Display OBJECT-TYPE
	SYNTAX  INTEGER
	MAX-ACCESS  read-only
	STATUS  current
	DESCRIPTION "RTU_port_address display number."
	::= {dpsRTUv2DisplayEntry 3}

dpsRTUv2DispDesc OBJECT-TYPE
	SYNTAX  DisplayString (SIZE (20))
	MAX-ACCESS  read-only
	STATUS  current
	DESCRIPTION "A description of the associated display."
	::= {dpsRTUv2DisplayEntry 4}

dpsRTUv2PntMap OBJECT-TYPE
	SYNTAX  DisplayString (SIZE (71))
	MAX-ACCESS  read-only
	STATUS  current
	DESCRIPTION "A map of the points appearing in this display."
	::= {dpsRTUv2DisplayEntry 5}


-- structure used to issue a control to a managed point

dpsRTUv2ControlGrid OBJECT IDENTIFIER ::= {dpsRTUv2 3}

dpsRTUv2CPort OBJECT-TYPE
	SYNTAX  INTEGER
	MAX-ACCESS  read-write
	STATUS  current
	DESCRIPTION "RTU port number."
	::= {dpsRTUv2ControlGrid 1}

dpsRTUv2CAddress OBJECT-TYPE
	SYNTAX  INTEGER
	MAX-ACCESS  read-write
	STATUS  current
	DESCRIPTION "RTU_port address number."
	::= {dpsRTUv2ControlGrid 2}

dpsRTUv2CDisplay OBJECT-TYPE
	SYNTAX  INTEGER
	MAX-ACCESS  read-write
	STATUS  current
	DESCRIPTION "RTU_port_address display number."
	::= {dpsRTUv2ControlGrid 3}

dpsRTUv2CPoint OBJECT-TYPE
	SYNTAX  INTEGER (1..64)
	MAX-ACCESS  read-write
	STATUS  current
	DESCRIPTION "RTU_port_display point number (1-64)."
	::= {dpsRTUv2ControlGrid 4}

dpsRTUv2CAction OBJECT-TYPE
	SYNTAX  INTEGER {	latch(1),
							release(2),
							momentary(3)
						 }
	MAX-ACCESS  read-write
	STATUS  current
	DESCRIPTION "Requested action on point (RTU will ignore if invalid)."
	::= {dpsRTUv2ControlGrid 5}

dpsRTUv2AlarmGrid OBJECT-TYPE
	SYNTAX  SEQUENCE OF DPSrtuV2AlarmEntry
	MAX-ACCESS  not-accessible
	STATUS  current
	DESCRIPTION "Holds individual alarm point information."
	::= {dpsRTUv2 5}

dpsRTUv2AlarmEntry OBJECT-TYPE
	SYNTAX  DPSrtuV2AlarmEntry
	MAX-ACCESS  not-accessible
	STATUS  current
	DESCRIPTION "Detailed information about a particular RTU display."
	INDEX   {dpsRTUv2APort, dpsRTUv2AAddress, dpsRTUv2ADisplay, dpsRTUv2APoint}
	::= {dpsRTUv2AlarmGrid 1}

DPSrtuV2AlarmEntry ::= SEQUENCE	 {	dpsRTUv2APort			INTEGER32,
											dpsRTUv2AAddress		INTEGER32,
											dpsRTUv2ADisplay		INTEGER32,
											dpsRTUv2APoint		INTEGER32,
											dpsRTUv2APntDesc		DisplayString,
											dpsRTUv2AState		DisplayString}

dpsRTUv2APort OBJECT-TYPE
	SYNTAX  INTEGER
	MAX-ACCESS  read-only
	STATUS  current
	DESCRIPTION "RTU port number."
	::= {dpsRTUv2AlarmEntry 1}

dpsRTUv2AAddress OBJECT-TYPE
	SYNTAX  INTEGER
	MAX-ACCESS  read-only
	STATUS  current
	DESCRIPTION "RTU_port address number."
	::= {dpsRTUv2AlarmEntry 2}

dpsRTUv2ADisplay OBJECT-TYPE
	SYNTAX  INTEGER
	MAX-ACCESS  read-only
	STATUS  current
	DESCRIPTION "RTU_port_address display number."
	::= {dpsRTUv2AlarmEntry 3}

dpsRTUv2APoint OBJECT-TYPE
	SYNTAX  INTEGER
	MAX-ACCESS  read-only
	STATUS  current
	DESCRIPTION "RTU_port_address_display point number."
	::= {dpsRTUv2AlarmEntry 4}

dpsRTUv2APntDesc OBJECT-TYPE
	SYNTAX  DisplayString (SIZE (21))
	MAX-ACCESS  read-only
	STATUS  current
	DESCRIPTION "A description of this point."
	::= {dpsRTUv2AlarmEntry 5}

dpsRTUv2AState OBJECT-TYPE
	SYNTAX  DisplayString (SIZE (8))
	MAX-ACCESS  read-only
	STATUS  current
	DESCRIPTION "The current state of this point."
	::= {dpsRTUv2AlarmEntry 6}


END
