--------------------------------------------------------------------
-- OLD-CISCO-CHASSIS-MIB
-- May 1997
--
-- Copyright (c) 1994-1997 by cisco Systems, Inc.
-- All rights reserved.
--
--------------------------------------------------------------------

               OLD-CISCO-CHASSIS-MIB DEFINITIONS ::= BEGIN

               IMPORTS
                    TimeTicks
                        FROM RFC1155-SMI
                    OBJECT-TYPE
			FROM RFC-1212
                    DisplayString
			FROM RFC1213-MIB
		    temporary
			FROM CISCO-SMI;
          
               chassis             OBJECT IDENTIFIER ::= { temporary 6 }

               -- Temporary Chassis Section


               -- (not the same as the IETF Chassis MIB)

          -- This group is present in all products.

               chassisType OBJECT-TYPE
                   SYNTAX  INTEGER {
                        unknown(1),
                        multibus(2),
                        agsplus(3),
                        igs(4),
                        c2000(5),
                        c3000(6),
                        c4000(7),
                        c7000(8),
                        cs500(9),
                        c7010(10),
                        c2500(11),
                        c4500(12),
			c2102(13),
			c2202(14),
			c2501(15),
			c2502(16),
			c2503(17),
			c2504(18),
			c2505(19),
			c2506(20),
			c2507(21),
			c2508(22),
			c2509(23),
			c2510(24),
			c2511(25),
			c2512(26),
			c2513(27),
			c2514(28),
			c2515(29),
			c3101(30),
			c3102(31),
			c3103(32),
			c3104(33),
			c3202(34),
			c3204(35),
			accessProRC(36),
			accessProEC(37),
                        c1000(38),
                        c1003(39),
			c1004(40),
			c2516(41),
			c7507(42),
			c7513(43),
			c7506(44),
			c7505(45),
			c1005(46),
			c4700(47),
			c2517(48),
			c2518(49),
			c2519(50),
			c2520(51),
			c2521(52),
			c2522(53),
			c2523(54),
			c2524(55),
			c2525(56),
			c4700S(57),
			c7206(58),
			c3640(59),
			as5200(60),
			c1601(61),
			c1602(62),
			c1603(63),
			c1604(64),
			c7204(65),
			c3620(66),
                        wsx3011(68),
			mc3810(69),
                        c1503(72),
		   	as5300(73),	
                        as2509RJ(74),
                        as2511RJ(75),
                        c2501FRAD-FX(77),
                        c2501LANFRAD-FX(78),
                        c2502LANFRAD-FX(79),
			c1605(81),
			c12012(82),
			c12008(85),
                        ubr7246(86),
                        c2610(87),
                        c2611(89),
                        c2612(88),
			c2620(95),
                        c2621(96),           
                        ubr904(90),
                        c7202(94),
                        c1710(100),
			c1720(101),
                        c7576(102),
			c1401(103),
                        c2613(104),
                        ubr7223(105),
                        c801(107),
                        c802(108),
                        c803(109),
                        c804(110),
                        c7206VXR(111),
                        c7204VXR(112),
                        c1750(113),
                        c805(116),
			c1417(128),
                        c7120-quadt1(136),
                        c7120-t3(137),
                        c7120-e3(138),
                        c7120-at3(139),
                        c7120-ae3(140),
                        c7120-smi3(141),
                        c7140-dualt3(142),
                        c7140-duale3(143),
                        c7140-dualat3(144),
                        c7140-dualae3(145),
                        c7140-dualmm3(146),
                        c827-quad-v(147),
                        ubr-7246-vxr(148),
                        as5400(151),
                        c7140-Octt1(152),
                        c7140-dualfe(153),
                        c827(159),
                        mc3810-v3(160),
                        c7507z(162),
                        c7513z(163),
                        c7507mx(164),
                        c7513mx(165),
			ubr914(168),
                        c7750-mrp200(176),
                        c7750-ssp80(177),
			cva122(180),
                        as5850(182),
                        as5350(187),
                        c7700(188),
                        c7750(189),
                        ubr10012(192),
                        c2650(195),
                        c2651(196), 
                        c826(198),
                        ws-c295012(199),
                        ws-c295024(200),
                        ws-c295024c(201),
                        c1751(202),
                        c3661-ac(214),
                        c3661-dc(215),
                        c3662-ac(216),
                        c3662-dc(217),
                        c3662-ac-co(218),
                        c3662-dc-co(219),
                        ubr7111(220),
                        ubr7111e(221),
                        ubr7114(222),
                        ubr7114e(223),
                        ws-c295024t(235),
			ubr905(227),
                        soho76(230),            
                        ciad2420(238),
                        c12010(224),            
                        cat355024(242),
                        cat355048(243),
                        cat355012t(244),
                        cat2924-lre-xl(245),
                        cat2912-lre-xl(246),
			cva122e(247),
                        curm(249),                                 
                        curm2fe(250),
                        curm2fe2v(251),
                        c951(253),
                        c952(254), 
                        c828(258),
                        c12416(261),
                        c12410(270),
                        c811(271),
                        c813(272),
			c4224(275),
                        c7401ASR(279),
			cVG248(280),   
                        c2691(288),     
                        c3725(289),
                        c1760(291),
                        c3631-co(300),
                        cat295012g(302),
                        cat295024g(303),
                        cat295048g(304),
                        cat355012g(306),
                        c3745(310),
                        c7304(313),
                        c1721(318),
                        cat355024-dc(325),
                        cat355024-mmf(333),
                        airap-1200(341)    
                   }
                   ACCESS  read-only
                   STATUS  mandatory
                   DESCRIPTION
                           "Chassis type."
                   ::= { chassis 1 }

               chassisVersion OBJECT-TYPE
                   SYNTAX  DisplayString
                   ACCESS  read-only
                   STATUS  mandatory
                   DESCRIPTION
                           "Chassis hardware revision level, or an empty
                           string if unavailable."
                   ::= { chassis 2 }

               chassisId OBJECT-TYPE
                   SYNTAX  DisplayString
                   ACCESS  read-write
                   STATUS  mandatory
                   DESCRIPTION
                           "Unique ID string. Defaults to chassis serial
                           number if available, otherwise empty. Can
                           also be set with 'snmp-server chassis-id'."
                   ::= { chassis 3 }

               romVersion OBJECT-TYPE
                   SYNTAX  DisplayString
                   ACCESS  read-only
                   STATUS  mandatory
                   DESCRIPTION
                           "ROM monitor version."
                   ::= { chassis 4 }

               romSysVersion OBJECT-TYPE
                   SYNTAX  DisplayString
                   ACCESS  read-only
                   STATUS  mandatory
                   DESCRIPTION
                           "ROM system software version, or an empty
                           string if unavailable."
                   ::= { chassis 5 }

               processorRam OBJECT-TYPE
                   SYNTAX  INTEGER
                   ACCESS  read-only
                   STATUS  mandatory
                   DESCRIPTION
                           "Bytes of RAM available to CPU."
                   ::= { chassis 6 }

               nvRAMSize OBJECT-TYPE
                   SYNTAX  INTEGER
                   ACCESS  read-only
                   STATUS  mandatory
                   DESCRIPTION
                           "Bytes of non-volatile configuration memory."
                   ::= { chassis 7 }

               nvRAMUsed OBJECT-TYPE
                   SYNTAX  INTEGER
                   ACCESS  read-only
                   STATUS  mandatory
                   DESCRIPTION
                           "Bytes of non-volatile configuration memory
                           in use."
                   ::= { chassis 8 }

               configRegister OBJECT-TYPE
                   SYNTAX  INTEGER
                   ACCESS  read-only
                   STATUS  mandatory
                   DESCRIPTION
                           "Value of configuration register."
                   ::= { chassis 9 }

               configRegNext OBJECT-TYPE
                   SYNTAX  INTEGER
                   ACCESS  read-only
                   STATUS  mandatory
                   DESCRIPTION
                           "Value of configuration register at next
                           reload."
                   ::= { chassis 10 }

               cardTable OBJECT-TYPE
                   SYNTAX  SEQUENCE OF CardTableEntry
                   ACCESS  not-accessible
                   STATUS  mandatory
                   DESCRIPTION
                            "Chassis card table."
                   ::= { chassis 11 }

               cardTableEntry OBJECT-TYPE
                   SYNTAX CardTableEntry
                   ACCESS  not-accessible
                   STATUS  mandatory
                   DESCRIPTION
                            "Chassis card table."
                   INDEX { cardIndex }
               ::= { cardTable 1 }

               CardTableEntry ::=
                   SEQUENCE {
                       cardIndex
                           INTEGER,
                       cardType
                           INTEGER,
                       cardDescr
                           DisplayString,
                       cardSerial
                           INTEGER,
                       cardHwVersion
                           DisplayString,
                       cardSwVersion
                           DisplayString,
                       cardSlotNumber
                           INTEGER,
                       cardContainedByIndex
                           INTEGER,
                       cardOperStatus
                           INTEGER,
                       cardSlots
                           INTEGER
                   }


          -- The following section describes the components of the
          -- table.

               cardIndex OBJECT-TYPE
                   SYNTAX  INTEGER
                   ACCESS  read-only
                   STATUS  mandatory
                   DESCRIPTION
                           "Index into cardTable (not physical chassis
                           slot number)."
                   ::= { cardTableEntry 1 }

               cardType OBJECT-TYPE
                   SYNTAX  INTEGER {
                        unknown(1),
                        csc1(2),
                        csc2(3),
                        csc3(4),
                        csc4(5),
                        rp(6),
                        cpu-igs(7),
                        cpu-2500(8),
                        cpu-3000(9),
                        cpu-3100(10),
                        cpu-accessPro(11),
                        cpu-4000(12),
                        cpu-4000m(13),
                        cpu-4500(14),
                        rsp1(15),
                        rsp2(16),
			cpu-4500m(17),
			cpu-1003(18),
			cpu-4700(19),
                        csc-m(20),
                        csc-mt(21),
                        csc-mc(22),
                        csc-mcplus(23),
                        csc-envm(24),
			chassisInterface(25),
			cpu-4700S(26),
			cpu-7200(27),
			rsp7000(28),
			chassisInterface7000(29),
			rsp4(30),
			cpu-3600(31),
			cpu-as5200(32),
			c7200-io1fe(33),
			cpu-4700m(34),
			cpu-1600(35),
			c7200-io(36),
                        cpu-1503(37),
                        cpu-1502(38),
			cpu-as5300(39),
                        csc-16(40),
                        csc-p(41),
                        csc-a(50),
                        csc-e1(51),
                        csc-e2(52),
                        csc-y(53),
                        csc-s(54),
                        csc-t(55),
                        csc-r(80),
                        csc-r16(81),
                        csc-r16m(82),
                        csc-1r(83),
                        csc-2r(84),
                        sci4s(56),
                        sci2s2t(57),
                        sci4t(58),
                        mci1t(59),
                        mci2t(60),
                        mci1s(61),
                        mci1s1t(62),
                        mci2s(63),
                        mci1e(64),
                        mci1e1t(65),
                        mci1e2t(66),
                        mci1e1s(67),
                        mci1e1s1t(68),
                        mci1e2s(69),
                        mci2e(70),
                        mci2e1t(71),
                        mci2e2t(72),
                        mci2e1s(73),
                        mci2e1s1t(74),
                        mci2e2s(75),
                        csc-cctl1(100),
                        csc-cctl2(101),
                        csc-mec2(110),
                        csc-mec4(111),
                        csc-mec6(112),
                        csc-fci(113),
                        csc-fcit(114),
                        csc-hsci(115),
                        csc-ctr(116),
			cpu-7200-npe150(121),
			cpu-7200-npe200(122),
			cpu-wsx5302(123),
			gsr-rp(124),
			cpu-3810(126),  
			cpu-2600(127),  
                        cpu-1700(131),
                        cpu-7200-npe300(132),
                        cpu-7200-npe175(137),
                        cpu-7200-npe225(138),
                        sp(150),
                        eip(151),
                        fip(152),
                        hip(153),
                        sip(154),
                        trip(155),
                        fsip(156),
                        aip(157),
                        mip(158),
                        ssp(159),
			cip(160),
			srs-fip(161),
			srs-trip(162),
			feip(163),
			vip(164),
			vip2(165),
			ssip(166),
			smip(167),
			posip(168),
			feip-tx(169),
			feip-fx(170),
			vip2-50(181),
			feip2(182),
                        mc11(184),
                        mc12a(185),
						io1fe-tx-isl(186),
                        geip(187),
                        mc1d4u(189),
                        mc1d6u(190),
                        mc11a(191),
                        cip2(192),
                        mc16-eur(193),
                        vip4-80(195),
                        vip4-50(196),
                        io-e-ge(197),
                        io-2fe(198),
                        geip-plus(199),
                        npm-4000-fddi-sas(200),
                        npm-4000-fddi-das(201),
                        npm-4000-1e(202),
                        npm-4000-1r(203),
                        npm-4000-2s(204),
                        npm-4000-2e1(205),
                        npm-4000-2e(206),
                        npm-4000-2r1(207),
                        npm-4000-2r(208),
                        npm-4000-4t(209),
                        npm-4000-4b(210),
                        npm-4000-8b(211),
                        npm-4000-ct1(212),
                        npm-4000-ce1(213),
                        npm-4000-1a(214),
     	                npm-4000-6e(215),
			npm-4500-2t16s(216),
			npm-4000-1fe(217),
                        npm-4000-1hssi(218),
                        npm-4500-2ev2(219),
			pa-1fe(230),
			pa-8e(231),
			pa-4e(232),
			pa-5e(233),
			pa-4t(234),
			pa-4r(235),
			pa-fddi(236),
			sa-encryption(237),
			pa-ah1t(238),
			pa-ah2t(239),
			pa-a4t(240),
			pa-a8t-v35(241),
			pa-1fe-tx-isl(242),
			pa-1fe-fx-isl(243),
			pa-1fe-tx-nisl(244),
			sa-compression(245),
			pa-atm-lite-1(246),
			pa-ct3(247),
			pa-oc3sm-mux-cbrt1(248),
			pa-oc3sm-mux-cbr120e1(249),
			pa-oc3sm-mux-cbr75e1(250),
			pa-oc3mm-mux-cbrt1(251),
			pa-oc3mm-mux-cbr120e1(252),
			pa-oc3mm-mux-cbr75e1(253),
			pa-ds3-mux-cbrt1(254),
			pa-e3-mux-cbr120e1(255),
                        pa-8b-st(257),
                        pa-4b-u(258),
			pa-fddi-fd(259),
			pm-cpm-1e2w(260),
			pm-cpm-2e2w(261),
			pm-cpm-1e1r2w(262),
			pm-ct1-csu(263),
			pm-2ct1-csu(264),
			pm-ct1-dsx1(265),
			pm-2ct1-dsx1(266),
			pm-ce1-balanced(267),
			pm-2ce1-balanced(268),
			pm-ce1-unbalanced(269),
			pm-2ce1-unbalanced(270),
			pm-4b-u(271),
			pm-4b-st(272),
			pm-8b-u(273),
			pm-8b-st(274),
			pm-4as(275),
			pm-8as(276),
                        pm-4e(277),
                        pm-1e(278),
                        pm-4r(279),
                        pm-m4t(280),
			pm-16a(281),
			pm-32a(282),
                        pm-c3600-1fe-tx(283),
			pm-c3600-compression(284),
                        pm-c3600-1fe-fx(288),
			pm-dmodem(285),
			pm-8admodem(286),
			pm-16admodem(287),
                        pm-1fe2ct1-csu(289),       
			as5200-carrier(290),
			as5200-2ct1(291),
			as5200-2ce1(292),
			as5200-dtd-carrier(293),
			pm-as5200-12m(310),
			pm-as5200-12m-56k(311),
			pm-as5200-12m-v110(312),
                        wm-c2500-5in1(330),
                        wm-c2500-t1-csudsu(331),
                        wm-c2500-sw56-2wire-csudsu(332),
                        wm-c2500-sw56-4wire-csudsu(333),
                        wm-c2500-bri(334),
                        wm-c2500-bri-nt1(335),
                        wic-serial-1t(360),
                        wic-serial-2t(361),
                        wic-csu-dsu-2(362),
                        wic-csu-dsu-4(363),
                        wic-s-t-3420(364),
                        wic-s-t-2186(365),
                        wic-u-3420(366),
                        wic-u-2091(367),
                        wic-u-2091-2081(368),
			wic-s-t-2186-leased(369),
			wic-1t-1dsu(370),
                        wic-serial-2as(371), 
                        pm-compression(372),
                        pm-atm-oc3MM(374),
                        pm-atmoc3mm-1v(375),
                        pm-atmoc3smi-1v(376),
                        pm-atmoc3sml-1v(377),
                        pm-atm-oc3SML(378), 
                        pm-atm-oc3SMI(379),     
                        pm-encryption-AIM(388), 
			pa-jt2(400),
			pa-posdw(401),
			pa-4me1-bal(402),
                        pa-2ce1-balanced(403),
                        pa-2ct1(404),
			pa-1vg(405),
			pa-atmdx-ds3(406),
			pa-atmdx-e3(407),
			pa-atmdx-sml-oc3(408),
			pa-atmdx-smi-oc3(409),
			pa-atmdx-mm-oc3(410),
			pa-a8t-x21(414),
			pa-a8t-rs232(415),
			pa-4me1-unbal(416),
			pa-4r-fdx(417),
			pa-1e3(418),
    		        pa-2e3(419),
			pa-1t3(420), 
			pa-2t3(421), 
                        pa-2ce1-unbalanced(422),
			pa-14e-switch(423),
			pa-esc-channel(425), 
			pa-par-channel(426), 
                        pa-ge(427),
                        pa-4ct1-csu(428),
                        pa-8ct1-csu(429),
                        pa-2feisl-tx(433),
                        pa-2feisl-fx(434),
                        mc3810-dcm(435),                
                        mc3810-mfm-e1balanced-bri(436),
                        mc3810-mfm-e1unbalanced-bri(437),
                        mc3810-mfm-e1-unbalanced(438),  
                        mc3810-mfm-dsx1-bri(439),      
                        mc3810-mfm-dsx1-csu(440),     
                        mc3810-vcm(441),             
                        mc3810-avm(442),            
                        mc3810-avm-fxs(443),       
                        mc3810-avm-fxo(444),      
                        mc3810-avm-em(445),      
                        mc3810-bvm(447),
                        mc3810-vdm(454), 
                        mc3810-bvm-nt-te(456),
			pm-dtd-6m(461),
			pm-dtd-12m(462),
			as5300-4ct1(480),
			as5300-4ce1(481),
			as5300-modem-carrier(482),
			as5300-dtd-carrier(484),
			as5300-8ct1-4t(485),
			as5300-8ce1-4t(486),
			as5300-4ct1-4t(487),
			as5300-4ce1-4t(488),
			as5300-dtd12-carrier(489),
                        vic-em(500),
                        vic-fxo(501),
			vic-fxs(502),
                        vpm-2v(503),
                        vpm-4v(504),
                        vfc(505),
                        dspm(507),
			vic-fxo-eu(508),
			vic-fxo-m3(509),
			vic-bri(515),
                        wvic-t1-1dsu(518),
                        wvic-e1-1dsu(519),
                        vwic-2mft-t1(520),
                        vwic-2e1(521),
                        vwic-2t1-di(522),
                        vwic-2e1-di(523),
                        vic-fxo-m2(525),
                        vic-16fxs(526),
                        vic-8fxs(527),
                        hda-nm-4fxs(528),   
                        vic-fxo-m1(1101),
			pos-qoc3-mm(530),
                        pos-qoc3-sm(531),
                        pos-oc12-mm(532),
                        pos-oc12-sm(533),
                        atm-oc12-mm(534),
                        atm-oc12-sm(535),
                        pos-oc48-mm-l(536),
                        pos-oc48-sm-lr-fc(537),
                        gsr-sfc(538),
                        gsr-csc(539),
                        gsr-csc4(540),
                        gsr-csc8(541),
                        gsr-sfc8(542),
                        atm-qoc3-mm(543),
                        atm-qoc3-sm(544),
                        gsr-oc12chds3-mm(545),
                        gsr-oc12chds3-sm(546),
			gsr-1ge(547),
			gsr-oc12chsts3-mm(548),
			gsr-oc12chsts3-sm(549),
			pos-oc48-sm-sr-fc(552),
			pos-qoc3-sm-l(553),
                        pos-8oc3-mm(554),
                        pos-8oc3-ir(555),
                        pos-8oc3-lr(556),
                        pos-16oc3-mm(557),
			pos-16oc3-ir(558),
			pos-16oc3-lr(559),
                        pa-8ct1(560), 
                        pa-8ce1(561), 
                        pa-ce3(562),
                        pa-4r-dtr(563),
                        pa-possw-sm(564),
                        pa-possw-mm(565),
                        pa-possw-lr(566),
                        pa-1t3-plus(567),
                        pa-2t3-plus(568),
                        pa-ima-t1(569),
                        pa-ima-e1(570),
                        pa-2ct1-csu(571),
                        pa-2ce1(572),
                        pa-2fe-tx(573),
                        pa-2fe-fx(574),
                        pm-1fe-1ct1(600),  
                        pm-1fe-2CT1(601), 
                        pm-1fe-1CE1(602),    
			pm-1fe-2CE1(603),
                        pm-1fe-1ct1-csu(604),    
                        pm-atm25(605),
			pm-hssi(606),
                        as5800-dsc(630),
                        as5800-12t1(631),
                        as5800-12e1(632),
                        as5800-mica-hmm(633),
                        as5800-t3(634),
                        as5800-1fe-dsi(635),
                        as5800-mica-dmm(636),
			as5800-vcc(637),
			as5800-dspm-6c549(638),
			as5800-dsp(639),
			as5800-vccmc(640),
                        pa-vxc-2t1e1(800),
                        pa-vxb-2t1e1(801),
                        pa-atm-oc12-mm(802),
                        pa-atm-oc12-smi(803),
                        pa-mct3(804),
                        pa-mc2t3(805),
                        srp-pa-oc12-mm(808),
                        srp-pa-oc12-sm-ir(809),
                        srp-pa-oc12-lr(810),
                        pa-mcx-2te1(811),  
                        pa-mcx-4te1(812),
                        pa-mcx-8te1(813),
			pa-vxc(815),
			pa-vxb(816),
                        pa-mc-stm1-smi(817),
                        pa-mc-stm1-mm(818),
                        pa-dual-wide-ge(819), 
                        pa-mc-8t1e1(822),
                        ubr-mc16s(1001),
                        ubr-mc11(1002),
                        ubr-mc11c(1003),
                        ubr-mc12c(1004),
                        ubr-mc14c(1005),
                        ubr-mc16a(1006),
                        ubr-mc16b(1007),
                        ubr-mc16c(1008),
                        ubr-mc16e(1009),
                        ubr-clk(1015),
			ubr-he-radio(1018),
			ubr-su-radio(1019),
                        ubr-mc28cf(1020),
                        ubr-mc28c-bnc(1021),
                        ubr-mc26cf(1022),
                        ubr-mc26c-bnc(1023),
                        gsr-8fe-tx(1050),
                        gsr-8fe-fx(1051),
			ssrp-oc48-sm-sr(1052),
			ssrp-oc48-sm-lr(1053),
                        pos-qoc12-sm-lr(1054),     
			pos-qoc12-mm-sr(1055),
			pos-oc48-sm-lr-sc(1056),
			pos-oc48-sm-sr-sc(1057),
			srp-oc12-sm-ir(1058),
			srp-oc12-sm-lr(1059),
			srp-oc12-mm(1060),
                        pos-en-oc48-sr-sc(1061),
                        pos-en-oc48-sr-fc(1062),
                        pos-en-oc48-lr-sc(1063),
                        pos-en-oc48-lr-fc(1064),
                        pos-en-qoc12-sr(1065),
                        pos-en-qoc12-ir(1066),
                        copper-6ds3(1067),
                        copper-12ds3(1068),
                        pos-oc192-sm-ir-fc(1069),
                        pos-oc192-sm-sr-fc(1070),
                        pos-oc192-sm-ir-sc(1071),
                        pos-oc192-sm-sr-sc(1072),
			gsr-sfc16(1073),
			gsr-csc16(1074),
			gsr-3ge(1075),
                        pos-en-qoc48-sm-sr-fc(1080),
                        pos-en-qoc48-sm-sr-sc(1081),
                        pos-en-qoc48-sm-lr-sc(1082),
                        pos-en-qoc48-sm-lr-fc(1083),
                        gsr-6ct3(1084),
                        gsr-sfc16-oc192(1091),
                        gsr-csc16-oc192(1092),  
		        pm-3des-encryption(1102),  		
                        pm-ds3(1106),
                        pm-e3(1107), 
                        aim-t1-e1-atm(1108),
                        aim-t1-atm-24dsp(1109),
                        aim-e1-atm-30dsp(1110),
                        vic-2vp-fxs-did(1111),
                        wic-serial-1t-12in1(1112),
                        vic-2b-nt-te(1113),
                        nm-aic64(1114),
                        mix3660-64(1115),
                        wic-async-1am(1116),
                        wic-async-2am(1117),
                        aim-4dsps(1119),
                        wic-ethernet(1124),
                        nm-16esw1(1128),
                        dnm-36esw1(1129),           
			io-2fe-tx-isl(1150),
                        ism-ipsec-mppe(1151),
			cpu-as5400(1182),
			cpu-as5850(1187),
			cpu-as5350(1189),
                        cpu-c7300-nse100(1197),
                        acc-24fe-tx(1307),
                        acc-24fe-fx-mm(1308),
                        acc-24fe-fx-sm(1309),
                        srp-oc48-sr(1310),
                        srp-oc48-ir(1311),
 			as5400-dfc-carrier(1350),
			dfc-8ce1(1450),
			dfc-8ct1(1451),
			dfc-ct3(1452),
			dfc-np108(1453),
                        isa-ipsec-mppe(1454),
                        wic-dslsar-20150(1455),
			dfc-4ce1(1456),
			dfc-4ct1(1457),
			dfc-2ce1(1458),
			dfc-2ct1(1459),
			dfc-np60(1460),
			spe-np6(1461),
                        cpu-rsp8(1183),
                        cpu-trp(1184),
                        cpu-7200-nse1(1186),
                        cpu-7200-npe400(1188),
                        vwic-2e1-di-g703(1554),
                        vwic-e1-g703(1555),
                        encryption-des(1557),
                        encryption-3des(1558),
                        wic-1shdsl(1565),
                        ge-esw1(1570),
                        pwr-16esw1(1571),
                        pwr-36esw1(1572),            
                        hda-em-4dsp(1590),
                        hda-em-10fxs(1591),
                        ics7750-spe200(1650),
                        ics7750-mrp200(1651),
                        ics7750-sap(1652),
                        as5850-rsc-2ge(1750),
			as5850-ct3-216up(1751),
			as5850-8ce1-216up(1752),
			as58xx-324up(1753),
			as5850-24e1(1754),
			as5850-24t1(1755),
			as5350-dfc-carrier(1800),
			copper-6e3(1921),
                        copper-12e3(1922),
                        iad2420-vm-8fxs(1950),
                        iad2420-16fxs(1951),
                        iad2420-vm-pwr(1952),
                        iad2420-adsl(1953),
                        iad2420-hcm1(1954),
                        iad2420-hcm2(1955),
                        iad2420-hcm3(1956),
                        iad2420-hcm4(1957),
                        iad2420-hcm5(1958),
                        iad2420-hcm6(1959),
                        iad2420-cpu(1960),
                        iad2420-mfm-e1-unbalanced(1961),
                        iad2420-mfm-e1-dsx1-csu(1962),
                        iad2420-mfm-t1-dsx1-csu(1963),
                        io-c7401-ge(2101),
                        c7300-4oc3-pos-mm(2103),
                        c7300-oc48-pos-sm-sr(2106)
                   }
                   ACCESS  read-only
                   STATUS  mandatory
                   DESCRIPTION
                           "Functional type of this card."
                   ::= { cardTableEntry 2 }

               cardDescr OBJECT-TYPE
                   SYNTAX  DisplayString
                   ACCESS  read-only
                   STATUS  mandatory
                   DESCRIPTION
                           "Text description of this card."
                   ::= { cardTableEntry 3 }

               cardSerial OBJECT-TYPE
                   SYNTAX  INTEGER
                   ACCESS  read-only
                   STATUS  mandatory
                   DESCRIPTION
                           "The serial number of this card, or zero if
                           unavailable."
                   ::= { cardTableEntry 4 }

               cardHwVersion OBJECT-TYPE
                   SYNTAX  DisplayString
                   ACCESS  read-only
                   STATUS  mandatory
                   DESCRIPTION
                           "Hardware revision level of this card, or an
                           empty string if unavailable."
                   ::= { cardTableEntry 5 }

               cardSwVersion OBJECT-TYPE
                   SYNTAX  DisplayString
                   ACCESS  read-only
                   STATUS  mandatory
                   DESCRIPTION
                           "Version of the firmware or microcode
                           installed on this card, or an empty string if
                           unavailable."
                   ::= { cardTableEntry 6 }

               cardSlotNumber OBJECT-TYPE
                   SYNTAX  INTEGER
                   ACCESS  read-only
                   STATUS  mandatory
                   DESCRIPTION
                           "Slot number relative to the containing card or 
                           chassis, or -1 if neither applicable nor 
                           determinable."
                   ::= { cardTableEntry 7 }

               cardContainedByIndex OBJECT-TYPE
                   SYNTAX  INTEGER
                   ACCESS  read-only
                   STATUS  mandatory
                   DESCRIPTION
                           "cardIndex of the parent card which
                           directly contains this card, or 0 if
                           contained by the chassis, or -1 if not
                           applicable nor determinable."
                   ::= { cardTableEntry 8 }

               cardOperStatus OBJECT-TYPE
                   SYNTAX  INTEGER {
                          not-specified(1), 
                          up(2),
                          down(3),
                          standby(4)
                      }
                   ACCESS  read-only
                   STATUS  mandatory
                   DESCRIPTION
                           "The operational status of the card.
                           cardOperStatus is up when a card is
                           recognized by the device and is enabled for
                           operation. cardOperStatus is down if the
                           card is not recognized by the device, or if
                           it is not enabled for operation.
                           cardOperStatus is standby if the card is
                           enabled and acting as a standby slave"
                   ::= { cardTableEntry 9 }

               cardSlots OBJECT-TYPE
                   SYNTAX  INTEGER
                   ACCESS  read-only
                   STATUS  mandatory
                   DESCRIPTION
                           "Number of slots on this card, or 0 if no
                           slots or not applicable, or -1 if not 
			   determinable."
                   ::= { cardTableEntry 10 }

               -- End of table


               chassisSlots OBJECT-TYPE
                   SYNTAX  INTEGER
                   ACCESS  read-only
                   STATUS  mandatory
                   DESCRIPTION
                           "Number of slots in this chassis, or -1 of
                           neither applicable nor determinable."
                   ::= { chassis 12 }

               cardIfIndexTable OBJECT-TYPE
                   SYNTAX  SEQUENCE OF CardIfIndexEntry
                   ACCESS  not-accessible
                   STATUS  mandatory
                   DESCRIPTION
                            "Chassis card table."
                   ::= { chassis 13 }

               cardIfIndexEntry OBJECT-TYPE
                   SYNTAX CardIfIndexEntry
                   ACCESS  not-accessible
                   STATUS  mandatory
                   DESCRIPTION
                            "Chassis card table."
                   INDEX { cardIfIndex }
               ::= { cardIfIndexTable 1 }

               CardIfIndexEntry ::=
                   SEQUENCE {
                       cardIfIndex
                           INTEGER,
                       cardIfSlotNumber
                           INTEGER,
                       cardIfPortNumber
                           INTEGER,
                       cardIfCardIndex
                           INTEGER,
                       cardIfConnectorTypeEnabled
                           INTEGER
                   }

               cardIfIndex OBJECT-TYPE
                   SYNTAX  INTEGER
                   ACCESS  read-only
                   STATUS  mandatory
                   DESCRIPTION
                           "matches RFC1213 ifTable IfIndex"
                   ::= { cardIfIndexEntry 1 }

               cardIfSlotNumber OBJECT-TYPE
                   SYNTAX  INTEGER
                   ACCESS  read-only
                   STATUS  mandatory
                   DESCRIPTION
                           "Chassis slot number, or -1 if neither
                           applicable nor determinable."
                   ::= { cardIfIndexEntry 2 }

               cardIfPortNumber OBJECT-TYPE
                   SYNTAX  INTEGER
                   ACCESS  read-only
                   STATUS  mandatory
                   DESCRIPTION
                           "Chassis port number, unique per port on a 
                            given card if available."
                   ::= { cardIfIndexEntry 3 }

               cardIfCardIndex OBJECT-TYPE
                   SYNTAX  INTEGER
                   ACCESS  read-only
                   STATUS  mandatory
                   DESCRIPTION
                           "cardIndex of the card in the Chassis 
			   cardTable which contains this interface."
                   ::= { cardIfIndexEntry 4 }

               cardIfConnectorTypeEnabled OBJECT-TYPE
                   SYNTAX  INTEGER {
                           not-specified(1), 
                           none (2),
                           rj-45 (3),
                           db-40 (4),
                           db-15 (5),
                           gbic-sx (7),
                           gbic-lx (8),
                           gbic-lh (9),
                           gbic-cx (10),
                           gbic-missing (11)

                   }
                   ACCESS  read-only
                   STATUS  mandatory
                   DESCRIPTION
                           "Interface connector type currently
                           enabled. Value will be 1 if not known or not
                           used, or 2 if none of this ports' interface
                           connectors are enabled."
                   ::= { cardIfIndexEntry 5 }

	       -- End of table

               chassisPartner OBJECT-TYPE
                   SYNTAX  INTEGER {
                        cisco(1),
                        synoptics(2),
                        chipcom(3),
                        cabletron(4),
                        dec(5),
                        ncr(6),
                        usrobotics(7),
                        alcatel(8),
                        nec(9),
                        dsc(10),
                        microcom(11),
                        oki(12),
                        ubn(13),
                        hp(14)
                   }
                   ACCESS  read-only
                   STATUS  mandatory
                   DESCRIPTION
                           "Used to determine if this is a partner 
                            variant of a product."
                   ::= { chassis 14 }

               sysUpTimeAtLastChassisChange OBJECT-TYPE
                   SYNTAX  TimeTicks
                   ACCESS  read-only
                   STATUS  mandatory
                   DESCRIPTION
                           "Time in seconds/100 from the last cold
                           start to the last change in the chassis'
                           configuration. This value will be updated
                           whenever the chassis experiences a change
                           in the count, type, or slot position of
                           a card in cardTable."
                   ::= { chassis 15 }


               END
