-- ====================================================================
-- Copyright (C) 2003 by  HUAWEI TECHNOLOGIES. All rights reserved.
--
-- Description:Huawei Datacomm OID MIB,this mib will maintain the mib oid 
--             for router and lanswitch only
-- Reference:
-- Version: V1.0
-- History:
--     Chenbaojiang,2003-01-21,initial version
-- Version: V1.01
-- History:
--     Yubo,2003-02-19,assign oid to hwVoiceGeneralMIB, hwVoiceIfMIB, hwVoiceAnalogInterfaceMIB, hwVoiceDigitalInterfaceMIB, hwVoiceDialControlMIB
-- Version: V1.02
-- History:
--     Yubo,2003-03-11,assign oid to hwVoiceCallActiveMIB, hwVoiceCallHistoryMIB, hwVoiceGKClientMIB, hwVoiceAAAClientMIB, hwSystemMan
--     Yubo,2003-03-17,assign oid to hwVoiceH323CallStatMIB,
--			             hwFWTP,hwHIIP,hwHRP,
--			             hwASPF,hwNAT,hwBLS,hwMACBIND,hwATCKDF,hwSECSTAT,hwPFLT,hwTRNG,hwPAM,hwSZONE,hwSLOG
-- Version: V1.03
-- History:
--     Yubo,2003-03-21,assign oid to hwSSHMIB.
--
-- Version: V1.04
-- History:
--     Yubo,2003-04-09,assign oid to hwUserLogMIB.
--     Yubo,2003-04-10,modify description of 25.10 and 25.14
--     Yubo,2003-04-11,modify oid of hwSystemMan ,assign oid to hwTACACS,hwIPX,hwNBPortalMIB
--     Yubo,2003-04-14 remove  "ifEntry,InterfaceIndex FROM IF-MIB"
-- ====================================================================

HUAWEI-DATACOMM-OID-MIB    DEFINITIONS ::= BEGIN

IMPORTS
    OBJECT-TYPE
        FROM RFC-1212
    enterprises
        FROM RFC1155-SMI;

huawei                  OBJECT IDENTIFIER ::= { enterprises 2011 }
hwLocal                 OBJECT IDENTIFIER ::= { huawei 1 }
products                OBJECT IDENTIFIER ::= { huawei 2 }
oem                     OBJECT IDENTIFIER ::= { huawei 3 }
huaweiExperimental      OBJECT IDENTIFIER ::= { huawei 4 }
huaweiMgmt              OBJECT IDENTIFIER ::= { huawei 5 }
huaweiUtility           OBJECT IDENTIFIER ::= { huawei 6 }
huaweiMpls              OBJECT IDENTIFIER ::= { huawei 13 } 
huaweiDatacomm          OBJECT IDENTIFIER ::= { huaweiMgmt 25 }

--  HUAWEI datacommunication extension mib 
voice                   OBJECT IDENTIFIER ::= { huaweiDatacomm 1 }

-- name: guoxiaojun
-- id: 29157
-- product: R2600,R1700,R3600
-- reason: new mib requirement for voice

hwVoiceGeneralMIB              OBJECT IDENTIFIER ::= { voice 1 }

hwVoiceIfMIB                   OBJECT IDENTIFIER ::= { voice 2 }

hwVoiceAnalogInterfaceMIB      OBJECT IDENTIFIER ::= { voice 3 }

hwVoiceDigitalInterfaceMIB     OBJECT IDENTIFIER ::= { voice 4 }

hwVoiceDialControlMIB          OBJECT IDENTIFIER ::= { voice 5 }

hwVoiceCallActiveMIB           OBJECT IDENTIFIER ::= { voice 6 }

hwVoiceCallHistoryMIB          OBJECT IDENTIFIER ::= { voice 7 }

hwVoiceGKClientMIB	       OBJECT IDENTIFIER ::= { voice 8 }           

hwVoiceAAAClientMIB	       OBJECT IDENTIFIER ::= { voice 9 }

hwVoiceH323CallStatMIB	       OBJECT IDENTIFIER ::= { voice 11 }

-- name: guoxiaojun
-- id: 29157
-- product: R2600,R1700,R3600
-- reason: new mib requirement for voice General ,voice interface , voice analog interface, voice digital interface, voice dial control, call active, call history, GK client, AAA client,H323 call sataict.

hwIPX	       OBJECT IDENTIFIER ::= { huaweiDatacomm 2 }

hwFWTP	       OBJECT IDENTIFIER ::= { huaweiDatacomm 3 }

hwHIIP	       OBJECT IDENTIFIER ::= { huaweiDatacomm 4 }

hwHRP	       OBJECT IDENTIFIER ::= { huaweiDatacomm 5 }

-- name: xuqingwei
-- id: 27902
-- product: 
-- reason: new mib requirement for hwIPX,hwFWTP,hwHIIP,hwHRP.


hwASPF		OBJECT IDENTIFIER ::= { huaweiDatacomm 6 }

hwNAT		OBJECT IDENTIFIER ::= { huaweiDatacomm 7 }

hwBLS		OBJECT IDENTIFIER ::= { huaweiDatacomm 8 }

hwMACBIND	OBJECT IDENTIFIER ::= { huaweiDatacomm 9 }	

hwATK	        OBJECT IDENTIFIER ::= { huaweiDatacomm 10 }

hwSECSTAT	OBJECT IDENTIFIER ::= { huaweiDatacomm 11 }

hwPFLT		OBJECT IDENTIFIER ::= { huaweiDatacomm 12 }

hwTRNG		OBJECT IDENTIFIER ::= { huaweiDatacomm 13 }

hwSMAP		OBJECT IDENTIFIER ::= { huaweiDatacomm 14 }

hwSZONE		OBJECT IDENTIFIER ::= { huaweiDatacomm 15 }

hwSLOG		OBJECT IDENTIFIER ::= { huaweiDatacomm 16 }

-- name: xuqingwei
-- id: 27902
-- product: 
-- reason: new mib requirement for safety characteristic.

hwSSHMIB	       OBJECT IDENTIFIER ::= { huaweiDatacomm 17 }

-- name: guoxiaojun
-- id: 29157
-- product: R2600,R1700,R3600
-- reason: new mib requirement for SSH.

hwUserLogMIB	       OBJECT IDENTIFIER ::= { huaweiDatacomm 18 }

-- name: libingshan
-- id: 22055
-- product: NE05/08/08E/16/16E
-- reason: new mib requirement for user log.

hwSystemMan    OBJECT IDENTIFIER ::= { huaweiDatacomm 19 }

-- name: xuqingwei
-- id: 27902
-- product: 
-- reason: new mib requirement for system management

hwTACACS    OBJECT IDENTIFIER ::= { huaweiDatacomm 20 }

-- name: limeng 
-- id: 15814
-- product: 
-- reason: new mib requirement for hwTACACS (to send Email)

hwNBPortalMIB	       OBJECT IDENTIFIER ::= { huaweiDatacomm 21 }

-- name: libingshan
-- id: 22055
-- product: NE05/08/08E/16/16E
-- reason: new mib requirement for portal of router narrowband.


END
