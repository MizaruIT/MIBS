-- ============================================================================
-- Copyright (C) 2012 by  HUAWEI TECHNOLOGIES. All rights reserved.
-- Description:  The mib is used for configuring QoS such as queue scheduling
--               rate limiting, rate mirroring and so on.
-- Reference:    
-- Version:      V1.19
-- ============================================================================

  HUAWEI-QOS-MIB DEFINITIONS ::= BEGIN
 
    IMPORTS
        huaweiMgmt      
            FROM HUAWEI-MIB     
        Counter64, Integer32, Unsigned32,OBJECT-TYPE, MODULE-IDENTITY, NOTIFICATION-TYPE     
            FROM SNMPv2-SMI        
        MacAddress, TruthValue, RowStatus     
            FROM SNMPv2-TC;
  
    hwLswQosAclMib MODULE-IDENTITY 
        LAST-UPDATED "201206051200Z"    
        ORGANIZATION 
            "Huawei Technologies Co.,Ltd."
        CONTACT-INFO                                        
            "Huawei Industrial Base
             Bantian, Longgang
             Shenzhen 518129
             People's Republic of China
             Website: http://www.huawei.com
             Email: support@huawei.com
            "                                      
        DESCRIPTION 
            "The mib is used for configuring QoS such as queue scheduling
             rate limiting, rate mirroring and so on."   
        
        -- Revision history   
        REVISION    "201206051200Z"              
        DESCRIPTION "V1.19, add a leaf node hwAclUserSideActionmode in hwLswQosAclMib.
                     modified value range of hwRateLimitTargetRate.
                     modified value range of hwOntRateLimitOntId." 
	                       
        REVISION    "201111261200Z"              
        DESCRIPTION "V1.18, modified the description of hwRateLimitAclIndex, hwPriorityAclIndex, 
                     hwRedirectAclIndex, hwStatisticAclIndex and hwMirrorAclIndex.
                     modified the description and value range of hwLineRateValue and hwLineRateInboundValue." 
                
        REVISION    "201109101200Z"  
        DESCRIPTION "V1.17, modified the description of hwRateLimitTable, hwPriorityTable, hwRedirectTable, hwStatisticTable and hwMirrorTable." 
        
        REVISION    "201102221200Z"  
        DESCRIPTION "V1.16, add hwOntRateLimitTable in hwLswQosAclMib." 
        
        REVISION    "201101130000Z"  
        DESCRIPTION "V1.15, modify hwRateLimitTable, hwPriorityTable, hwRedirectTable, hwStatisticTable and hwMirrorTable for IPv6." 
        
        REVISION    "201008191500Z"  
        DESCRIPTION "V1.14, add hwMirrorEthHead in hwLswQosAclMib." 
        
        REVISION    "201011220000Z"  
        DESCRIPTION "V1.13, modified description of hwQueueTable and hwRateLimitDirection."    
        
        REVISION    "201011190000Z"  
        DESCRIPTION "V1.12, modified description of hwQueueEntry."            
        
        REVISION    "201007230000Z"  
        DESCRIPTION "V1.11, modified description."
             
        REVISION    "201004261500Z"  
        DESCRIPTION "V1.10, modified description and value range of hwRateLimitDirection."
        
        REVISION    "201004150000Z"  
        DESCRIPTION "V1.09, modified description." 
            
        REVISION    "201002100000Z"  
        DESCRIPTION "V1.08, modified name of module from HUAWEI_LQOS_MIB to HUAWEI-QOS-MIB."

        REVISION    "200912301500Z"  
        DESCRIPTION "V1.07, modified format of this file."

        REVISION    "200912221500Z"  
        DESCRIPTION "V1.06, modified datatype definition,description of objects and add traps."
        
        REVISION    "200909040000Z"    
        DESCRIPTION "V1.04, added hwLineRateValue in hwLineRateTable and modify the value range of hwLineRateInboundValue."    
        
        REVISION    "200803040000Z"     
        DESCRIPTION "V1.02, added hwLineRateInboundValue in hwLineRateTable."     
          
        REVISION    "200512130000Z"     
        DESCRIPTION "V1.00, initial draft"      
          
        ::= { huaweiMgmt 2 }
    
    -- 1.3.6.1.4.1.2011.5.2.2
    hwQueueTable OBJECT-TYPE
        SYNTAX SEQUENCE OF HwQueueEntry
        MAX-ACCESS not-accessible
        STATUS current
        DESCRIPTION
            "Indicates the queue scheduling feature, there is only one item.
             The index of this table is hwQueuePortIfIndex.
            "
        ::= { hwLswQosAclMib 2 }    
      
    -- 1.3.6.1.4.1.2011.5.2.2.1
    hwQueueEntry OBJECT-TYPE
        SYNTAX HwQueueEntry
        MAX-ACCESS not-accessible
        STATUS current
        DESCRIPTION
            "Indicates the queue scheduling feature, there is only one item.
             The index of this entry is hwQueuePortIfIndex.
            "
        INDEX { hwQueuePortIfIndex }
        ::= { hwQueueTable 1 }
    
    HwQueueEntry ::=
        SEQUENCE { 
          hwQueuePortIfIndex
            Integer32,
          hwQueueScheduleMode
            INTEGER,
          hwQueueWeight1
            Integer32,
          hwQueueWeight2
            Integer32,
          hwQueueWeight3
            Integer32,
          hwQueueWeight4
            Integer32,
          hwQueueWeight5
            Integer32,
          hwQueueWeight6
            Integer32,
          hwQueueWeight7
            Integer32,
          hwQueueWeight8
            Integer32,
          hwWFQMaxWeight1
            Integer32,
          hwWFQMaxWeight2
            Integer32,
          hwWFQMaxWeight3
            Integer32,
          hwWFQMaxWeight4
            Integer32,
          hwWFQMaxWeight5
            Integer32,
          hwWFQMaxWeight6
            Integer32,
          hwWFQMaxWeight7
            Integer32,
          hwWFQMaxWeight8
            Integer32,
          hwQueueMaxDelay
            Integer32
         }

    -- 1.3.6.1.4.1.2011.5.2.2.1.1
    hwQueuePortIfIndex OBJECT-TYPE
        SYNTAX Integer32 (1..255)
        MAX-ACCESS read-only
        STATUS current
        DESCRIPTION
            "The index of the table, it is used to configure the interface index for queue scheduling. 
             Range: 1-255 
             0 indicates global.
            "
        ::= { hwQueueEntry 1 }
    
    -- 1.3.6.1.4.1.2011.5.2.2.1.2
    hwQueueScheduleMode OBJECT-TYPE
        SYNTAX INTEGER
        {
          sp(1),
          wrr(2),
          wfq(8)
        }
        MAX-ACCESS read-write
        STATUS current
        DESCRIPTION
            "The flag indicates the queue scheduling mode.
             Options:
             1. sp(1)  -indicates the strict priority queue scheduling mode
             2. wrr(2) -indicates the weighted round robin mode
             3. wfq(8) -indicates the weighted fair queuing mode
            "
        DEFVAL { sp }
        ::= { hwQueueEntry 2 }
    
    -- 1.3.6.1.4.1.2011.5.2.2.1.3
    hwQueueWeight1 OBJECT-TYPE
        SYNTAX Integer32 (0..100)
        MAX-ACCESS read-write
        STATUS current
        DESCRIPTION
            "In the WRR mode, it indicates the weight of queue 1; 0 indicates an invalid value. 
             In the WFQ mode, it indicates the minimum bandwidth quota of queue 1.
            "
        ::= { hwQueueEntry 3 }
    
    -- 1.3.6.1.4.1.2011.5.2.2.1.4
    hwQueueWeight2 OBJECT-TYPE
        SYNTAX Integer32 (0..100)
        MAX-ACCESS read-write
        STATUS current
        DESCRIPTION
            "In the WRR mode, it indicates the weight of queue 2; 0 indicates an invalid value. 
             In the WFQ mode, it indicates the minimum bandwidth quota of queue 2.
            "
        ::= { hwQueueEntry 4 }
    
    -- 1.3.6.1.4.1.2011.5.2.2.1.5
    hwQueueWeight3 OBJECT-TYPE
        SYNTAX Integer32 (0..100)
        MAX-ACCESS read-write
        STATUS current
        DESCRIPTION
            "In the WRR mode, it indicates the weight of queue 3; 0 indicates an invalid value. 
             In the WFQ mode, it indicates the minimum bandwidth quota of queue 3.
            "
        ::= { hwQueueEntry 5 }
    
    -- 1.3.6.1.4.1.2011.5.2.2.1.6
    hwQueueWeight4 OBJECT-TYPE
        SYNTAX Integer32 (0..100)
        MAX-ACCESS read-write
        STATUS current
        DESCRIPTION
            "In the WRR mode, it indicates the weight of queue 4; 0 indicates an invalid value. 
             In the WFQ mode, it indicates the minimum bandwidth quota of queue 4.
            "
        ::= { hwQueueEntry 6 }
    
    -- 1.3.6.1.4.1.2011.5.2.2.1.7
    hwQueueWeight5 OBJECT-TYPE
        SYNTAX Integer32 (0..100)
        MAX-ACCESS read-write
        STATUS current
        DESCRIPTION
            "In the WRR mode, it indicates the weight of queue 5; 0 indicates an invalid value. 
             In the WFQ mode, it indicates the minimum bandwidth quota of queue 5.
            "
        ::= { hwQueueEntry 7 }
    
    -- 1.3.6.1.4.1.2011.5.2.2.1.8
    hwQueueWeight6 OBJECT-TYPE
        SYNTAX Integer32 (0..100)
        MAX-ACCESS read-write
        STATUS current
        DESCRIPTION
            "In the WRR mode, it indicates the weight of queue 6; 0 indicates an invalid value. 
             In the WFQ mode, it indicates the minimum bandwidth quota of queue 6.
            "
        ::= { hwQueueEntry 8 }
    
    -- 1.3.6.1.4.1.2011.5.2.2.1.9
    hwQueueWeight7 OBJECT-TYPE
        SYNTAX Integer32 (0..100)
        MAX-ACCESS read-write
        STATUS current
        DESCRIPTION
            "In the WRR mode, it indicates the weight of queue 7; 0 indicates an invalid value. 
             In the WFQ mode, it indicates the minimum bandwidth quota of queue 7.
            "
        ::= { hwQueueEntry 9 }
    
    -- 1.3.6.1.4.1.2011.5.2.2.1.10
    hwQueueWeight8 OBJECT-TYPE
        SYNTAX Integer32 (0..100)
        MAX-ACCESS read-write
        STATUS current
        DESCRIPTION
            "In the WRR mode, it indicates the weight of queue 8; 0 indicates an invalid value. 
             In the WFQ mode, it indicates the minimum bandwidth quota of queue 8.
            "
        ::= { hwQueueEntry 10 }
    
    -- 1.3.6.1.4.1.2011.5.2.2.1.11
    hwWFQMaxWeight1 OBJECT-TYPE
        SYNTAX Integer32 (0..100)
        MAX-ACCESS read-write
        STATUS current
        DESCRIPTION
            "Maximum bandwidth quota of queue 1"
        ::= { hwQueueEntry 11 }
    
    -- 1.3.6.1.4.1.2011.5.2.2.1.12
    hwWFQMaxWeight2 OBJECT-TYPE
        SYNTAX Integer32 (0..100)
        MAX-ACCESS read-write
        STATUS current
        DESCRIPTION
            "Maximum bandwidth quota of queue 2"
        ::= { hwQueueEntry 12 }
    
    -- 1.3.6.1.4.1.2011.5.2.2.1.13
    hwWFQMaxWeight3 OBJECT-TYPE
        SYNTAX Integer32 (0..100)
        MAX-ACCESS read-write
        STATUS current
        DESCRIPTION
            "Maximum bandwidth quota of queue 3"
        ::= { hwQueueEntry 13 }
    
    -- 1.3.6.1.4.1.2011.5.2.2.1.14
    hwWFQMaxWeight4 OBJECT-TYPE
        SYNTAX Integer32 (0..100)
        MAX-ACCESS read-write
        STATUS current
        DESCRIPTION
            "Maximum bandwidth quota of queue 4"
        ::= { hwQueueEntry 14 }
    
    -- 1.3.6.1.4.1.2011.5.2.2.1.15
    hwWFQMaxWeight5 OBJECT-TYPE
        SYNTAX Integer32 (0..100)
        MAX-ACCESS read-write
        STATUS current
        DESCRIPTION
            "Maximum bandwidth quota of queue 5"
        ::= { hwQueueEntry 15 }
    
    -- 1.3.6.1.4.1.2011.5.2.2.1.16
    hwWFQMaxWeight6 OBJECT-TYPE
        SYNTAX Integer32 (0..100)
        MAX-ACCESS read-write
        STATUS current
        DESCRIPTION
            "Maximum bandwidth quota of queue 6"
        ::= { hwQueueEntry 16 }
    
    -- 1.3.6.1.4.1.2011.5.2.2.1.17
    hwWFQMaxWeight7 OBJECT-TYPE
        SYNTAX Integer32 (0..100)
        MAX-ACCESS read-write
        STATUS current
        DESCRIPTION
            "Maximum bandwidth quota of queue 7"
        ::= { hwQueueEntry 17 }
    
    -- 1.3.6.1.4.1.2011.5.2.2.1.18
    hwWFQMaxWeight8 OBJECT-TYPE
        SYNTAX Integer32 (0..100)
        MAX-ACCESS read-write
        STATUS current
        DESCRIPTION
            "Maximum bandwidth quota of queue 8"
        ::= { hwQueueEntry 18 }
    
    -- 1.3.6.1.4.1.2011.5.2.2.1.19
    hwQueueMaxDelay OBJECT-TYPE
        SYNTAX Integer32 (0..4080)
        MAX-ACCESS read-only
        STATUS current
        DESCRIPTION
            "Maximum delay. 
             0 indicates an invalid value, invalid in current version.
            "
        ::= { hwQueueEntry 19 }
    
    -- 1.3.6.1.4.1.2011.5.2.3
    hwRateLimitTable OBJECT-TYPE
        SYNTAX SEQUENCE OF HwRateLimitEntry
        MAX-ACCESS not-accessible
        STATUS current
        DESCRIPTION
            "Describes the traffic limitation on packets that are received by a specified port or a specified slot and that match the ACL rule. 
             The indexes of this table are hwRateLimitAclIndex, hwRateLimitIfIndex, and hwRateLimitDirection.
             Make sure that the ACL rule in hwRateLimitTable is already created in hwAclBasicRuleTable, hwAclAdvancedRuleTable, 
             hwAclLinkTable, or hwAclUserTable. 
            "
        ::= { hwLswQosAclMib 3 }
    
    -- 1.3.6.1.4.1.2011.5.2.3.1
    hwRateLimitEntry OBJECT-TYPE
        SYNTAX HwRateLimitEntry
        MAX-ACCESS not-accessible
        STATUS current
        DESCRIPTION
            "Describes the traffic limitation on packets that are received by a specified port or a specified slot and that match the ACL rule. 
             The indexes of this entry are hwRateLimitAclIndex, hwRateLimitIfIndex, and hwRateLimitDirection.
             Make sure that the ACL rule in hwRateLimitTable is already created in hwAclBasicRuleTable, hwAclAdvancedRuleTable, 
             hwAclLinkTable, or hwAclUserTable.
            "
        INDEX { hwRateLimitAclIndex, hwRateLimitIfIndex, hwRateLimitDirection }
        ::= { hwRateLimitTable 1 }
    
    HwRateLimitEntry ::=
        SEQUENCE { 
          hwRateLimitAclIndex
            Integer32,
          hwRateLimitIfIndex
            Unsigned32,
          hwRateLimitDirection
            INTEGER,
          hwRateLimitUserAclNum
            Integer32,
          hwRateLimitUserAclSubitem
            Unsigned32,
          hwRateLimitIpAclNum
            Integer32,
          hwRateLimitIpAclSubitem
            Unsigned32,
          hwRateLimitLinkAclNum
            Integer32,
          hwRateLimitLinkAclSubitem
            Unsigned32,
          hwRateLimitTargetRate
            Integer32,
          hwRateLimitExceedDrop
            TruthValue,
          hwRateLimitExceedDscp
            Integer32,
          hwRateLimitRuntime
            TruthValue,
          hwRateLimitRowStatus
            RowStatus,
          hwRateLimitCir
            Integer32,
          hwRateLimitCbs
            Integer32,
          hwRateLimitPir
            Integer32,
          hwRateLimitPbs
            Integer32,
          hwRateLimitIpv6AclNum
            Integer32,
          hwRateLimitIpv6AclSubitem
            Unsigned32,
          hwRateLimitRedDrop
            TruthValue, 
          hwRateLimitRedRemarkDscp
            Integer32, 
          hwRateLimitYellowDrop
            TruthValue,
          hwRateLimitYellowRemarkDscp
            Integer32
         }    
       
    -- 1.3.6.1.4.1.2011.5.2.3.1.1
    hwRateLimitAclIndex OBJECT-TYPE
        SYNTAX Integer32 (0..2999)
        MAX-ACCESS read-only
        STATUS current
        DESCRIPTION
            "The delivery entry index of an ACL rule used for traffic limitation is a delivery record entry index used by software, 
             which is meaningless to users. The index is used in hwRateLimitTable to search the delivery entries fast. 
             Range: 0-2999
             In the create operation, the device automatically allocates a delivery entry index. 
             There is a suggestion that users can always input 0.
            "
        ::= { hwRateLimitEntry 1 }
    
    -- 1.3.6.1.4.1.2011.5.2.3.1.2
    hwRateLimitIfIndex OBJECT-TYPE
        SYNTAX Unsigned32 (0|1..4294967295)
        MAX-ACCESS read-only
        STATUS current
        DESCRIPTION
            "Specifies the index of a port or a slot for traffic limitation. 
             It uniquely identifies a port or a slot. 
             The value and algorithm are the same as those of ifIndex. 
             
             If the configuration based on a slot, the bits map is shown as follows:
             ---------------------------------------------------------------------------------------------------------------
             | 31-25 bits          | 24-19 bits         | 18-13 bits         | 12-6 bits            | 5-0 bits is reserved |
             | indicate iftype     | indicate frame ID  | indicate slot ID   | indicate port ID     |                      |               
             --------------------------------------------------------------------------------------------------------------- 
             | the value of iftype | frame ID           | slot ID            | the value of port ID | the reserved value   |
             | is always 0x68      |                    |                    | is always 0          | is always 0          |
             ---------------------------------------------------------------------------------------------------------------
             Range: 0-4294967295
            "
        ::= { hwRateLimitEntry 2 }
    
    -- 1.3.6.1.4.1.2011.5.2.3.1.3
    hwRateLimitDirection OBJECT-TYPE
        SYNTAX INTEGER
          {
          invalid(0),
          inbound(1),
          outbound(2)
          }
        MAX-ACCESS read-only
        STATUS current
        DESCRIPTION
            "Indicates the direction where an ACL rule used for traffic limitation takes effect. 
             Currently, only the inbound direction is supported. 
             Options:
             1. invalid(0)   -indicates an invalid parameter
             2. inbound(1)   -indicates the inbound direction of a port or a slot
             3. outbound(2)  -indicates the outbound direction of a port or a slot            
             "
        ::= { hwRateLimitEntry 3 }
    
    -- 1.3.6.1.4.1.2011.5.2.3.1.4
    hwRateLimitUserAclNum OBJECT-TYPE
        SYNTAX Integer32 (0 | 5000..5999)
        MAX-ACCESS read-create
        STATUS current
        DESCRIPTION
            "Describes the user-defined ACL rule group that is used when 
             a user-defined ACL rule for traffic limitation is delivered to a specified port or a specified slot.
             Range: 0, 5000-5999
             Make sure that the user-defined ACL rule group is already created. 
             In the query operation, if the user-defined ACL rule group is not used, the value obtained is 0. 
            "
        ::= { hwRateLimitEntry 4 }
    
    -- 1.3.6.1.4.1.2011.5.2.3.1.5
    hwRateLimitUserAclSubitem OBJECT-TYPE
        SYNTAX Unsigned32 (0|1..4294967295)
        MAX-ACCESS read-create
        STATUS current
        DESCRIPTION
            "Describes the user-defined ACL rule that is used when a user-defined ACL rule for traffic limitation is delivered to a specified port or a specified slot. 
             This leaf must be used together with hwRateLimitUserAclNum, uniquely identifying an ACL rule.
             Range: 0-4294967295
             Make sure that the user-defined ACL rule is already created. 
             In the query operation, if the user-defined ACL rule is not used, the value obtained is 4294967295. 
            "
        ::= { hwRateLimitEntry 5 }   

    -- 1.3.6.1.4.1.2011.5.2.3.1.6
    hwRateLimitIpAclNum OBJECT-TYPE
        SYNTAX Integer32 (0 | 2000..3999)
        MAX-ACCESS read-create
        STATUS current
        DESCRIPTION
            "Describes the basic or advanced ACL rule group that is used when 
             a basic or advanced ACL rule for traffic limitation is delivered to a specified port or a specified slot.
             Range: 0, 2000-3999
             Make sure that the basic or advanced ACL rule group is already created. 
             In the query operation, if the basic or advanced ACL rule group is not used, the value obtained is 0. 
            "
        ::= { hwRateLimitEntry 6 }
    
    -- 1.3.6.1.4.1.2011.5.2.3.1.7
    hwRateLimitIpAclSubitem OBJECT-TYPE
        SYNTAX Unsigned32 (0|1..4294967295)
        MAX-ACCESS read-create
        STATUS current
        DESCRIPTION     
            "Describes the basic or advanced ACL rule that is used when a basic or advanced ACL rule 
            for traffic limitation is delivered to a specified port or a specified slot. 
            This leaf must be used together with hwRateLimitIpAclNum, uniquely identifying an ACL rule. 
            Range: 0-4294967295
            Make sure that the basic or advanced ACL rule is already created. 
            In the query operation, if the basic or advanced ACL rule is not used, the value obtained is 4294967295. 
            "
        ::= { hwRateLimitEntry 7 }
    
    -- 1.3.6.1.4.1.2011.5.2.3.1.8
    hwRateLimitLinkAclNum OBJECT-TYPE
        SYNTAX Integer32 (0 | 4000..4999)
        MAX-ACCESS read-create
        STATUS current
        DESCRIPTION
            "Describes the L2 ACL rule group that is used when an L2 ACL rule for traffic limitation is delivered to a specified port or a specified slot.
             Range: 0, 4000-4999
             Make sure that the L2 ACL rule group is already created. 
             In the query operation, if the L2 ACL rule group is not used, the value obtained is 0. 
            "
        ::= { hwRateLimitEntry 8 }
    
    -- 1.3.6.1.4.1.2011.5.2.3.1.9
    hwRateLimitLinkAclSubitem OBJECT-TYPE
        SYNTAX Unsigned32 ( 0|1..4294967295)
        MAX-ACCESS read-create
        STATUS current
        DESCRIPTION
            "Describes the L2 ACL rule that is used when an L2 ACL rule for traffic limitation is delivered to a specified port or a specified slot. 
             This leaf must be used together with hwRateLimitLinkAclNum, uniquely identifying an ACL rule.
             Range: 0-4294967295
             Make sure that the L2 ACL rule is already created. 
             In the query operation, if the L2 ACL rule is not used, the value obtained is 4294967295. 
            "
        ::= { hwRateLimitEntry 9 }
    
    -- 1.3.6.1.4.1.2011.5.2.3.1.10
    hwRateLimitTargetRate OBJECT-TYPE
        SYNTAX Integer32 (0|64..10000000)
        MAX-ACCESS read-create
        STATUS current
        DESCRIPTION
            "Indicates the target value of traffic limitation on a port or a specified slot. 
             Range: 64-10000000 (which must be an integer multiple of 64)
             Unit: Kbit/s. 
             0 indicates an invalid value.
            "
        ::= { hwRateLimitEntry 10 }
    
    -- 1.3.6.1.4.1.2011.5.2.3.1.11
    hwRateLimitExceedDrop OBJECT-TYPE
        SYNTAX TruthValue
        MAX-ACCESS read-create
        STATUS current
        DESCRIPTION
            "Indicates the action when traffic exceeds the target value.     
             Options:
             1.true(1)   -discard    
             2.false(2)  -not discard
             If this leaf is not specified, the default value is true(1).
             In the set operation, if false(2) is entered, must input valid value of hwRateLimitExceedDscp, 
             otherwise the default value is true(1) will take effect. 
            "
        DEFVAL { 1 }
        ::= { hwRateLimitEntry 11 }
    
    -- 1.3.6.1.4.1.2011.5.2.3.1.12
    hwRateLimitExceedDscp OBJECT-TYPE
        SYNTAX Integer32 (0..63 | 255)
        MAX-ACCESS read-create
        STATUS current
        DESCRIPTION
            "Describes the specified DSCP priority when configuring the DSCP priority of the 
             packets that match the ACL rule. The larger the DSCP value is, the higher the priority is.
             Range: 0-63, 255 
             In the query operation, if this parameter is not used, the obtained value is 255, which indicates invalidity. 
             The number in the brackets is the DSCP value. 
             The names and meanings of the DSCP names are as follows: 
             af1: service of Assured Forwarding 1 (10) 
             af2: service of Assured Forwarding 2 (18) 
             af3: service of Assured Forwarding 3 (26) 
             af4: service of Assured Forwarding 4 (34) 
             be: Best Effort service (0) 
             cs1: service of Class Selector 1 (8) 
             cs2: service of Class Selector 2 (16) 
             cs3: service of Class Selector 3 (24) 
             cs4: service of Class Selector 4 (32) 
             cs5: service of Class Selector 5 (40) 
             cs6: service of Class Selector 6 (48) 
             cs7: service of Class Selector 7 (56) 
             ef: Expedited Forwarding service (46)
            "
        DEFVAL { 255 }
        ::= { hwRateLimitEntry 12 }
    
    -- 1.3.6.1.4.1.2011.5.2.3.1.13
    hwRateLimitRuntime OBJECT-TYPE
        SYNTAX TruthValue
        MAX-ACCESS read-only
        STATUS current
        DESCRIPTION
            "Describes whether the ACL rule for traffic limitation delivered to a specified port or a specified slot takes effect. 
             This leaf is read-only.
             Options:   
             1. true(1)  -if the ACL rule is associated with a time range parameter 
                          and the current time is within the defined time range, the value is true(1), 
                          which indicates validity.
             2. false(2) -if the current time is not within the defined time range, the value is false(2), 
                          which indicates invalidity.    
             If the ACL rule is not associated with a time range parameter, the value is always true(1). 
            "
        ::= { hwRateLimitEntry 13 }
    
    -- 1.3.6.1.4.1.2011.5.2.3.1.14
    hwRateLimitRowStatus OBJECT-TYPE
        SYNTAX RowStatus
        MAX-ACCESS read-create
        STATUS current
        DESCRIPTION
            "Indicates the row status. 
             It is used for delivering an ACL rule for traffic limitation to a specified port or a specified slot and 
             deleting the delivered ACL rule on a port or a specified slot.
             Options:
             1. active(1)      -when this leaf is queried, the value is fixed to active(1).
             2. createAndGo(4) -deliver an ACL rule for traffic limitation to a specified port or a specified slot
             3. destroy(6)     -delete an ACL rule delivered to a port or a slot
             When an ACL rule is delivered to a specified port or a specified slot, make sure that at least one of the 
             following groups is configured. 
             (1) hwRateLimitUserAclNum and hwRateLimitUserAclSubitem
             (2) hwRateLimitIpAclNum and hwRateLimitIpAclSubitem
             (3) hwRateLimitLinkAclNum and hwRateLimitLinkAclSubitem
             In addition to independent configuration of each group, the combined configuration of 
             group (2) and (3) is permitted. The combined configuration of group (1) and (2) or 
             combining group (1) and (3) is prohibited. In addition, hwRateLimitRowStatus must be 
             set to createAndGo(4). 
             To delete the ACL rule delivered to a port or a slot, set hwRateLimitRowStatus to destroy(6). 
             When this leaf is queried, the value is fixed to active(1).
            "
        ::= { hwRateLimitEntry 14 }
    
    -- 1.3.6.1.4.1.2011.5.2.3.1.15
    hwRateLimitCir OBJECT-TYPE
        SYNTAX Integer32 (0|64..10240000)
        MAX-ACCESS read-create
        STATUS current
        DESCRIPTION
            "Indicates the Committed information rate for rate limiting.
             Value Rage: 0, 64-10240000.
             0 indicates an invalid value.
             unit: Kbit/s
            "
        ::= { hwRateLimitEntry 15 }

    -- 1.3.6.1.4.1.2011.5.2.3.1.16
    hwRateLimitCbs OBJECT-TYPE
        SYNTAX Integer32 (0|2000..10240000)
        MAX-ACCESS read-create
        STATUS current
        DESCRIPTION
            "Indicates the Committed burst size for rate limiting.
             Value Rage: 0, 2000-10240000.
             If not set, the value is min(2000+hwRateLimitCir*32，1024000).
             0 indicates an invalid value.
             unit: byte
            "
        ::= { hwRateLimitEntry 16 }

    -- 1.3.6.1.4.1.2011.5.2.3.1.17
    hwRateLimitPir OBJECT-TYPE
        SYNTAX Integer32 (0|64..10240000)
        MAX-ACCESS read-create
        STATUS current
        DESCRIPTION
            "Indicates the Peak information rate for rate limiting.
             If not set, the value is min(hwRateLimitCir*2，10240000).
             PIR must not be less than CIR.
             Value Rage: 0, 64-10240000.
             0 indicates an invalid value.
             unit: Kbit/s
            "
        ::= { hwRateLimitEntry 17 }

    -- 1.3.6.1.4.1.2011.5.2.3.1.18
    hwRateLimitPbs OBJECT-TYPE
        SYNTAX Integer32 (0|2000..10240000)
        MAX-ACCESS read-create
        STATUS current
        DESCRIPTION
            "Indicates the Committed information rate for rate limiting.
             If not set, the value is min(2000+hwRateLimitPir*32，1024000).
             Value Rage: 0, 2000-10240000.
             0 indicates an invalid value.
             unit: byte
            "
        ::= { hwRateLimitEntry 18 }

    -- 1.3.6.1.4.1.2011.5.2.3.1.19
    hwRateLimitIpv6AclNum OBJECT-TYPE
        SYNTAX Integer32 (0|2000..3999)
        MAX-ACCESS read-create
        STATUS current
        DESCRIPTION
            "Indicates the basic or advanced ACLv6 rule group that is used when 
             a basic or advanced ACLv6 rule for traffic limitation is delivered to a specified port or a specified slot.
             Range: 0, 2000-3999
             Make sure that the basic or advanced ACLv6 rule group is already created. 
             In the query operation, if the basic or advanced ACLv6 rule group is not used, the value obtained is 0. 
            "
        ::= { hwRateLimitEntry 19 }
        
    -- 1.3.6.1.4.1.2011.5.2.3.1.20
    hwRateLimitIpv6AclSubitem OBJECT-TYPE
        SYNTAX Unsigned32 (0..4294967295)
        MAX-ACCESS read-create
        STATUS current
        DESCRIPTION
            "Indicates the basic or advanced ACLv6 rule that is used when a basic or advanced ACLv6 rule 
             for traffic limitation is delivered to a specified port or a specified slot. 
             This leaf must be used together with hwRateLimitIpv6AclNum, uniquely identifying an ACLv6 rule. 
             Range: 0-4294967295
             Make sure that the basic or advanced ACLv6 rule is already created. 
             In the query operation, if the basic or advanced ACLv6 rule is not used, the value obtained is 4294967295. 
            "
        ::= { hwRateLimitEntry 20 }  
        
    -- 1.3.6.1.4.1.2011.5.2.3.1.21
    hwRateLimitRedDrop OBJECT-TYPE
        SYNTAX TruthValue
        MAX-ACCESS read-create
        STATUS current
        DESCRIPTION
            "Indicates the action when traffic is marked to red.
             TRUE(1): discard the packets.
             FALSE(2): don't discard the packets
            "
        DEFVAL { 1 }
        ::= { hwRateLimitEntry 21 }         

    -- 1.3.6.1.4.1.2011.5.2.3.1.22
    hwRateLimitRedRemarkDscp OBJECT-TYPE
        SYNTAX Integer32 (-1|0..63)
        MAX-ACCESS read-create
        STATUS current
        DESCRIPTION
            "Indicates the new DSCP value that is preset when the preset traffic is marked to red.
             -1 indicates an invalid value
            "
        ::= { hwRateLimitEntry 22 }

    -- 1.3.6.1.4.1.2011.5.2.3.1.23
    hwRateLimitYellowDrop OBJECT-TYPE
        SYNTAX TruthValue
        MAX-ACCESS read-create
        STATUS current
        DESCRIPTION
            "Indicates the action when traffic is marked to yellow.
             TRUE(1): discard the packets.
             FALSE(2): don't discard the packets
            "
        DEFVAL { 2 }
        ::= { hwRateLimitEntry 23 } 
        
    -- 1.3.6.1.4.1.2011.5.2.3.1.24
    hwRateLimitYellowRemarkDscp OBJECT-TYPE
        SYNTAX Integer32 (-1|0..63)
        MAX-ACCESS read-create
        STATUS current
        DESCRIPTION
            "Indicates the new DSCP value that is preset when the preset traffic is marked to yellow.
             -1 indicates an invalid value
            "
        ::= { hwRateLimitEntry 24 }   
                                     
    -- 1.3.6.1.4.1.2011.5.2.4
    hwPriorityTable OBJECT-TYPE
        SYNTAX SEQUENCE OF HwPriorityEntry
        MAX-ACCESS not-accessible
        STATUS current
        DESCRIPTION
            "Describes the priority marking for packets that match the ACL rule on a specified port or a specified slot. 
             The indexes of this table are hwPriorityAclIndex, hwPriorityIfIndex and hwPriorityDirection.
             Make sure that the ACL rule in hwPriorityTable is already created in hwAclBasicRuleTable, 
             hwAclAdvancedRuleTable, hwAclLinkTable, or hwAclUserTable. 
            "
        ::= { hwLswQosAclMib 4 }
    
    -- 1.3.6.1.4.1.2011.5.2.4.1
    hwPriorityEntry OBJECT-TYPE
        SYNTAX HwPriorityEntry
        MAX-ACCESS not-accessible
        STATUS current
        DESCRIPTION
            "Describes the priority marking for packets that match the ACL rule on a specified port or a specified slot. 
             The indexes of this entry are hwPriorityAclIndex, hwPriorityIfIndex and hwPriorityDirection.
             Make sure that the ACL rule in hwPriorityTable is already created in hwAclBasicRuleTable, 
             hwAclAdvancedRuleTable, hwAclLinkTable, or hwAclUserTable. 
            "
        INDEX { hwPriorityAclIndex, hwPriorityIfIndex, hwPriorityDirection }
        ::= { hwPriorityTable 1 }
    
    HwPriorityEntry ::=
        SEQUENCE { 
          hwPriorityAclIndex
            Integer32,
          hwPriorityIfIndex
            Unsigned32,
          hwPriorityDirection
            INTEGER,
          hwPriorityUserAclNum
            Integer32,
          hwPriorityUserAclSubitem
            Unsigned32,
          hwPriorityIpAclNum
            Integer32,
          hwPriorityIpAclSubitem
            Unsigned32,
          hwPriorityLinkAclNum
            Integer32,
          hwPriorityLinkAclSubitem
            Unsigned32,
          hwPriorityDscp
            Integer32,
          hwPriorityIpPreValue
            Integer32,
          hwPriorityIpPreFromCos
            TruthValue,
          hwPriorityCosValue
            Integer32,
          hwPriorityCosFromIpPre
            TruthValue,
          hwPriorityLocalPre
            Integer32,
          hwPriorityRuntime
            TruthValue,
          hwPriorityRowStatus
            RowStatus,
          hwPriorityIpv6AclNum
            Integer32,
          hwPriorityIpv6AclSubitem
            Unsigned32                 
         }

    -- 1.3.6.1.4.1.2011.5.2.4.1.1
    hwPriorityAclIndex OBJECT-TYPE
        SYNTAX Integer32 (0..2999)
        MAX-ACCESS read-only
        STATUS current
        DESCRIPTION
            "Indicates the delivery entry index of an ACL rule for priority marking. 
             It is a delivery record entry index used by software, which is meaningless to users. 
             The index is used in hwPriorityTable to search the delivery entries fast. 
             Range: 0-2999
             In the create operation, the device automatically allocates a delivery entry index. 
             There is a suggestion that users can always input 0.
            "
        ::= { hwPriorityEntry 1 }
    
    -- 1.3.6.1.4.1.2011.5.2.4.1.2
    hwPriorityIfIndex OBJECT-TYPE
        SYNTAX Unsigned32 (0|1..4294967295)
        MAX-ACCESS read-only
        STATUS current
        DESCRIPTION
            "Indicates the port index or the slot index when the device delivers an ACL rule for priority marking to a specified port or a specified slot. 
             The index uniquely identifies a port or a slot. The value and algorithm are the same as those of ifIndex. 
             
             If the configuration based on a slot, the bits map is shown as follows:
             ---------------------------------------------------------------------------------------------------------------
             | 31-25 bits          | 24-19 bits         | 18-13 bits         | 12-6 bits            | 5-0 bits is reserved |
             | indicate iftype     | indicate frame ID  | indicate slot ID   | indicate port ID     |                      |               
             --------------------------------------------------------------------------------------------------------------- 
             | the value of iftype | frame ID           | slot ID            | the value of port ID | the reserved value   |
             | is always 0x68      |                    |                    | is always 0          | is always 0          |
             ---------------------------------------------------------------------------------------------------------------
             Range: 0-4294967295
            "
        ::= { hwPriorityEntry 2 }
    
    -- 1.3.6.1.4.1.2011.5.2.4.1.3
    hwPriorityDirection OBJECT-TYPE
        SYNTAX INTEGER
          {
          invalid(0),
          inbound(1),
          outbound(2)         
          }
        MAX-ACCESS read-only
        STATUS current
        DESCRIPTION
            "Indicates the direction where an ALC rule for priority marking 
             takes effect when the device delivers an ACL rule to a specified port or a specified slot.  
             Options:
             1. invalid(0)  -indicates an invalid parameter. 
             2. inbound(1)  -indicates the inbound direction of a port or a slot. 
                             It is used to configure the priority for the packets 
                             that are received on a specified port or a slot.  
             3. outbound(2) -indicates the outbound direction of a port or a slot. 
                             It is used to configure the priority for the packets 
                             that are transmitted on a specified port or a slot.
            "
        ::= { hwPriorityEntry 3 }
    
    -- 1.3.6.1.4.1.2011.5.2.4.1.4
    hwPriorityUserAclNum OBJECT-TYPE
        SYNTAX Integer32 (0 | 5000..5999)
        MAX-ACCESS read-create
        STATUS current
        DESCRIPTION
            "Describes the user-defined ACL rule group that is used when a user-defined 
             ACL rule for priority marking is delivered to a specified port or a specified slot. 
             Range: 0, 5000-5999
             Make sure that the user-defined ACL rule group is already created. 
             In the query operation, if the user-defined ACL rule group is not used, 
             the value obtained is 0. 
            "
        ::= { hwPriorityEntry 4 }
    
    -- 1.3.6.1.4.1.2011.5.2.4.1.5
    hwPriorityUserAclSubitem OBJECT-TYPE
        SYNTAX Unsigned32 (0|1..4294967295)
        MAX-ACCESS read-create
        STATUS current
        DESCRIPTION
            "Describes the user-defined ACL rule that is used when a user-defined 
             ACL rule for priority marking is delivered to a specified port or a specified slot.
             This leaf must be used together with hwPriorityUserAclNum, 
             uniquely identifying an ACL rule
             Range: 0-4294967295
             Make sure that the user-defined ACL rule is already created. 
             In the query operation, if the user-defined ACL rule is not used, 
             the value obtained is 4294967295. 
            "
        ::= { hwPriorityEntry 5 }
    
    -- 1.3.6.1.4.1.2011.5.2.4.1.6
    hwPriorityIpAclNum OBJECT-TYPE
        SYNTAX Integer32 (0 | 2000..3999)
        MAX-ACCESS read-create
        STATUS current
        DESCRIPTION
            "Describes the basic or advanced ACL rule group that is used when a basic or 
             advanced ACL rule for priority marking is delivered to a specified port or a specified slot.
             Range: 0, 2000-3999
             Make sure that the basic or advanced ACL rule group is already created. 
             In the query operation, if the basic or advanced ACL rule group is not used, 
             the value obtained is 0. 
            "
        ::= { hwPriorityEntry 6 }
    
    -- 1.3.6.1.4.1.2011.5.2.4.1.7
    hwPriorityIpAclSubitem OBJECT-TYPE
        SYNTAX Unsigned32 (0|1..4294967295)
        MAX-ACCESS read-create
        STATUS current
        DESCRIPTION
            "Describes the basic or advanced ACL rule that is used when a basic or advanced 
             ACL rule for priority marking is delivered to a specified port or a specified slot.
             This leaf must be used together with hwPriorityIpAclNum, 
             uniquely identifying an ACL rule.
             Range: 0-4294967295
             Make sure that the basic or advanced ACL rule group is already created. 
             In the query operation, if the basic or advanced ACL rule is not used, 
             the value obtained is 4294967295. 
            "
        ::= { hwPriorityEntry 7 }
    
    -- 1.3.6.1.4.1.2011.5.2.4.1.8
    hwPriorityLinkAclNum OBJECT-TYPE
        SYNTAX Integer32 (0 | 4000..4999)
        MAX-ACCESS read-create
        STATUS current
        DESCRIPTION
            "Describes the L2 ACL rule group that is used when an L2 ACL rule for 
             priority marking is delivered to a specified port or a specified slot. 
             Range: 0, 4000-4999
             Make sure that the L2 ACL rule group is already created. 
             In the query operation, if the L2 ACL rule group is not used, 
             the value obtained is 0.
            "
        ::= { hwPriorityEntry 8 }
    
    -- 1.3.6.1.4.1.2011.5.2.4.1.9
    hwPriorityLinkAclSubitem OBJECT-TYPE
        SYNTAX Unsigned32 (0|1..4294967295)
        MAX-ACCESS read-create
        STATUS current
        DESCRIPTION
            "Describes the L2 ACL rule that is used when an L2 ACL rule for priority 
             marking is delivered to a specified port or a specified slot. 
             This leaf must be used together with hwPriorityLinkAclNum, 
             uniquely identifying an ACL rule.
             Range: 0-4294967295
             Make sure that the L2 ACL rule is already created. 
             In the query operation, if the L2 ACL rule is not used, 
             the value obtained is 4294967295. 
            "
        ::= { hwPriorityEntry 9 }
    
    -- 1.3.6.1.4.1.2011.5.2.4.1.10
    hwPriorityDscp OBJECT-TYPE
        SYNTAX Integer32 (0..63 | 255)
        MAX-ACCESS read-create
        STATUS current
        DESCRIPTION
            "Describes the specified DSCP priority when configuring the DSCP priority for 
             the packets that match the ACL rule for priority marking. 
             The larger the DSCP value is, the higher the priority is.
             Range: 0-63, 255 
             In the query operation, if this parameter is not used, 
             the obtained value is 255, which indicates invalidity. 
             The number in the brackets is the DSCP value. 
             The names and meanings of the DSCP names are as follows: 
             af1:   service of Assured Forwarding 1 (10) 
             af2:   service of Assured Forwarding 2 (18) 
             af3:   service of Assured Forwarding 3 (26) 
             af4:   service of Assured Forwarding 4 (34) 
             be:    Best Effort service (0) 
             cs1:   service of Class Selector 1 (8) 
             cs2:   service of Class Selector 2 (16) 
             cs3:   service of Class Selector 3 (24) 
             cs4:   service of Class Selector 4 (32) 
             cs5    service of Class Selector 5 (40) 
             cs6:   service of Class Selector 6 (48) 
             cs7:   service of Class Selector 7 (56) 
             ef:    Expedited Forwarding service (46)
            "
        DEFVAL { 255 }
        ::= { hwPriorityEntry 10 }
    
    -- 1.3.6.1.4.1.2011.5.2.4.1.11
    hwPriorityIpPreValue OBJECT-TYPE
        SYNTAX Integer32 (0..7 | 255)
        MAX-ACCESS read-create
        STATUS current
        DESCRIPTION
            "Describes the specified IP precedence when configuring the IP precedence
             for the packets that match the ACL rule for precedence marking.
             Range: 0-7, 255
             The larger the value is, the higher the precedence is. 
             In the query operation, if this parameter is not used, 
             the obtained value is 255, which indicates invalidity. 
             Meanings: 
             routine:           Routine precedence (0) 
             priority:          Priority precedence (1) 
             immediate:         Immediate precedence (2)
             flash:             Flash precedence (3) 
             flash-override:    Flash-override precedence (4) 
             critical:          Critical precedence (5) 
             internet:          Internetwork control precedence (6) 
             network:           Network control precedence (7)
            "
        DEFVAL { 255 }
        ::= { hwPriorityEntry 11 }
    
    -- 1.3.6.1.4.1.2011.5.2.4.1.12
    hwPriorityIpPreFromCos OBJECT-TYPE
        SYNTAX TruthValue
        MAX-ACCESS read-create
        STATUS current
        DESCRIPTION
            "Indicates whether to set the IP priority the same as the 802.1p priority, 
             that is, copy the 802.1p priority.     
             Options:
             1. true(1)  -copy     
             2. false(2) -not copy
             If this leaf is not specified, the default value is false(2). 
            "
        DEFVAL { 2 }
        ::= { hwPriorityEntry 12 }
    
    -- 1.3.6.1.4.1.2011.5.2.4.1.13
    hwPriorityCosValue OBJECT-TYPE
        SYNTAX Integer32 (0..7 | 255)
        MAX-ACCESS read-create
        STATUS current
        DESCRIPTION
            "Describes the specified 802.1p priority when configuring the 802.1p priority 
             for the packets that match the ACL rule for priority marking.
             Range: 0-7, 255
             The larger the value is, the higher the priority is. 
             In the query operation, if this parameter is not used, 
             the obtained value is 255, which indicates invalidity. 
             Meanings: 
             best-effort:        Best-effort priority (0) 
             background:         Background priority (1) 
             spare:              Spare priority (2). 
             excellent-effort:   Excellent-effort priority (3) 
             controlled-load:    Controlled-load priority (4) 
             video:              Video priority (5) 
             voice:              Voice priority (6) 
             network-management: Network-management priority (7)
            "
        DEFVAL { 255 }
        ::= { hwPriorityEntry 13 }
    
    -- 1.3.6.1.4.1.2011.5.2.4.1.14
    hwPriorityCosFromIpPre OBJECT-TYPE
        SYNTAX TruthValue
        MAX-ACCESS read-create
        STATUS current
        DESCRIPTION
            "Indicates whether to set the IP priority the same as the 802.1p priority, 
             that is, copy the IP priority.      
             Options:
             1. true(1)  -copy 
             2. false(2) -not copy 
             If this leaf is not specified, the default value is false(2). 
            "
        DEFVAL { 2 }
        ::= { hwPriorityEntry 14 }
    
    -- 1.3.6.1.4.1.2011.5.2.4.1.15
    hwPriorityLocalPre OBJECT-TYPE
        SYNTAX Integer32 (0..7 | 255)
        MAX-ACCESS read-create
        STATUS current
        DESCRIPTION
            "Describes the specified local priority when configuring the local 
             priority for the packets that match the ACL rule for priority marking.
             Range: 0-7, 255
             The larger the value is, the higher the priority is. 
             In the query operation, if this parameter is not used, 
             the obtained value is 255, which indicates invalidity. 
            "
        DEFVAL { 255 }
        ::= { hwPriorityEntry 15 }   

    -- 1.3.6.1.4.1.2011.5.2.4.1.16
    hwPriorityRuntime OBJECT-TYPE
        SYNTAX TruthValue
        MAX-ACCESS read-only
        STATUS current
        DESCRIPTION
            "Describes whether the ACL rule for priority marking 
             delivered to a specified port or a specified slot takes effect.
             This leaf is read-only.
             Options:   
             1. true(1)  -if the ACL rule is associated with a time range parameter 
                          and the current time is within the defined time range, the value is true(1), 
                          which indicates validity.
             2. false(2) -if the current time is not within the defined time range, the value is false(2), 
                          which indicates invalidity.    
             If the ACL rule is not associated with a time range parameter, the value is always true(1). 
            "
        ::= { hwPriorityEntry 16 }
    
    -- 1.3.6.1.4.1.2011.5.2.4.1.17
    hwPriorityRowStatus OBJECT-TYPE
        SYNTAX RowStatus
        MAX-ACCESS read-create
        STATUS current
        DESCRIPTION
            "Indicates the row status. It is used for delivering an ACL rule for 
             priority marking to a specified port or a specified slot and deleting the delivered ACL rule on a port or a slot.
             Options:     
             1. active(1)      -when this leaf is queried, the value is fixed to active(1)
             2. createAndGo(4) -deliver an ACL rule for priority marking to a specified port or a specified slot
             3. destroy(6)     -delete an ACL rule for priority marking delivered to a port or a specified slot
             When an ACL rule is delivered to a specified port or a specified slot, make sure that at 
             least one of the following groups is configured. 
             (1)hwPriorityUserAclNum and hwPriorityUserAclSubitem
             (2)hwPriorityIpAclNum and hwPriorityIpAclSubitem
             (3)hwPriorityLinkAclNum and hwPriorityLinkAclSubitem
             In addition to independent configuration of each group, 
             the combined configuration of group (2) and (3) is permitted. 
             The combined configuration of group (1) and (2) or combining group (1) and (3) is prohibited. 
             In addition, hwPriorityRowStatus must be set to createAndGo(4). 
             To delete the ACL rule for priority marking delivered to a port or a slot, set hwPriorityRowStatus to destroy(6). 
             When this leaf is queried, the value is fixed to active(1). 
            "
        ::= { hwPriorityEntry 17 }

    -- 1.3.6.1.4.1.2011.5.2.4.1.18
    hwPriorityIpv6AclNum OBJECT-TYPE
        SYNTAX Integer32 (0 | 2000..3999)
        MAX-ACCESS read-create
        STATUS current
        DESCRIPTION
            "Indicates the basic or advanced ACLv6 rule group that is used when a basic or 
             advanced ACLv6 rule for priority marking is delivered to a specified port or a specified slot.
             Range: 0, 2000-3999
             Make sure that the basic or advanced ACLv6 rule group is already created. 
             In the query operation, if the basic or advanced ACLv6 rule group is not used, 
             the value obtained is 0. 
            "
        ::= { hwPriorityEntry 18 }
    
    -- 1.3.6.1.4.1.2011.5.2.4.1.19
    hwPriorityIpv6AclSubitem OBJECT-TYPE
        SYNTAX Unsigned32 (0..4294967295)
        MAX-ACCESS read-create
        STATUS current
        DESCRIPTION
            "Indicates the basic or advanced ACLv6 rule that is used when a basic or advanced 
             ACLv6 rule for priority marking is delivered to a specified port or a specified slot.
             This leaf must be used together with hwPriorityIpv6AclNum, 
             uniquely identifying an ACLv6 rule.
             Range: 0-4294967295
             Make sure that the basic or advanced ACLv6 rule group is already created. 
             In the query operation, if the basic or advanced ACLv6 rule is not used, 
             the value obtained is 4294967295. 
            "
        ::= { hwPriorityEntry 19 }               
    
    -- 1.3.6.1.4.1.2011.5.2.5
    hwRedirectTable OBJECT-TYPE
        SYNTAX SEQUENCE OF HwRedirectEntry
        MAX-ACCESS not-accessible
        STATUS current
        DESCRIPTION 
            "Describes the redirection for packets that match the ACL rule from a port to another port. 
             The indexes of this table are hwRedirectAclIndex, hwRedirectIfIndex and hwRedirectDirection.
             Make sure that the ACL rule in hwRedirectTable is already created in hwAclBasicRuleTable, 
             hwAclAdvancedRuleTable, hwAclLinkTable, or hwAclUserTable. 
            "
        ::= { hwLswQosAclMib 5 }
    
    -- 1.3.6.1.4.1.2011.5.2.5.1
    hwRedirectEntry OBJECT-TYPE
        SYNTAX HwRedirectEntry
        MAX-ACCESS not-accessible
        STATUS current
        DESCRIPTION
            "Describes the redirection for packets that match the ACL rule from a port to another port. 
             The indexes of this entry are hwRedirectAclIndex, hwRedirectIfIndex and hwRedirectDirection.
             Make sure that the ACL rule in hwRedirectTable is already created in hwAclBasicRuleTable, 
             hwAclAdvancedRuleTable, hwAclLinkTable, or hwAclUserTable. 
            "
        INDEX { hwRedirectAclIndex, hwRedirectIfIndex, hwRedirectDirection }
        ::= { hwRedirectTable 1 }
    
    HwRedirectEntry ::=
        SEQUENCE { 
          hwRedirectAclIndex
            Integer32,
          hwRedirectIfIndex
            Unsigned32,
          hwRedirectDirection
            INTEGER,
          hwRedirectUserAclNum
            Integer32,
          hwRedirectUserAclSubitem
            Unsigned32,
          hwRedirectIpAclNum
            Integer32,
          hwRedirectIpAclSubitem
            Unsigned32,
          hwRedirectLinkAclNum
            Integer32,
          hwRedirectLinkAclSubitem
            Unsigned32,
          hwRedirectToCpu
            TruthValue,
          hwRedirectToIfIndex
            Unsigned32,
          hwRedirectRuntime
            TruthValue,
          hwRedirectRowStatus
            RowStatus,
          hwRedirectIpv6AclNum
            Integer32,
          hwRedirectIpv6AclSubitem
            Unsigned32                 
         }

    -- 1.3.6.1.4.1.2011.5.2.5.1.1
    hwRedirectAclIndex OBJECT-TYPE
        SYNTAX Integer32 (0..2999)
        MAX-ACCESS read-only
        STATUS current
        DESCRIPTION
            "The delivery entry index of an ACL rule for redirecting packets is a delivery 
             record entry index used by software, which is meaningless to users. 
             The index is used in hwRedirectTable to search the delivery entries fast. 
             Range: 0-2999
             In the create operation, the device automatically allocates a delivery entry index. 
             There is a suggestion that users can always input 0.
            "
        ::= { hwRedirectEntry 1 }
    
    -- 1.3.6.1.4.1.2011.5.2.5.1.2
    hwRedirectIfIndex OBJECT-TYPE
        SYNTAX Unsigned32 (0|1..4294967295)
        MAX-ACCESS read-only
        STATUS current
        DESCRIPTION
            "Indicates the port index when the device delivers an ACL rule for redirecting 
             packets to a specified port. The index uniquely identifies a port. 
             The value and algorithm are the same as those of ifIndex. 
             Range: 0-4294967295
            "
        ::= { hwRedirectEntry 2 }
    
    -- 1.3.6.1.4.1.2011.5.2.5.1.3
    hwRedirectDirection OBJECT-TYPE
        SYNTAX INTEGER
          {
            invalid(0),
            inbound(1),
            outbound(2)
          }
        MAX-ACCESS read-only
        STATUS current
        DESCRIPTION
            "Indicates the direction where an ACL rule for redirecting packets takes 
             effect when the device delivers an ACL rule to a specified port.
             Options:
             1. invalid(0)  -indicates an invalid parameter. 
             2. inbound(1)  -indicates the inbound direction of a port. 
                             It is used for redirecting the packets received on a port.    
             3. outbound(2) -indicates the outbound direction of a port. 
                             It is used for redirecting the packets transmitted on a port.
            "
        ::= { hwRedirectEntry 3 }    
      
    -- 1.3.6.1.4.1.2011.5.2.5.1.4
    hwRedirectUserAclNum OBJECT-TYPE
        SYNTAX Integer32 (0 | 5000..5999)
        MAX-ACCESS read-create
        STATUS current
        DESCRIPTION
            "Describes the user-defined ACL rule group that is used when a user-defined 
             ACL rule for redirecting packets is delivered to a specified port.
             Range: 0, 5000-5999
             Make sure that the user-defined ACL rule group is already created. 
             In the query operation, if the user-defined ACL rule group is not used, 
             the value obtained is 0. 
            "
        ::= { hwRedirectEntry 4 }
    
    -- 1.3.6.1.4.1.2011.5.2.5.1.5
    hwRedirectUserAclSubitem OBJECT-TYPE
        SYNTAX Unsigned32 (0|1..4294967295)
        MAX-ACCESS read-create
        STATUS current
        DESCRIPTION
            "Describes the user-defined ACL rule that is used when a user-defined 
             ACL rule for redirecting packets is delivered to a specified port.
             This leaf must be used together with hwRedirectUserAclNum, 
             uniquely identifying an ACL rule.
             Range: 0-4294967295
             Make sure that the user-defined ACL rule is already created. 
             In the query operation, if the user-defined ACL rule is not used, 
             the value obtained is 4294967295. 
            "
        ::= { hwRedirectEntry 5 }
    
    -- 1.3.6.1.4.1.2011.5.2.5.1.6
    hwRedirectIpAclNum OBJECT-TYPE
        SYNTAX Integer32 (0 | 2000..3999)
        MAX-ACCESS read-create
        STATUS current
        DESCRIPTION
            "Describes the basic or advanced ACL rule group that is used when a basic 
             or advanced ACL rule for redirecting packets is delivered to a specified port.
             Range: 0, 2000-3999
             Make sure that the basic or advanced ACL rule group is already created. 
             In the query operation, if the basic or advanced ACL rule group is not used, 
             the value obtained is 0. 
            "
        ::= { hwRedirectEntry 6 }
    
    -- 1.3.6.1.4.1.2011.5.2.5.1.7
    hwRedirectIpAclSubitem OBJECT-TYPE
        SYNTAX Unsigned32 (0|1..4294967295)
        MAX-ACCESS read-create
        STATUS current
        DESCRIPTION
            "Describes the basic or advanced ACL rule that is used when a basic or advanced 
             ACL rule for redirecting packets is delivered to a specified port.
             This leaf must be used together with hwRedirectIpAclNum, 
             uniquely identifying an ACL rule.
             Range: 0-4294967295
             Make sure that the basic or advanced ACL rule group is already created. 
             In the query operation, if the basic or advanced ACL rule is not used, 
             the value obtained is 4294967295. 
            "
        ::= { hwRedirectEntry 7 }    

    -- 1.3.6.1.4.1.2011.5.2.5.1.8
    hwRedirectLinkAclNum OBJECT-TYPE
        SYNTAX Integer32 (0 | 4000..4999)
        MAX-ACCESS read-create
        STATUS current
        DESCRIPTION
            "Describes the L2 ACL rule group that is used when an L2 ACL rule 
             for redirecting packets is delivered to a specified port.
             Range: 0, 4000-4999
             Make sure that the L2 ACL rule group is already created. 
             In the query operation, if the L2 ACL rule group is not used, 
             the value obtained is 0. 
            "
        ::= { hwRedirectEntry 8 }
    
    -- 1.3.6.1.4.1.2011.5.2.5.1.9
    hwRedirectLinkAclSubitem OBJECT-TYPE
        SYNTAX Unsigned32 (0..4294967295)
        MAX-ACCESS read-create
        STATUS current
        DESCRIPTION
            "Describes the L2 ACL rule that is used when an L2 ACL rule for 
             redirecting packets is delivered to a specified port.
             This leaf must be used together with hwRedirectLinkAclNum, 
             uniquely identifying an ACL rule.
             Range: 0-4294967295
             Make sure that the L2 ACL rule is already created. 
             In the query operation, if the L2 ACL rule is not used, 
             the value obtained is 4294967295. 
            "
        ::= { hwRedirectEntry 9 }
    
    -- 1.3.6.1.4.1.2011.5.2.5.1.10
    hwRedirectToCpu OBJECT-TYPE
        SYNTAX TruthValue
        MAX-ACCESS read-create
        STATUS current
        DESCRIPTION
            "Indicates whether to redirect packets to the CPU. 
             After the packets are redirected to the CPU, they cannot be forwarded. 
             Options:
             1. true(1)  -indicates to redirect packets to the CPU      
             2. false(2) -indicates to redirect packets to a specified port 
             If you want to redirect packets to a destination port, 
             you can set hwRedirectToIfIndex rather than hwRedirectToCpu. 
             If hwRedirectCpu is set to true(1) and hwRedirectToIfIndex is entered, 
             the packets will be redirected to the destination port specified in hwRedirectToIfIndex. 
            "
        DEFVAL { 2 }
        ::= { hwRedirectEntry 10 }
    
    -- 1.3.6.1.4.1.2011.5.2.5.1.11
    hwRedirectToIfIndex OBJECT-TYPE
        SYNTAX Unsigned32 (0..4294967295)
        MAX-ACCESS read-create
        STATUS current
        DESCRIPTION
            "Indicates the index for redirecting the packet to the destination port. 
             The value and algorithm are the same as those of ifIndex. 
             Range: 0-4294967295
            "
        ::= { hwRedirectEntry 11 }
    
    -- 1.3.6.1.4.1.2011.5.2.5.1.12
    hwRedirectRuntime OBJECT-TYPE
        SYNTAX TruthValue
        MAX-ACCESS read-only
        STATUS current
        DESCRIPTION
            "Describes whether the ACL rule for redirecting packets delivered 
             to a specified port takes effect. This leaf is read-only.
             Options:   
             1. true(1)  -if the ACL rule is associated with a time range parameter 
                          and the current time is within the defined time range, the value is true(1), 
                          which indicates validity.
             2. false(2) -if the current time is not within the defined time range, the value is false(2), 
                          which indicates invalidity.            
             If the ACL rule is not associated with a time range parameter, the value is always true(1). 
            "
        ::= { hwRedirectEntry 12 }
    
    -- 1.3.6.1.4.1.2011.5.2.5.1.13
    hwRedirectRowStatus OBJECT-TYPE
        SYNTAX RowStatus
        MAX-ACCESS read-create
        STATUS current
        DESCRIPTION
            "Indicates the row status. It is used for delivering an ACL rule for redirecting 
             packets to a specified port and deleting the delivered ACL rule on a port.
             Options:   
             1. active(1)      -when this leaf is queried, the value is fixed to active(1).
             2. createAndGo(4) -deliver an ACL rule for redirecting packets to a specified port
             3. destroy(6)     -delete an ACL rule delivered to a port
             When an ACL rule is delivered to a specified port, make sure that at least one 
             of the following group is configured. 
             (1)hwRedirectUserAclNum and hwRedirectUserAclSubitem
             (2)hwRedirectIpAclNum and hwRedirectIpAclSubitem
             (3)hwRedirectLinkAclNum and hwRedirectLinkAclSubitem
             In addition to independent configuration of each group, the combined configuration 
             of group (2) and (3) is permitted. The combined configuration of group (1) and (2) 
             or combining group (1) and (3) is prohibited. 
             In addition, hwRedirectRowStatus must be set to createAndGo(4).
             To delete the ACL rule delivered to a port, set hwRedirectRowStatus to destroy(6). 
             When this leaf is queried, the value is fixed to active(1).
            "
        ::= { hwRedirectEntry 13 }
    -- 1.3.6.1.4.1.2011.5.2.5.1.14
    hwRedirectIpv6AclNum OBJECT-TYPE
        SYNTAX Integer32 (0 | 2000..3999)
        MAX-ACCESS read-create
        STATUS current
        DESCRIPTION
            "Indicates the basic or advanced ACLv6 rule group that is used when a basic 
             or advanced ACLv6 rule for redirecting packets is delivered to a specified port.
             Range: 0, 2000-3999
             Make sure that the basic or advanced ACLv6 rule group is already created. 
             In the query operation, if the basic or advanced ACLv6 rule group is not used, 
             the value obtained is 0. 
            "
        ::= { hwRedirectEntry 14 }

    -- 1.3.6.1.4.1.2011.5.2.5.1.15
    hwRedirectIpv6AclSubitem OBJECT-TYPE
        SYNTAX Unsigned32 (0..4294967295)
        MAX-ACCESS read-create
        STATUS current
        DESCRIPTION
            "Indicates the basic or advanced ACLv6 rule that is used when a basic or advanced 
             ACLv6 rule for redirecting packets is delivered to a specified port.
             This leaf must be used together with hwRedirectIpv6AclNum, 
             uniquely identifying an ACLv6 rule.
             Range: 0-4294967295
             Make sure that the basic or advanced ACLv6 rule group is already created. 
             In the query operation, if the basic or advanced ACLv6 rule is not used, 
             the value obtained is 4294967295. 
            "
        ::= { hwRedirectEntry 15 }            
    
    -- 1.3.6.1.4.1.2011.5.2.6
    hwStatisticTable OBJECT-TYPE
        SYNTAX SEQUENCE OF HwStatisticEntry
        MAX-ACCESS not-accessible
        STATUS current
        DESCRIPTION
            "Describes the statistics of packets that match the ACL rule on a specified port. 
             The indexes of this table are hwStatisticAclIndex, hwStatisticIfIndex, and hwStatisticDirection.
             Make sure that the ACL rule in hwStatisticTable is already created in hwAclBasicRuleTable, 
             hwAclAdvancedRuleTable, hwAclLinkTable, or hwAclUserTable. 
            "
        ::= { hwLswQosAclMib 6 }
    
    -- 1.3.6.1.4.1.2011.5.2.6.1
    hwStatisticEntry OBJECT-TYPE
        SYNTAX HwStatisticEntry
        MAX-ACCESS not-accessible
        STATUS current
        DESCRIPTION
            "Describes the statistics of packets that match the ACL rule on a specified port. 
             The indexes of this entry are hwStatisticAclIndex, hwStatisticIfIndex, and hwStatisticDirection.
             Make sure that the ACL rule in hwStatisticTable is already created in hwAclBasicRuleTable, 
             hwAclAdvancedRuleTable, hwAclLinkTable, or hwAclUserTable. 
            "
        INDEX { hwStatisticAclIndex, hwStatisticIfIndex, hwStatisticDirection }
        ::= { hwStatisticTable 1 }
    
    HwStatisticEntry ::=
        SEQUENCE { 
          hwStatisticAclIndex
            Integer32,
          hwStatisticIfIndex
            Unsigned32,
          hwStatisticDirection
            INTEGER,
          hwStatisticUserAclNum
            Integer32,
          hwStatisticUserAclSubitem
            Unsigned32,
          hwStatisticIpAclNum
            Integer32,
          hwStatisticIpAclSubitem
            Unsigned32,
          hwStatisticLinkAclNum
            Integer32,
          hwStatisticLinkAclSubitem
            Unsigned32,
          hwStatisticRuntime
            TruthValue,
          hwStatisticPacketCount
            Counter64,
          hwStatisticCountClear
            INTEGER,
          hwStatisticRowStatus
            RowStatus,
          hwStatisticUnit
            INTEGER,
          hwStatisticByteCount
            Counter64,
          hwStatisticIpv6AclNum
            Integer32,
          hwStatisticIpv6AclSubitem
            Unsigned32               
         }

    -- 1.3.6.1.4.1.2011.5.2.6.1.1
    hwStatisticAclIndex OBJECT-TYPE
        SYNTAX Integer32 (0..2999)
        MAX-ACCESS read-only
        STATUS current
        DESCRIPTION
            "Indicates the delivery entry index of an ACL rule for traffic measurement. 
             It is a delivery record entry index used by software, which is meaningless to users. 
             The index is used in hwStatisticTable to search the delivery entries fast. 
             Range: 0-2999
             In the create operation, the device automatically allocates a delivery entry index. 
             There is a suggestion that users can always input 0.
            "
        ::= { hwStatisticEntry 1 }
    
    -- 1.3.6.1.4.1.2011.5.2.6.1.2
    hwStatisticIfIndex OBJECT-TYPE
        SYNTAX Unsigned32 (0|1..4294967295)
        MAX-ACCESS read-only
        STATUS current
        DESCRIPTION
            "Indicates the port index when the device delivers an ACL rule for traffic measurement 
             to a specified port. The index uniquely identifies a port. 
             The value and algorithm are the same as those of ifIndex. 
             Range: 0-4294967295
            "
        ::= { hwStatisticEntry 2 }
    
    -- 1.3.6.1.4.1.2011.5.2.6.1.3
    hwStatisticDirection OBJECT-TYPE
        SYNTAX INTEGER
          {
            invalid(0),
            inbound(1),
            outbound(2)
          }
        MAX-ACCESS read-only
        STATUS current
        DESCRIPTION
            "Indicates the direction where an ACL rule for traffic measurement takes effect 
             when the device delivers an ACL rule to a specified port.    
             Options:
             1. invalid(0)   -indicates an invalid parameter. 
             2. inbound(1)   -indicates the inbound direction of a port. 
                              It is used for measuring the traffic measurement received on a specified port. 
             3. outbound(2)  -indicates the outbound direction of a port. 
                              It is used for measuring the traffic measurement transmitted on a specified port.
            "
        ::= { hwStatisticEntry 3 }
    
    -- 1.3.6.1.4.1.2011.5.2.6.1.4
    hwStatisticUserAclNum OBJECT-TYPE
        SYNTAX Integer32 (0 | 5000..5999)
        MAX-ACCESS read-create
        STATUS current
        DESCRIPTION
            "Describes the user-defined ACL rule group that is used when a user-defined ACL rule 
             for traffic measurement is delivered to a specified port.
             Range: 0, 5000-5999
             Make sure that the user-defined ACL rule group is already created. 
             In the query operation, if the user-defined ACL rule group is not used, 
             the value obtained is 0. 
            "
        ::= { hwStatisticEntry 4 }
    
    -- 1.3.6.1.4.1.2011.5.2.6.1.5
    hwStatisticUserAclSubitem OBJECT-TYPE
        SYNTAX Unsigned32 (0|1..4294967295)
        MAX-ACCESS read-create
        STATUS current
        DESCRIPTION
            "Describes the user-defined ACL rule that is used when a user-defined ACL rule 
             for traffic measurement is delivered to a specified port. 
             This leaf must be used together with hwStatisticUserAclNum, 
             uniquely identifying an ACL rule.
             Range: 0-4294967295
             Make sure that the user-defined ACL rule is already created. 
             In the query operation, if the user-defined ACL rule is not used, 
             the value obtained is 4294967295. 
            "
        ::= { hwStatisticEntry 5 }
    
    -- 1.3.6.1.4.1.2011.5.2.6.1.6
    hwStatisticIpAclNum OBJECT-TYPE
        SYNTAX Integer32 (0 | 2000..3999)
        MAX-ACCESS read-create
        STATUS current
        DESCRIPTION
            "Describes the basic or advanced ACL rule group that is used when a basic 
             or advanced ACL rule for traffic measurement is delivered to a specified port. 
             Range: 0, 2000-3999
             Make sure that the basic or advanced ACL rule group is already created. 
             In the query operation, if the basic or advanced ACL rule group is not used, 
             the value obtained is 0. 
            "
        ::= { hwStatisticEntry 6 }
    
    -- 1.3.6.1.4.1.2011.5.2.6.1.7
    hwStatisticIpAclSubitem OBJECT-TYPE
        SYNTAX Unsigned32 (0|1..4294967295)
        MAX-ACCESS read-create
        STATUS current
        DESCRIPTION
            "Describes the basic or advanced ACL rule that is used when a basic or advanced 
             ACL rule for traffic measurement is delivered to a specified port. 
             This leaf must be used together with hwStatisticIpAclNum, 
             uniquely identifying an ACL rule.
             Range: 0-4294967295
             Make sure that the basic or advanced ACL rule is already created. 
             In the query operation, if the basic or advanced ACL rule is not used, 
             the value obtained is 4294967295. 
            "
        ::= { hwStatisticEntry 7 }
    
    -- 1.3.6.1.4.1.2011.5.2.6.1.8
    hwStatisticLinkAclNum OBJECT-TYPE
        SYNTAX Integer32 (0 | 4000..4999)
        MAX-ACCESS read-create
        STATUS current
        DESCRIPTION
            "Describes the L2 ACL rule group that is used when an L2 ACL rule for traffic 
             measurement is delivered to a specified port.
             Range: 0, 4000-4999
             Make sure that the L2 ACL rule group is already created. 
             In the query operation, if the L2 ACL rule group is not used, the value obtained is 0. 
            "
        ::= { hwStatisticEntry 8 }
    
    -- 1.3.6.1.4.1.2011.5.2.6.1.9
    hwStatisticLinkAclSubitem OBJECT-TYPE
        SYNTAX Unsigned32 (0|1..4294967295)
        MAX-ACCESS read-create
        STATUS current
        DESCRIPTION
            "Describes the L2 ACL rule that is used when an L2 ACL rule for traffic measurement 
             is delivered to a specified port. This leaf must be used together with hwStatisticLinkAclNum, 
             uniquely identifying an ACL rule.
             Range: 0-4294967295
             Make sure that the L2 ACL rule is already created. 
             In the query operation, if the L2 ACL rule is not used, the value obtained is 4294967295.
            "
        ::= { hwStatisticEntry 9 }
    
    -- 1.3.6.1.4.1.2011.5.2.6.1.10
    hwStatisticRuntime OBJECT-TYPE
        SYNTAX TruthValue
        MAX-ACCESS read-only
        STATUS current
        DESCRIPTION
            "Describes whether the ACL rule for traffic measurement delivered to a specified port takes effect.
             This leaf is read-only.
             Options:   
             1. true(1)  -if the ACL rule is associated with a time range parameter 
                          and the current time is within the defined time range, the value is true(1), 
                          which indicates validity.
             2. false(2) -if the current time is not within the defined time range, the value is false(2), 
                          which indicates invalidity.    
             If the ACL rule is not associated with a time range parameter, the value is always true(1). 
            "
        ::= { hwStatisticEntry 10 }
    
    -- 1.3.6.1.4.1.2011.5.2.6.1.11
    hwStatisticPacketCount OBJECT-TYPE
        SYNTAX Counter64
        MAX-ACCESS read-only
        STATUS current
        DESCRIPTION
            "Describes the statistics of packets that matches an ACL rule on a specified port. "
        ::= { hwStatisticEntry 11 }
    
    -- 1.3.6.1.4.1.2011.5.2.6.1.12
    hwStatisticCountClear OBJECT-TYPE
        SYNTAX INTEGER
          {
          cleared(1),
          nouse(2)
          }
        MAX-ACCESS read-write
        STATUS current
        DESCRIPTION
            "Used for deleting the statistics of packets that matches an ACL rule on a specified port. 
             To clear hwStatisticPacketCount, you can set this leaf to cleared(1). 
             In the query operation, this leaf is fixed to nouse(2). 
             Options:
             1. cleared(1) -delete the statistics of packets that matches an ACL rule on a specified port
             2. nouse(2)   -in the query operation, this leaf is fixed to nouse(2). 
            "
        ::= { hwStatisticEntry 12 }
    
    -- 1.3.6.1.4.1.2011.5.2.6.1.13
    hwStatisticRowStatus OBJECT-TYPE
        SYNTAX RowStatus
        MAX-ACCESS read-create
        STATUS current
        DESCRIPTION
            "Indicates the row status. It is used for delivering an ACL rule for traffic measurement 
             to a specified port and deleting the delivered ACL rule on a port.
             Options:    
             1. active(1)      -when this leaf is queried, the value is fixed to active(1).
             2. createAndGo(4) -deliver an ACL rule for traffic measurement to a specified port
             3. destroy(6)     -delete an ACL rule for traffic measurement delivered to a port
             When an ACL rule is delivered to a specified port, 
             make sure that at least one of the following group is configured. 
             (1)hwStatisticUserAclNum and hwStatisticUserAclSubitem
             (2)hwStatisticIpAclNum and hwStatisticIpAclSubitem
             (3)hwStatisticLinkAclNum and hwStatisticLinkAclSubitem
             In addition to independent configuration of each group, the combined configuration of group (2) 
             and (3) is permitted. The combined configuration of group (1) and (2) or combining group (1) and (3) 
             is prohibited. In addition, hwStatisticRowStatus must be set to createAndGo(4). 
             To delete the ACL rule for traffic measurement delivered to a port, set hwStatisticRowStatus to destroy(6). 
             To delete the statistics of hwStatisticPacketCount, you need not specify hwStatisticRowStatus. 
             When this leaf is queried, the value is fixed to active(1). 
            "
        ::= { hwStatisticEntry 13 }

    -- 1.3.6.1.4.1.2011.5.2.6.1.14
    hwStatisticUnit OBJECT-TYPE
        SYNTAX INTEGER
            {
                packet(1),
                byte(2)
            }
        MAX-ACCESS read-create
        STATUS current
        DESCRIPTION
            "Indicates Unit of a standard or extended ACLv6 for traffic measurement.
             Options: 
             1. packet(1) -measure by packet
             2. byte(2)   -measure by byte
             Default: packet(1)
             "
        ::= { hwStatisticEntry 14 }
        
    -- 1.3.6.1.4.1.2011.5.2.6.1.15
    hwStatisticByteCount OBJECT-TYPE
        SYNTAX Counter64
        MAX-ACCESS read-only
        STATUS current
        DESCRIPTION
            "Indicates the count of matched bytes."
        ::= { hwStatisticEntry 15 }

    -- 1.3.6.1.4.1.2011.5.2.6.1.16
    hwStatisticIpv6AclNum OBJECT-TYPE
        SYNTAX Integer32 (0 | 2000..3999)
        MAX-ACCESS read-create
        STATUS current
        DESCRIPTION
            "Indicates the basic or advanced ACLv6 rule group that is used when a basic 
             or advanced ACLv6 rule for traffic measurement is delivered to a specified port. 
             Range: 0, 2000-3999
             Make sure that the basic or advanced ACLv6 rule group is already created. 
             In the query operation, if the basic or advanced ACLv6 rule group is not used, 
             the value obtained is 0. 
            "
        ::= { hwStatisticEntry 16 }

    -- 1.3.6.1.4.1.2011.5.2.6.1.17
    hwStatisticIpv6AclSubitem OBJECT-TYPE
        SYNTAX Unsigned32 (0..4294967295)
        MAX-ACCESS read-create
        STATUS current
        DESCRIPTION
            "Indicates the basic or advanced ACLv6 rule that is used when a basic or advanced 
             ACLv6 rule for traffic measurement is delivered to a specified port. 
             This leaf must be used together with hwStatisticIpv6AclNum, 
             uniquely identifying an ACLv6 rule.
             Range: 0-4294967295
             Make sure that the basic or advanced ACLv6 rule is already created. 
             In the query operation, if the basic or advanced ACLv6 rule is not used, 
             the value obtained is 4294967295. 
            "
        ::= { hwStatisticEntry 17 }              
            
    -- 1.3.6.1.4.1.2011.5.2.7
    hwMirrorTable OBJECT-TYPE
        SYNTAX SEQUENCE OF HwMirrorEntry
        MAX-ACCESS not-accessible
        STATUS current
        DESCRIPTION
            "Describes the mirroring for packets that match the ACL rule from a port or a slot to another port. 
             The indexes of this table are hwMirrorAclIndex, hwMirrorIfIndex, and hwMirrorDirection.
             Make sure that the ACL rule in hwMirrorTable is already created in hwAclBasicRuleTable, 
             hwAclAdvancedRuleTable, hwAclLinkTable, or hwAclUserTable. 
            "       
        ::= { hwLswQosAclMib 7 }
    
    -- 1.3.6.1.4.1.2011.5.2.7.1
    hwMirrorEntry OBJECT-TYPE
        SYNTAX HwMirrorEntry
        MAX-ACCESS not-accessible
        STATUS current
        DESCRIPTION
            "Describes the mirroring for packets that match the ACL rule from a port or a slot to another port. 
             The indexes of this entry are hwMirrorAclIndex, hwMirrorIfIndex, and hwMirrorDirection.
             Make sure that the ACL rule in hwMirrorTable is already created in hwAclBasicRuleTable, 
             hwAclAdvancedRuleTable, hwAclLinkTable, or hwAclUserTable. 
            "
        INDEX { hwMirrorAclIndex, hwMirrorIfIndex, hwMirrorDirection }
        ::= { hwMirrorTable 1 }
    
    HwMirrorEntry ::=
        SEQUENCE { 
          hwMirrorAclIndex
            Integer32,
          hwMirrorIfIndex
            Unsigned32,
          hwMirrorDirection
            INTEGER,
          hwMirrorUserAclNum
            Integer32,
          hwMirrorUserAclSubitem
            Unsigned32,
          hwMirrorIpAclNum
            Integer32,
          hwMirrorIpAclSubitem
            Unsigned32,
          hwMirrorLinkAclNum
            Integer32,
          hwMirrorLinkAclSubitem
            Unsigned32,
          hwMirrorToIfIndex
            Unsigned32,
          hwMirrorRuntime
            TruthValue,
          hwMirrorRowStatus
            RowStatus,
          hwMirrorIpv6AclNum
            Integer32,
          hwMirrorIpv6AclSubitem
            Unsigned32                 
         }

    -- 1.3.6.1.4.1.2011.5.2.7.1.1
    hwMirrorAclIndex OBJECT-TYPE
        SYNTAX Integer32 (0..2999)
        MAX-ACCESS read-only
        STATUS current
        DESCRIPTION
            "Indicates the delivery entry index of an ACL rule for mirroring packets. 
             It is a delivery record entry index used by software, which is meaningless to users. 
             The index is used in hwMirrorTable to search the delivery entries fast. 
             Range: 0-2999
             In the create operation, the device automatically allocates a delivery entry index. 
             There is a suggestion that users can always input 0.
            "
        ::= { hwMirrorEntry 1 }
    
    -- 1.3.6.1.4.1.2011.5.2.7.1.2
    hwMirrorIfIndex OBJECT-TYPE
        SYNTAX Unsigned32 (0|1..4294967295)
        MAX-ACCESS read-only
        STATUS current
        DESCRIPTION
            "Indicates the port or the slot index when the device delivers an ACL rule for mirroring packets to a specified port. 
             The index uniquely identifies a port or a slot. The value and algorithm are the same as those of ifIndex.
             
             If the configuration based on a slot, the bits map is shown as follows:
             ---------------------------------------------------------------------------------------------------------------
             | 31-25 bits          | 24-19 bits         | 18-13 bits         | 12-6 bits            | 5-0 bits is reserved |
             | indicate iftype     | indicate frame ID  | indicate slot ID   | indicate port ID     |                      |               
             --------------------------------------------------------------------------------------------------------------- 
             | the value of iftype | frame ID           | slot ID            | the value of port ID | the reserved value   |
             | is always 0x68      |                    |                    | is always 0          | is always 0          |
             ---------------------------------------------------------------------------------------------------------------
             Range: 0-4294967295 
            "
        ::= { hwMirrorEntry 2 }
    
    -- 1.3.6.1.4.1.2011.5.2.7.1.3
    hwMirrorDirection OBJECT-TYPE
        SYNTAX INTEGER
          {
            invalid(0),
            inbound(1),
            outbound(2)
          }
        MAX-ACCESS read-only
        STATUS current
        DESCRIPTION
            "Indicates the direction where an ACL rule for mirroring packets takes 
             effect when the device delivers an ACL rule to a specified port or a specified slot.         
             Options:
             1. invalid(0)   -indicates an invalid parameter. 
             2. inbound(1)   -indicates the inbound direction of a port or slot. 
                              It is used for mirroring the packets that are received on a specified port or a specified slot.     
             3. outbound(2)  -indicates the outbound direction of a port or slot. 
                              It is used for mirroring the packets that are transmitted on a specified port or a specified slot.

            "
        ::= { hwMirrorEntry 3 }
    
    -- 1.3.6.1.4.1.2011.5.2.7.1.4
    hwMirrorUserAclNum OBJECT-TYPE
        SYNTAX Integer32 (0 | 5000..5999)
        MAX-ACCESS read-create
        STATUS current
        DESCRIPTION
            "Describes the user-defined ACL rule group that is used when a user-defined 
             ACL rule for mirroring packets is delivered to a specified port or a specified slot.
             Range: 0, 5000-5999
             Make sure that the user-defined ACL rule group is already created. 
             In the query operation, if the user-defined ACL rule group is not used, 
             the value obtained is 0. 
            "
        ::= { hwMirrorEntry 4 }
    
    -- 1.3.6.1.4.1.2011.5.2.7.1.5
    hwMirrorUserAclSubitem OBJECT-TYPE
        SYNTAX Unsigned32 (0|1..4294967295)
        MAX-ACCESS read-create
        STATUS current
        DESCRIPTION
            "Describes the user-defined ACL rule that is used when a user-defined 
             ACL rule for mirroring packets is delivered to a specified port or a specified slot. 
             This leaf must be used together with hwMirrorUserAclNum, 
             uniquely identifying an ACL rule.
             Range: 0-4294967295
             Make sure that the user-defined ACL rule is already created. 
             In the query operation, if the user-defined ACL rule is not used, 
             the value obtained is 4294967295. 
            "
        ::= { hwMirrorEntry 5 }
    
    -- 1.3.6.1.4.1.2011.5.2.7.1.6
    hwMirrorIpAclNum OBJECT-TYPE
        SYNTAX Integer32 (0 | 2000..3999)
        MAX-ACCESS read-create
        STATUS current
        DESCRIPTION
            "Describes the basic or advanced ACL rule group that is used when a basic 
             or advanced ACL rule for mirroring packets is delivered to a specified port or a specified slot.
             Range: 0, 2000-3999
             Make sure that the basic or advanced ACL rule group is already created. 
             In the query operation, if the basic or advanced ACL rule group is not used, 
             the value obtained is 0. 
            "
        ::= { hwMirrorEntry 6 }
    
    -- 1.3.6.1.4.1.2011.5.2.7.1.7
    hwMirrorIpAclSubitem OBJECT-TYPE
        SYNTAX Unsigned32 (0|1..4294967295)
        MAX-ACCESS read-create
        STATUS current
        DESCRIPTION
            "Describes the basic or advanced ACL rule that is used when a basic or advanced 
             ACL rule for mirroring packets is delivered to a specified port or a specified slot. 
             This leaf must be used together with hwMirrorIpAclNum, uniquely identifying an ACL rule.
             Range: 0-4294967295
             Make sure that the basic or advanced ACL rule is already created. 
             In the query operation, if the basic or advanced ACL rule is not used, 
             the value obtained is 4294967295.
            "
        ::= { hwMirrorEntry 7 }
    
    -- 1.3.6.1.4.1.2011.5.2.7.1.8
    hwMirrorLinkAclNum OBJECT-TYPE
        SYNTAX Integer32 (0 | 4000..4999)
        MAX-ACCESS read-create
        STATUS current
        DESCRIPTION
            "Describes the L2 ACL rule group that is used when an L2 ACL rule for 
             mirroring packets is delivered to a specified port or a specified slot.
             Range: 0, 4000-4999
             Make sure that the L2 ACL rule group is already created. 
             In the query operation, if the L2 ACL rule group is not used, the value obtained is 0. 
            "
        ::= { hwMirrorEntry 8 }
    
    -- 1.3.6.1.4.1.2011.5.2.7.1.9
    hwMirrorLinkAclSubitem OBJECT-TYPE
        SYNTAX Unsigned32 (0|1..4294967295)
        MAX-ACCESS read-create
        STATUS current
        DESCRIPTION
            "Describes the L2 ACL rule that is used when an L2 ACL rule for mirroring 
             packets is delivered to a specified port or a specified slot. 
             This leaf must be used together with hwMirrorLinkAclNum, 
             uniquely identifying an ACL rule.
             Range: 0-4294967295
             Make sure that the L2 ACL rule is already created. 
             In the query operation, if the L2 ACL rule is not used, 
             the value obtained is 4294967295. 
            "
        ::= { hwMirrorEntry 9 }
    
    --  1.3.6.1.4.1.2011.5.2.7.1.10   
    hwMirrorToIfIndex OBJECT-TYPE
        SYNTAX Unsigned32 (0|1..4294967295)
        MAX-ACCESS read-create
        STATUS current
        DESCRIPTION
            "Indicates the index for mirroring the packets to the destination port. 
             The value and algorithm are the same as those of ifIndex. 
             Range: 0-4294967295
            "
        ::= { hwMirrorEntry 10 }
    
    -- 1.3.6.1.4.1.2011.5.2.7.1.11
    hwMirrorRuntime OBJECT-TYPE
        SYNTAX TruthValue
        MAX-ACCESS read-only
        STATUS current
        DESCRIPTION
            "Describes whether the ACL rule for mirroring packets delivered to a specified port or a specified slot takes effect.
             This leaf is read-only.
             Options:   
             1. true(1)  --If the ACL rule is associated with a time range parameter 
                           and the current time is within the defined time range, the value is true(1), 
                           which indicates validity.
             2. false(2) --If the current time is not within the defined time range, the value is false(2), 
                           which indicates invalidity.    
             If the ACL rule is not associated with a time range parameter, the value is always true(1). 
            "
        ::= { hwMirrorEntry 11 }
    
    -- 1.3.6.1.4.1.2011.5.2.7.1.12
    hwMirrorRowStatus OBJECT-TYPE
        SYNTAX RowStatus
        MAX-ACCESS read-create
        STATUS current
        DESCRIPTION
            "Indicates the row status. It is used for delivering an ACL rule for mirroring packets to 
             a specified port or a specified slot and deleting the delivered ACL rule on a port or a slot. 
             Options:  
             1. active(1)      -when this leaf is queried, the value is fixed to active(1).
             2. createAndGo(4) -deliver an ACL rule for mirroring packets to a specified port or a specified slot
             3. destroy(6)     -delete an ACL rule delivered to a port or a slot
             When an ACL rule is delivered to a specified port or a specified slot, 
             make sure that at least one of the following group  is configured. 
             (1)hwMirrorUserAclNum and hwMirrorUserAclSubitem
             (2)hwMirrorIpAclNum and hwMirrorIpAclSubitem
             (3)hwMirrorLinkAclNum and hwMirrorLinkAclSubitem
             In addition to independent configuration of each group, 
             the combined configuration of group (2) and (3) is permitted. 
             The combined configuration of group (1) and (2) or combining group (1) and (3) is prohibited. 
             In addition, hwMirrorRowStatus must be set to createAndGo(4). 
             To delete the ACL rule delivered to a port or a slot, set hwMirrorRowStatus to destroy(6). 
             When this leaf is queried, the value is fixed to active(1). 
            "
        ::= { hwMirrorEntry 12 }

    -- 1.3.6.1.4.1.2011.5.2.7.1.13
    hwMirrorIpv6AclNum OBJECT-TYPE
        SYNTAX Integer32 (0 | 2000..3999)
        MAX-ACCESS read-create
        STATUS current
        DESCRIPTION
            "Indicates the basic or advanced ACLv6 rule group that is used when a basic 
             or advanced ACLv6 rule for mirroring packets is delivered to a specified port or a specified slot.
             Range: 0, 2000-3999
             Make sure that the basic or advanced ACLv6 rule group is already created. 
             In the query operation, if the basic or advanced ACLv6 rule group is not used, 
             the value obtained is 0. 
            "
        ::= { hwMirrorEntry 13 }

    -- 1.3.6.1.4.1.2011.5.2.7.1.14
    hwMirrorIpv6AclSubitem OBJECT-TYPE
        SYNTAX Unsigned32 (0..4294967295)
        MAX-ACCESS read-create
        STATUS current
        DESCRIPTION
            "Indicates the basic or advanced ACLv6 rule that is used when a basic or advanced 
             ACLv6 rule for mirroring packets is delivered to a specified port or a specified slot. 
             This leaf must be used together with hwMirrorIpv6AclNum, uniquely identifying an ACLv6 rule.
             Range: 0-4294967295
             Make sure that the basic or advanced ACLv6 rule is already created. 
             In the query operation, if the basic or advanced ACLv6 rule is not used, 
             the value obtained is 4294967295.
            "
        ::= { hwMirrorEntry 14 }   
                   
    -- 1.3.6.1.4.1.2011.5.2.9
    hwLineRateTable OBJECT-TYPE
        SYNTAX SEQUENCE OF HwLineRateEntry
        MAX-ACCESS not-accessible
        STATUS current
        DESCRIPTION
            "Describes the rate limitation on packets that match the ACL rule on a specified port. 
             The index of this table is hwLineRateIfIndex.
            "
        ::= { hwLswQosAclMib 9 }
    
    -- 1.3.6.1.4.1.2011.5.2.9.1
    hwLineRateEntry OBJECT-TYPE
        SYNTAX HwLineRateEntry
        MAX-ACCESS not-accessible
        STATUS current
        DESCRIPTION
            "Describes the rate limitation on packets that match the ACL rule on a specified port. 
             The index of this entry is hwLineRateIfIndex.
            "
        INDEX { hwLineRateIfIndex }
        ::= { hwLineRateTable 1 }
    
    HwLineRateEntry ::=
        SEQUENCE { 
          hwLineRateIfIndex
            Unsigned32,
          hwLineRateValue
            Integer32,
          hwLineRateRowStatus
            RowStatus,
          hwLineRateInboundValue
            Integer32       
         }

    -- 1.3.6.1.4.1.2011.5.2.9.1.1
    hwLineRateIfIndex OBJECT-TYPE
        SYNTAX Unsigned32 (0|1..4294967295)
        MAX-ACCESS read-only
        STATUS current
        DESCRIPTION
            "Indicates the index of the port on which rate limitation is configured. 
             The value and algorithm are the same as those of ifIndex.
             Range: 0-4294967295 
            "
        ::= { hwLineRateEntry 1 }
    
    -- 1.3.6.1.4.1.2011.5.2.9.1.2
    hwLineRateValue OBJECT-TYPE
        SYNTAX Integer32 (-1|64..10000000)
        MAX-ACCESS read-create
        STATUS current
        DESCRIPTION
            "Indicates the outbound rate limitation of a port. 
             Range: -1，64-10000000 (which must be an integer multiple of 64)
             Unit: Kbit/s. 
             when the value is set to -1 and the value of hwLineRateRowStatus is set to destroy(6), 
             it will disable the outbound limitation on a specified port.
             -1 can be used only in the case of disable the limitation.
            "
        ::= { hwLineRateEntry 2 }
    
    -- 1.3.6.1.4.1.2011.5.2.9.1.3
    hwLineRateRowStatus OBJECT-TYPE
        SYNTAX RowStatus
        MAX-ACCESS read-create
        STATUS current
        DESCRIPTION
            "Indicates the row status. It is used to configure, modify, 
             or delete an ACL rule for rate limitation on a specified port. 
             Options:   
             1. active(1)      -when this leaf is queried, the value is fixed to active(1).
             2. createAndGo(4) -deliver an ACL rule for rate limitation on a specified port
             3. destroy(6)     -delete an ACL rule for rate limitation on a specified port
             When configuring rate limitation on packets on a port, 
             enter the values of hwLineRateValue and hwLineRateInboundValue 
             and set hwLineRateRowStatus to createAndGo(4). 
             When modifying the rate limitation value existed on a port, 
             set hwLineRateValue or hwLineRateInboundValue rather than hwLineRateRowStatus. 
             To delete rate limitation on packets on a port, set hwLineRateRowStatus to destroy(6). 
             When this leaf is queried, the value is fixed to active(1). 
            "
        ::= { hwLineRateEntry 3 }
    
    -- 1.3.6.1.4.1.2011.5.2.9.1.4
    hwLineRateInboundValue OBJECT-TYPE
        SYNTAX Integer32 (-1|64..10000000)
        MAX-ACCESS read-create
        STATUS current
        DESCRIPTION
            "Indicates the inbound rate limitation of a port. 
             Range: -1, 64-10000000 (which must be an integer multiple of 64)
             Unit: Kbit/s. 
             when the value is set to -1 and the value of hwLineRateRowStatus is set to destroy(6), 
             it will disable the inbound limitation on a specified port.
             -1 can be used only in the case of disable the limitation.
            "
        ::= { hwLineRateEntry 4 }   
      
	hwMirrorEthHead OBJECT IDENTIFIER ::= { hwLswQosAclMib 11 }
	
	hwMirrorEthHeadDMAC OBJECT-TYPE
		SYNTAX MacAddress
		MAX-ACCESS read-write
		STATUS current
	        DESCRIPTION
	            "Describes the destination MAC address, which is contained in the Ethernet packet head, added into the mirrored packet. 
	             the value obtained is not the boradcast address, the multicast address, or all zero address.
	            "
		::= { hwMirrorEthHead 1 }
	
	hwMirrorEthHeadSMAC OBJECT-TYPE
		SYNTAX MacAddress
		MAX-ACCESS read-write
		STATUS current
	        DESCRIPTION
	            "Describes the source MAC address, which is contained in the Ethernet packet head, added into the mirrored packet. 
	             the value obtained is not the boradcast address, the multicast address, or all zero address.
	            "
		::= { hwMirrorEthHead 2 }
	
	hwMirrorEthHeadEthType OBJECT-TYPE
		SYNTAX Unsigned32 (0..65535)
		MAX-ACCESS read-write
		STATUS current
		DESCRIPTION
		    "Describes the ether type value, which is contained in the Ethernet packet head, added into the mirrored packet. 
		     Range: 0-65535
		     Default value: 0x8100
		    "
		::= { hwMirrorEthHead 3 }
	
	hwMirrorEthHeadVlanID OBJECT-TYPE
		SYNTAX Unsigned32 (1..4093)
		MAX-ACCESS read-write
		STATUS current
		DESCRIPTION
		    "Describes the vlan Id, which is contained in the Ethernet packet head, added into the mirrored packet. 
		     Range: 1-4093
		     Default value: 1		     
		    "
		::= { hwMirrorEthHead 4 }
	
	hwMirrorEthHeadProtocolDot1pPriority OBJECT-TYPE
		SYNTAX Integer32 (0..7)
		MAX-ACCESS read-write
		STATUS current
		DESCRIPTION
		    "Describes the priority of vlan, which is contained in the Ethernet packet head, added into the mirrored packet. 
		     Range: 0-7
		     Default value: 0
		    "
		::= { hwMirrorEthHead 5 }         
		
    -- 1.3.6.1.4.1.2011.5.2.12
    hwOntRateLimitTable OBJECT-TYPE
        SYNTAX SEQUENCE OF HwOntRateLimitEntry
        MAX-ACCESS not-accessible
        STATUS current
        DESCRIPTION
            "Indicates the ONT down stream traffic table. It is used to add, query, 
             modify or delete an ONT down stream traffic table.
             The indexes of this table are hwOntRateLimitIfIndex and hwOntRateLimitOntId.
            "
        ::= { hwLswQosAclMib 12 }  
        
     -- 1.3.6.1.4.1.2011.5.2.12.1
     hwOntRateLimitEntry OBJECT-TYPE
        SYNTAX HwOntRateLimitEntry
        MAX-ACCESS not-accessible
        STATUS current
        DESCRIPTION
            "Indicates the ONT down stream traffic table. It is used to add, query, 
             modify or delete an ONT down stream traffic table.
             The indexes of this entry are hwOntRateLimitIfIndex and hwOntRateLimitOntId.
            "
        INDEX { hwOntRateLimitIfIndex, hwOntRateLimitOntId }
        ::= { hwOntRateLimitTable 1 }
	
     HwOntRateLimitEntry ::=
        SEQUENCE { 
          hwOntRateLimitIfIndex
            Unsigned32,
          hwOntRateLimitOntId
            Integer32,
          hwOntRateLimitDSTrafficTableId
            Integer32,
          hwOntRateLimitRowStatus
            RowStatus
         }

     -- 1.3.6.1.4.1.2011.5.2.12.1.1
     hwOntRateLimitIfIndex OBJECT-TYPE
        SYNTAX Unsigned32 (0|1..4294967295)
        MAX-ACCESS not-accessible
        STATUS current
        DESCRIPTION
            "It is one of the table indexes. Specifies the index of a port for ONT traffic limitation. 
             It uniquely identifies a port. 
             The value and algorithm are the same as those of ifIndexes. 
            "
        ::= { hwOntRateLimitEntry 1 }

    -- 1.3.6.1.4.1.2011.5.2.12.1.2
    hwOntRateLimitOntId OBJECT-TYPE
        SYNTAX Integer32
        MAX-ACCESS not-accessible
        STATUS current
        DESCRIPTION
            "It is one of the table indexes. Indicates the ONT ID. 
            "
        ::= { hwOntRateLimitEntry 2 }
    
    -- 1.3.6.1.4.1.2011.5.2.12.1.3
    hwOntRateLimitDSTrafficTableId OBJECT-TYPE
        SYNTAX Integer32 (1..1024)
        MAX-ACCESS read-create
        STATUS current
        DESCRIPTION
            "Indicates the down stream traffic table ID.
            "
        ::= { hwOntRateLimitEntry 3 }
    
    -- 1.3.6.1.4.1.2011.5.2.12.1.4
    hwOntRateLimitRowStatus OBJECT-TYPE
        SYNTAX RowStatus
        MAX-ACCESS read-create
        STATUS current
        DESCRIPTION
            "Indicates the row status.
             Options:  
             1. active(1)      -when this leaf is queried, the value is fixed to active(1).
             2. createAndGo(4) -deliver a traffic table ID to an ONT
             3. destroy(6)     -delete an ONT traffic table 
            "
        ::= { hwOntRateLimitEntry 4 }
	
	-- 1.3.6.1.4.1.2011.5.2.17  
	   hwAclUserSideActionmode OBJECT-TYPE
       SYNTAX INTEGER
           {
           port(1),  
           slot(2),
           frame(3)
           }
       MAX-ACCESS read-write  
       STATUS current
       DESCRIPTION
           "Sets the action mode of user-side ACL of the system.
            Options: 
            1. port(1)  -indicating port-based action mode of user-side ACL  
            2. slot(2)  -indicating slot-based action mode of user-side ACL  
            3. frame(3) -indicating frame-based action mode of user-side ACL         
            Default: port(1)
           "  
       DEFVAL { port }    
       ::= { hwLswQosAclMib 17 }
       
    hwQosTraps OBJECT IDENTIFIER ::= { hwLswQosAclMib 10 }  
  
    hwQosCommonTraps OBJECT IDENTIFIER ::= { hwQosTraps 1 }   
    
    hwQosCommonTrapsPrefix OBJECT IDENTIFIER ::= { hwQosCommonTraps 0 }
  
    hwQosAlarmTraps OBJECT IDENTIFIER ::= { hwQosTraps 2 }      
  
    -- add rate limit acl
    hwAddRateLimitAclTrap NOTIFICATION-TYPE
        OBJECTS {
            hwRateLimitAclIndex,
            hwRateLimitIfIndex,
            hwRateLimitDirection
            }         
        STATUS current
        DESCRIPTION
            "The hwAddRateLimitAclTrap will be sent when the rate limit acl is added."        
        ::= { hwQosCommonTraps 0 1 }  
    
    -- delete rate limit acl
    hwDeleteRateLimitAclTrap NOTIFICATION-TYPE
        OBJECTS {
             hwRateLimitAclIndex,
             hwRateLimitIfIndex,
             hwRateLimitDirection
            }      
        STATUS current
        DESCRIPTION
            "The hwDeleteRateLimitAclTrap will be sent when the rate limit acl is deleted."        
        ::= { hwQosCommonTraps 0 2 }   
    
    -- add priority acl
    hwAddPriorityAclTrap NOTIFICATION-TYPE
        OBJECTS {
             hwPriorityAclIndex,
             hwPriorityIfIndex,
             hwPriorityDirection
            }
        STATUS current 
        DESCRIPTION
            "The hwAddPriorityAclTrap will be sent when the priority acl is added."        
        ::= { hwQosCommonTraps 0 3 }  
    
    -- delete priority acl
    hwDeletePriorityAclTrap NOTIFICATION-TYPE
        OBJECTS {
             hwPriorityAclIndex,
             hwPriorityIfIndex,
             hwPriorityDirection
            }
        STATUS current 
        DESCRIPTION
            "The hwDeletePriorityAclTrap will be sent when the priority acl is deleted."        
        ::= { hwQosCommonTraps 0 4 }  
    
    -- add redirection acl
    hwAddRedirectAclTrap NOTIFICATION-TYPE
        OBJECTS {
             hwRedirectAclIndex,
             hwRedirectIfIndex,
             hwRedirectDirection
            }
        STATUS current 
        DESCRIPTION
            "The hwAddRedirectAclTrap will be sent when the redirect acl is added."        
        ::= { hwQosCommonTraps 0 5 }  
    
    -- delete redirection acl
    hwDeleteRedirectAclTrap NOTIFICATION-TYPE
        OBJECTS {
             hwRedirectAclIndex,
             hwRedirectIfIndex,
             hwRedirectDirection
            } 
        STATUS current
        DESCRIPTION
            "The hwDeleteRedirectAclTrap will be sent when the redirect acl is deleted."        
        ::= { hwQosCommonTraps 0 6 }  
    
    -- add statistic acl
    hwAddStatisticAclTrap NOTIFICATION-TYPE
        OBJECTS {
             hwStatisticAclIndex,
             hwStatisticIfIndex,
             hwStatisticDirection
            }
        STATUS current 
        DESCRIPTION
            "The hwAddStatisticAclTrap will be sent when the statistic acl added."        
        ::= { hwQosCommonTraps 0 7 }  
    
    -- delete statistic acl
    hwDeleteStatisticAclTrap NOTIFICATION-TYPE
        OBJECTS {
             hwStatisticAclIndex,
             hwStatisticIfIndex,
             hwStatisticDirection
            }
        STATUS current 
        DESCRIPTION
            "The hwDeleteStatisticAclTrap will be sent when the statistic acl is deleted."        
        ::= { hwQosCommonTraps 0 8 }       
    
    -- add mirror acl
    hwAddMirrorAclTrap NOTIFICATION-TYPE
        OBJECTS {
             hwMirrorAclIndex,
             hwMirrorIfIndex,
             hwMirrorDirection
            }
        STATUS current 
        DESCRIPTION
            "The hwAddMirrorAclTrap will be sent when the mirror acl is added."        
        ::= { hwQosCommonTraps 0 9 }  
    
    -- delete mirror acl
    hwDeleteMirrorAclTrap NOTIFICATION-TYPE
        OBJECTS {
             hwMirrorAclIndex,
             hwMirrorIfIndex,
             hwMirrorDirection
            }
        STATUS current 
        DESCRIPTION
            "The hwDeleteMirrorAclTrap will be sent when the mirror acl is deleted."        
        ::= { hwQosCommonTraps 0 10 }

  END
