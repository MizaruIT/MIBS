PROXY-MIB DEFINITIONS ::= BEGIN
--
-- $Id: proxy-mib-00.txt,v 1.2 1998/10/20 19:50:16 glenn Exp $
--
IMPORTS
	experimental, Unsigned32, TimeTicks, Gauge32, Counter32,
	MODULE-IDENTITY, OBJECT-TYPE
		FROM SNMPv2-SMI

	DisplayString
		FROM SNMPv2-TC;

nsfnet OBJECT IDENTIFIER ::= { experimental 25 }

proxy MODULE-IDENTITY
    LAST-UPDATED "9809010000Z"
    ORGANIZATION "National Laboratory for Applied Network Research"
    CONTACT-INFO
	    "        Glenn Chisholm

	     Postal: National Centre for Atmospheric Research (NCAR)
		     Room 36, SCD
		     PO Box 3000
		     Boulder, Colorado 80307
		     US

		Tel: +1 303 497 1289
		Fax: +1 303 497 1818

	     E-mail: glenn@ircache.net"
    DESCRIPTION
		"Proxy MIB defined for the generic management of proxy
		devices. See http://www.ircache.net/Cache/cache-snmp/."

    REVISION	  "9808260000Z"
    DESCRIPTION
		"Inital revision."
-- Need to get a real number from IANA when stable.
    ::= { nsfnet 17 }

--
-- OID Assignments
--
	proxySystem	OBJECT IDENTIFIER ::= { proxy 1 }
	proxyConfig	OBJECT IDENTIFIER ::= { proxy 2 }
	proxyPerf	OBJECT IDENTIFIER ::= { proxy 3 }

--
-- The Proxy System group
--
	proxyMemUsage OBJECT-TYPE
		SYNTAX Unsigned32
		MAX-ACCESS read-only
		STATUS current
		DESCRIPTION
			"The memory in use by the proxy independant of the
			support processes on the system running the proxy"
	::= { proxySystem 1 }

	proxyStorage OBJECT-TYPE
		SYNTAX Unsigned32
		MAX-ACCESS read-only
		STATUS current
		DESCRIPTION
			"The quantity of storage in use by the proxy in KB.
			This value can be zero if there is no caching occuring."
	::= { proxySystem 2 }

	proxyCpuUsage OBJECT-TYPE
		SYNTAX Unsigned32
		MAX-ACCESS read-only
		STATUS current
		DESCRIPTION
			"The amount of CPU consumed over the life of the process
			in seconds."
	::= { proxySystem 3 }

	proxyUpTime OBJECT-TYPE
		SYNTAX TimeTicks
		MAX-ACCESS read-only
		STATUS current
		DESCRIPTION
			"The amount of time the proxy has been running, in TimeTicks."
	::= { proxySystem 4 }

--
-- The Proxy Config group
--
-- The use of Display String needs to be examined. It may not be the best option in
-- this situation.
--
	proxyAdmin OBJECT-TYPE
		SYNTAX DisplayString
		MAX-ACCESS read-only
		STATUS current
		DESCRIPTION
			"The contact responsible for the administration of the
			proxy. Usually a name and email address."
	::= { proxyConfig 1 }

	proxySoftware OBJECT-TYPE
		SYNTAX DisplayString
		MAX-ACCESS read-only
		STATUS current
		DESCRIPTION
			"Name of the proxy sofware."
	::= { proxyConfig 2 }

	proxyVersion OBJECT-TYPE
		SYNTAX DisplayString
		MAX-ACCESS read-only
		STATUS current
		DESCRIPTION
			"Version of the proxy software."
	::= { proxyConfig 3 }

--
-- The Proxy Performance group
--
	proxySysPerf		OBJECT IDENTIFIER ::= { proxyPerf 1 }
	proxyProtoPerf		OBJECT IDENTIFIER ::= { proxyPerf 2 }

--
-- The peformance of the system running the proxy
--

	proxyCpuLoad OBJECT-TYPE
		SYNTAX Gauge32
		MAX-ACCESS read-only
		STATUS current
		DESCRIPTION
			"The current percentage of the CPU being consumed
			by the proxy proccess at this time."
	::= { proxySysPerf 1 }

	proxyNumObjects OBJECT-TYPE
		SYNTAX Counter32
		MAX-ACCESS read-only
		STATUS current
		DESCRIPTION
			"The number of objects currently held by the proxy."
	::= { proxySysPerf 2 }

--
-- The current protocol statistics for the proxy
--

	proxyProtoClient	OBJECT IDENTIFIER ::= { proxyProtoPerf 1 }
	proxyProtoServer	OBJECT IDENTIFIER ::= { proxyProtoPerf 2 }

--
-- Protocol statistics for items delivered by the proxy
--

	proxyClientHttpRequests OBJECT-TYPE
		SYNTAX Counter32
		MAX-ACCESS read-only
		STATUS current
		DESCRIPTION
			"The number of HTTP requests recieved from clients."
	::= { proxyProtoClient 1 }

	proxyClientHttpHits OBJECT-TYPE
		SYNTAX Counter32
		MAX-ACCESS read-only
		STATUS current
		DESCRIPTION
			"The number of HTTP hits that the proxy clients have
			produced."
	::= { proxyProtoClient 2 }

	proxyClientHttpErrors OBJECT-TYPE
		SYNTAX Counter32
		MAX-ACCESS read-only
		STATUS current
		DESCRIPTION
			"The number of HTTP errors caused by client connections."
	::= { proxyProtoClient 3 }

	proxyClientHttpInKbs OBJECT-TYPE
		SYNTAX Counter32
		MAX-ACCESS read-only
		STATUS current
		DESCRIPTION
			"The number of kilobits recieved from the clients by the proxy."
	::= { proxyProtoClient 4 }

	proxyClientHttpOutKbs OBJECT-TYPE
		SYNTAX Counter32
		MAX-ACCESS read-only
		STATUS current
		DESCRIPTION
			"The number of kilobits delivered to clients from the proxy."
	::= { proxyProtoClient 5 }

--
-- Protocol statistics for items fetched by the proxy
--

	proxyServerHttpRequests OBJECT-TYPE
		SYNTAX Counter32
		MAX-ACCESS read-only
		STATUS current
		DESCRIPTION
			"The number of HTTP requests that the proxy has issued."
	::= { proxyProtoServer 1 }

	proxyServerHttpErrors OBJECT-TYPE
		SYNTAX Counter32
		MAX-ACCESS read-only
		STATUS current
		DESCRIPTION
			"The number of HTTP errors while fetching objects."

	::= { proxyProtoServer 2 }

	proxyServerHttpInKbs OBJECT-TYPE
		SYNTAX Counter32
		MAX-ACCESS read-only
		STATUS current
		DESCRIPTION
			"The number of Kbs recieved by the proxy from remote
			servers."
	::= { proxyProtoServer 3 }

	proxyServerHttpOutKbs OBJECT-TYPE
		SYNTAX Counter32
		MAX-ACCESS read-only
		STATUS current
		DESCRIPTION
			"The number of kbs transmitted by the proxy to remote
			servers."
	::= { proxyProtoServer 4 }

--
-- Median statistics served by the proxy.
--

	proxyMedianSvcTable OBJECT-TYPE
		SYNTAX SEQUENCE OF ProxyMedianSvcEntry
		MAX-ACCESS  not-accessible
		STATUS		  current
		DESCRIPTION
			"The table of median statistics serviced by the proxy
			indexed by the median time."
	::= { proxyPerf 3 }

	proxyMedianSvcEntry OBJECT-TYPE
		SYNTAX		  ProxyMedianSvcEntry
		MAX-ACCESS	  not-accessible
		STATUS		  current
		DESCRIPTION
			"An entry in the proxyMedianSvcTable."
		INDEX { proxyMedianTime }
	::= { proxyMedianSvcTable 1 }

	ProxyMedianSvcEntry ::= SEQUENCE {
		    proxyMedianTime	    Integer32,
		    proxyHTTPAllSvcTime     Integer32,
		    proxyHTTPMissSvcTime    Integer32,
		    proxyHTTPHitSvcTime     Integer32,
		    proxyHTTPNhSvcTime	    Integer32,
		    proxyDnsSvcTime	    Integer32
	}

	proxyMedianTime OBJECT-TYPE
		SYNTAX		Integer32
		MAX-ACCESS	read-only
		STATUS		current
		DESCRIPTION
			"The median time used to index the table proxyMedianSvcTable."
	::= { proxyMedianSvcEntry 1 }

	proxyHTTPAllSvcTime OBJECT-TYPE
		SYNTAX		Integer32
		MAX-ACCESS	read-only
		STATUS		current
		DESCRIPTION
			"The service time for all HTTP requests."
	::= { proxyMedianSvcEntry 2 }

	proxyHTTPMissSvcTime OBJECT-TYPE
		SYNTAX		Integer32
		MAX-ACCESS	read-only
		STATUS		current
		DESCRIPTION
			"The service time for all HTTP misses."
	::= { proxyMedianSvcEntry 3 }

	proxyHTTPHitSvcTime OBJECT-TYPE
		SYNTAX		Integer32
		MAX-ACCESS	read-only
		STATUS		current
		DESCRIPTION
			"The service time for all HTTP hits."
	::= { proxyMedianSvcEntry 4 }

	proxyHTTPNhSvcTime OBJECT-TYPE
		SYNTAX		Integer32
		MAX-ACCESS	read-only
		STATUS		current
		DESCRIPTION
			"The service time for all HTTP near hits."
	::= { proxyMedianSvcEntry 5 }

	proxyDnsSvcTime OBJECT-TYPE
		SYNTAX		Integer32
		MAX-ACCESS	read-only
		STATUS		current
		DESCRIPTION
			"The DNS service time."
	::= { proxyMedianSvcEntry 6 }

END
