HUAWEI-ETHERNET-OPTICSMODULE-MIB DEFINITIONS ::= BEGIN

		IMPORTS 
			huaweiMgmt			
				FROM HUAWEI-MIB			
			ifIndex, InterfaceIndex
				FROM IF-MIB					
			TimeTicks,OBJECT-TYPE
				FROM SNMPv2-SMI			
			TruthValue, MacAddress, RowStatus, TEXTUAL-CONVENTION
				FROM SNMPv2-TC;

		hwEthernetPort MODULE-IDENTITY
			LAST-UPDATED "200207080900Z"
			ORGANIZATION
				"HAUWEI MIB Standard community
				固网MIB标准化委员会 "
			CONTACT-INFO
				"
				联系地址：中国广东深圳，华为技术有限公司
				"
			DESCRIPTION
				"V01_01_200207080900	
				评审专家：zengyonggang 26094/huawei, daiyuehua 20365/huawei, tongjian 28021/huawei, yuanminghui 31133/huawei, 
					   qizhenglin 27958/huawei, liwei 24366/huawei, zhoushiyong 10726/huawei lichangcai 28618/huawei, 
					   hebo 16103/huawei, xujinsong 19085/huawei, lvzhenfeng 18230/huawei, fuhongxun 29027/huawei, 
					   dongqing 18889/huawei,lijin 22251/huawei, zhangshilin 28161/huawei, heqingjian 9730/huawei, 
				          liuchenglong 25279/huawei			
			        "
			::= { huaweiMgmt 14 }
		
	
			PortList ::= TEXTUAL-CONVENTION
  				STATUS      current
    				DESCRIPTION
  				"Each octet within this value specifies a set of eight
 				       ports, with the first octet specifying ports 1 through
				       8, the second octet specifying ports 9 through 16, etc.
				        Within each octet, the most significant bit represents
 				       the lowest numbered port, and the least significant bit
 				       represents the highest numbered port.  Thus, each port
 				       of the bridge is represented by a single bit within the
				        value of this object.  If that bit has a value of '1'
				        then that port is included in the set of ports; the port
				        is not included if its bit has a value of '0'."
 			      SYNTAX      OCTET STRING

                hwOpticsModuleInformation OBJECT IDENTIFIER ::= { hwEthernetPort 6 }		
		
		hwOpticsModuleInformationTable OBJECT-TYPE
			SYNTAX SEQUENCE OF HwOpticsModuleInformationEntry
			MAX-ACCESS not-accessible
			STATUS current
			DESCRIPTION
				"   "
			::= { hwOpticsModuleInformation 1 }
			
		hwOpticsModuleInformationEntry OBJECT-TYPE
			SYNTAX HwOpticsModuleInformationEntry
			MAX-ACCESS not-accessible
			STATUS current
			DESCRIPTION
				"    "
			INDEX { ifIndex }
			::= { hwOpticsModuleInformationTable 1 }
			
                HwOpticsModuleInformationEntry ::=
			SEQUENCE { 
				hwOpticsMDIdentifier
					INTEGER,
				hwOpticsMDExtID
					INTEGER,
				hwOpticsMDConnector
					INTEGER,
				hwOpticsMDEncoding
					INTEGER,
				hwOpticsMDBrNominal
					INTEGER,
				hwOpticsMDLength9Micronkm
					INTEGER,
				hwOpticsMDLength9Micron
					INTEGER,
				hwOpticsMDLength50Micron
					INTEGER,
				hwOpticsMDLength62Micron5
					INTEGER,
				hwOpticsMDLengthCopper
					INTEGER,
				hwOpticsMDVendorName
					OCTET STRING,
				hwOpticsMDVendorOUI
					INTEGER,
				hwOpticsMDVendorPN
					OCTET STRING,
			        hwOpticsMDVendorRev
					OCTET STRING,
		                hwOpticsMDWaveLength
					INTEGER,
			        hwOpticsMDCcBase
					INTEGER,
			        hwOpticsMDOptions
					INTEGER,
				hwOpticsMDBrMax
					INTEGER,
				hwOpticsMDBrMin
					INTEGER,
				hwOpticsMDVendorSN
					OCTET STRING,
				hwOpticsMDDateCode
					OCTET STRING,
				hwOpticsMDDiagnosticMonitoringType
					INTEGER,
				hwOpticsMDEnhancedOptions
					INTEGER,
				hwOpticsMDSFF8472Compliance
					INTEGER,
				hwOpticsMDCcExt
					INTEGER,
				hwOpticsMDVendorSpecific
					OCTET STRING
			 }
		
		hwOpticsMDIdentifier OBJECT-TYPE        
			SYNTAX INTEGER
				{
				Unknown(1),
				GBIC(2),
				SolderedToMotherboard(3),
				SFP(4)
				}			          
			MAX-ACCESS read-only                              
			STATUS current                                    
			DESCRIPTION                                       
				" solderedToMotherboard(3):Module/connector soldered to motherboard "     
			::= { hwOpticsModuleInformationEntry 1 }
			
		hwOpticsMDExtID OBJECT-TYPE        
			SYNTAX INTEGER
				{
				NotSpecifiedOrNotCompliant(1),
				MODDEF1(2),
				MODDEF2(3),
				MODDEF3(4),
				BySerialIDOnly(5),
				MODDEF5(6),
				MODDEF6(7),
				MODDEF7(8)
				}			          
			MAX-ACCESS read-only                              
			STATUS current                                    
			DESCRIPTION                                       
				" 1 Not specified or not compliant with a defined
                                  MOD_DEF. 
                                  2 GBIC is compliant with MOD_DEF 1
                                  3 GBIC is compliant with MOD_DEF 2
                                  4 GBIC is compliant with MOD_DEF 3
                                  5 GBIC/SFP function is defined by serial ID only
                                  6 GBIC is compliant with MOD_DEF 5
                                  7 GBIC is compliant with MOD_DEF 6
                                  8 GBIC is compliant with MOD_DEF 7
				 "                   
			::= { hwOpticsModuleInformationEntry 2 }
		
		hwOpticsMDConnector OBJECT-TYPE        
			SYNTAX INTEGER
				{
				Unknown(1),
				SC(2),
				CopperConnector1(3),
				CopperConnector2(4),
                                BNCTNC(5),
                                CoaxialHeaders(6),
                                FiberJack(7),
                                LC(8),
                                MTRJ(9),
                                MU(10),
                                SG(11),
                                OpticalPigtail(12),
                                HSSDCII(13),
                                CopperPigtail(14),
                                VendorSpecific(15)
				}			          
			MAX-ACCESS read-only                              
			STATUS current                                    
			DESCRIPTION                                       
				" 				
				1   Unknown
				2   SC
				3   Fibre Channel Style 1 copper connector
				4   Fibre Channel Style 2 copper connector
                                5   BNC/TNC
                                6   Fibre Channel coaxial headers
                                7   FiberJack
                                8   LC
                                9   MT-RJ
                                10   MU
                                11   SG
                                12   Optical pigtail
                                13   HSSDC II
                                14   Copper Pigtail
                                15   Vendor specific
				 "    
			::= { hwOpticsModuleInformationEntry 3 }

		hwOpticsMDEncoding OBJECT-TYPE        
			SYNTAX INTEGER
				{
				Unspecified(1),
				EncodingMethod8B10B(2),
				EncodingMethod4B5B(3),
				NRZ(4),
				Manchester(5),
				SONETScrambled(6)
				}			          
			MAX-ACCESS read-only                              
			STATUS current                                    
			DESCRIPTION                                       
				" 	 "           
			::= { hwOpticsModuleInformationEntry 4 }
			
		hwOpticsMDBrNominal OBJECT-TYPE        
			SYNTAX INTEGER							          
			MAX-ACCESS read-only                              
			STATUS current                                    
			DESCRIPTION                                       
				" Nominal bit rate, units of 100 MBits/sec."                   
			::= { hwOpticsModuleInformationEntry 5 }
			
		hwOpticsMDLength9Micronkm OBJECT-TYPE        
			SYNTAX INTEGER							          
			MAX-ACCESS read-only                              
			STATUS current                                    
			DESCRIPTION                                       
				" Link length supported for 9/125 μm fiber, units of km."                   
			::= { hwOpticsModuleInformationEntry 6 }
			
		hwOpticsMDLength9Micron OBJECT-TYPE        
			SYNTAX INTEGER							          
			MAX-ACCESS read-only                              
			STATUS current                                    
			DESCRIPTION                                       
				" Link length supported for 9/125 μm fiber, units of 100 m."                   
			::= { hwOpticsModuleInformationEntry 7 }
			
		hwOpticsMDLength50Micron OBJECT-TYPE        
			SYNTAX INTEGER							          
			MAX-ACCESS read-only                              
			STATUS current                                    
			DESCRIPTION                                       
				" Link length supported for 50/125 μm fiber, units of 10 m."                   
			::= { hwOpticsModuleInformationEntry 8 }
			
		hwOpticsMDLength62Micron5 OBJECT-TYPE        
			SYNTAX INTEGER							          
			MAX-ACCESS read-only                              
			STATUS current                                    
			DESCRIPTION                                       
				" Link length supported for 62.5/125 μm fiber, units of 10 m."                   
			::= { hwOpticsModuleInformationEntry 9 }
			
		hwOpticsMDLengthCopper OBJECT-TYPE        
			SYNTAX INTEGER							          
			MAX-ACCESS read-only                              
			STATUS current                                    
			DESCRIPTION                                       
				" Link length supported for copper, units of meters."                   
			::= { hwOpticsModuleInformationEntry 10 }
			
		hwOpticsMDVendorName OBJECT-TYPE        
			SYNTAX OCTET STRING (SIZE (0..17))							          
			MAX-ACCESS read-only                              
			STATUS current                                    
			DESCRIPTION                                       
				" SFP vendor name (ASCII)."                   
			::= { hwOpticsModuleInformationEntry 11 }
			
		hwOpticsMDVendorOUI OBJECT-TYPE        
			SYNTAX INTEGER							          
			MAX-ACCESS read-only                              
			STATUS current                                    
			DESCRIPTION                                       
				" SFP vendor IEEE company ID."                   
			::= { hwOpticsModuleInformationEntry 12 }
			
		hwOpticsMDVendorPN OBJECT-TYPE        
			SYNTAX OCTET STRING (SIZE (0..17))							          
			MAX-ACCESS read-only                              
			STATUS current                                    
			DESCRIPTION                                       
				" Part number provided by SFP vendor (ASCII)."                   
			::= { hwOpticsModuleInformationEntry 13 }
			
		hwOpticsMDVendorRev OBJECT-TYPE        
			SYNTAX OCTET STRING (SIZE (0..5))							          
			MAX-ACCESS read-only                              
			STATUS current                                    
			DESCRIPTION                                       
				" Revision level for part number provided by vendor (ASCII)."  
			::= { hwOpticsModuleInformationEntry 14 }
			
		hwOpticsMDWaveLength OBJECT-TYPE        
			SYNTAX INTEGER							          
			MAX-ACCESS read-only                              
			STATUS current                                    
			DESCRIPTION                                       
				" Laser wavelength."                   
			::= { hwOpticsModuleInformationEntry 15 }
			
		hwOpticsMDCcBase OBJECT-TYPE        
			SYNTAX INTEGER							          
			MAX-ACCESS read-only                              
			STATUS current                                    
			DESCRIPTION                                       
				" Check code for Base ID Fields (one byte)."                   
			::= { hwOpticsModuleInformationEntry 16 }
			
		hwOpticsMDOptions OBJECT-TYPE        
			SYNTAX INTEGER
				{
                                RateSelect(1),
                                TXDisableAndTheSerialOutputDisabled(2),
                                TXFault(3),
                                SignalLossAndInvertedFromStandard(4),
                                SignalLossAndAsDefined(5)
				}						          
			MAX-ACCESS read-only                              
			STATUS current                                    
			DESCRIPTION                                       
				"                                
				1 RATE_SELECT is implemented
                                2 TX_DISABLE is implemented and disables the serial output.
                                3 TX_FAULT signal implemented. 
                                4 Loss of Signal implemented, signal inverted from standard
                                definition in SFP MSA.
                                5 Loss of Signal implemented, signal as defined in SFP MSA 
				"        
			::= { hwOpticsModuleInformationEntry 17 }
	        
		hwOpticsMDBrMax OBJECT-TYPE        
			SYNTAX INTEGER
			MAX-ACCESS read-only                              
			STATUS current                                    
			DESCRIPTION                                       
				" Upper bit rate margin, units of % "                   
			::= { hwOpticsModuleInformationEntry 18 }
			
		hwOpticsMDBrMin OBJECT-TYPE        
			SYNTAX INTEGER
			MAX-ACCESS read-only                              
			STATUS current                                    
			DESCRIPTION                                       
				"  Lower bit rate margin, units of % "                   
			::= { hwOpticsModuleInformationEntry 19 }
			
		hwOpticsMDVendorSN OBJECT-TYPE        
			SYNTAX OCTET STRING (SIZE (0..17))
			MAX-ACCESS read-only                              
			STATUS current                                    
			DESCRIPTION                                       
				"  Serial number provided by vendor (ASCII) "                   
			::= { hwOpticsModuleInformationEntry 20 }
			
		hwOpticsMDDateCode OBJECT-TYPE        
			SYNTAX OCTET STRING (SIZE (0..9))
			MAX-ACCESS read-only                              
			STATUS current                                    
			DESCRIPTION                                       
				"  Serial number provided by vendor (ASCII) "                   
			::= { hwOpticsModuleInformationEntry 21 }
			
		hwOpticsMDDiagnosticMonitoringType OBJECT-TYPE        
			SYNTAX INTEGER
				{
                                InternallyCalibrated(1),
                                ExternallyCalibrated(2)
                                }
			MAX-ACCESS read-only                              
			STATUS current                                    
			DESCRIPTION                                       
				" 
				 "     
			::= { hwOpticsModuleInformationEntry 22 }
			
		hwOpticsMDEnhancedOptions OBJECT-TYPE        
			SYNTAX INTEGER
				{
                                ForAllMonitoredQuantities(1), 
                                TX_DISABLE(2),
                                TX_FAULT(3),
                                RX_LOS(4),
                                RATE_SELECT(5)
                                }
			MAX-ACCESS read-only                              
			STATUS current                                    
			DESCRIPTION                                       
				"
				1 Optional Alarm/warning flags implemented for
                                all monitored quantities 
                                2 Optional Soft TX_DISABLE control and
                                monitoring implemented
                                3 Optional Soft TX_FAULT monitoring
                                implemented
                                4 Optional Soft RX_LOS monitoring
                                implemented
                                5 Optional Soft RATE_SELECT control and
                                monitoring implemented
				  "      
			::= { hwOpticsModuleInformationEntry 23 }
			
		hwOpticsMDSFF8472Compliance OBJECT-TYPE        
			SYNTAX INTEGER
				{
                                undefined(1), 
                                IncludesSFF8472(2),
                                TBD(3)
                                }
			MAX-ACCESS read-only                              
			STATUS current                                    
			DESCRIPTION                                       
				"
				1 Not included or undefined.
                                2 ncludes functionality described in Rev 9.3 SFF-8472.
                                3 To Be Determined.
                                	  "
			::= { hwOpticsModuleInformationEntry 24 }
			
		hwOpticsMDCcExt OBJECT-TYPE        
			SYNTAX INTEGER
			MAX-ACCESS read-only                              
			STATUS current                                    
			DESCRIPTION                                       
				"
				Check code for the Extended ID Fields (one byte).
                                	  "
			::= { hwOpticsModuleInformationEntry 25 }
			
		hwOpticsMDVendorSpecific OBJECT-TYPE        
			SYNTAX OCTET STRING (SIZE (0..96))
			MAX-ACCESS read-only                              
			STATUS current                                    
			DESCRIPTION                                       
				"
				32 bytes.
                                	  "
			::= { hwOpticsModuleInformationEntry 26 }

		hwOpticsModuleTransceiverTable OBJECT-TYPE
			SYNTAX SEQUENCE OF HwOpticsModuleTransceiverEntry
			MAX-ACCESS not-accessible
			STATUS current
			DESCRIPTION
				"   "
			::= { hwOpticsModuleInformation 2 }
		
		hwOpticsModuleTransceiverEntry OBJECT-TYPE
			SYNTAX HwOpticsModuleTransceiverEntry
			MAX-ACCESS not-accessible
			STATUS current
			DESCRIPTION
				"    "
			INDEX { ifIndex }
			::= { hwOpticsModuleTransceiverTable 1 }
		
                HwOpticsModuleTransceiverEntry ::=
			SEQUENCE { 
				hwOpticsMDInfinibandComplianceCodes
					INTEGER,
				hwOpticsMDSONETcomplianceCodes
					INTEGER,
				hwOpticsMDGEComplianceCodes
					INTEGER,
				hwOpticsMDLinkLength
					INTEGER,
				hwOpticsMDTransmitterTechnology
					INTEGER,
				hwOpticsMDTransmissionMedia
					INTEGER,
				hwOpticsMDSpeed
					INTEGER
			 }

		hwOpticsMDInfinibandComplianceCodes OBJECT-TYPE
			SYNTAX INTEGER
				{
				SX(1),
				LX(2),
				CopperActive(3),
				CopperPassive(4)
				}
			MAX-ACCESS read-only
			STATUS current
			DESCRIPTION
				"
				1.1XSX
				2.1XLX
				3.1XCopperActive
				4.1XCopperPassive
     
				"
			::= { hwOpticsModuleTransceiverEntry 1 }
			
		hwOpticsMDSONETcomplianceCodes OBJECT-TYPE
			SYNTAX INTEGER
				{
				OC48LongReach(1),
				OC48IntermediateReach(2),
				OC48ShortReach(3),
				OC12SingleModeLongReach(4),
				OC12SingleModeIntermediateReach(5),
				OC12MultiModeShortReach(6),
				OC3SingleModeLongReach(7),
				OC3SingleModeIntermediateReach(8),
				OC3MultiModeShortReach(9)
				}
			MAX-ACCESS read-only
			STATUS current
			DESCRIPTION
				"     "
			::= { hwOpticsModuleTransceiverEntry 2 }
			
		hwOpticsMDGEComplianceCodes OBJECT-TYPE
			SYNTAX INTEGER
				{
				T(1),
				CX(2),
				LX(3),
				SX(4)
				}
			MAX-ACCESS read-only
			STATUS current
			DESCRIPTION
				"   
				1.1000BASE-T
				2.1000BASE-CX
				3.1000BASE-LX
				4.1000BASE-SX
				  "
			::= { hwOpticsModuleTransceiverEntry 3 }
			
		hwOpticsMDLinkLength OBJECT-TYPE
			SYNTAX INTEGER
				{
				VeryLongDistance(1),
				ShortDistance(2),
				IntermediateDistance(3),
				LongDistance(4)
				}
			MAX-ACCESS read-only
			STATUS current
			DESCRIPTION
				"     "
			::= { hwOpticsModuleTransceiverEntry 4 }

		hwOpticsMDTransmitterTechnology OBJECT-TYPE
			SYNTAX INTEGER
				{
				longwaveLaser(1),
				electricalInterenclosure(2),
				shortwaveLaser(3)
				}
			MAX-ACCESS read-only
			STATUS current
			DESCRIPTION
				"  
				1.longwave laser
				2.electrical inter-enclosure
				3.shortwave laser 
				   "
			::= { hwOpticsModuleTransceiverEntry 5 }
			
		hwOpticsMDTransmissionMedia OBJECT-TYPE
			SYNTAX INTEGER
				{
				TwinAxialPair(1),
				ShieldedTwistedPair(2),
				MiniatureCoax(3),
				VideoCoax(4),
				MultiMode62m5(5),
				MultiMode50m(6),
				SingleMode(7)
				}
			MAX-ACCESS read-only
			STATUS current
			DESCRIPTION
				"    
				1 twin axial pair 
                                2 shielded twisted pair 
                                3 miniature coax 
                                4 video coax 
                                5 multi-mode, 62.5m 
                                6 multi-mode, 50 m 
                                7 single mode 
				 "
			::= { hwOpticsModuleTransceiverEntry 6 }
			
		hwOpticsMDSpeed OBJECT-TYPE
			SYNTAX INTEGER
				{
				Speed400MBytesPerSec(1),
				Speed200MBytesPerSec(2),
				Speed100MBytesPerSec(3)
				}
			MAX-ACCESS read-only
			STATUS current
			DESCRIPTION
				"     "
			::= { hwOpticsModuleTransceiverEntry 7 }
			

			
	END
