ISHELF-PM-MIB DEFINITIONS ::= BEGIN

IMPORTS
    OBJECT-TYPE,
    NOTIFICATION-TYPE,
    MODULE-IDENTITY,
    Counter32,
    Gauge32,
    Unsigned32
        FROM SNMPv2-SMI

    RowStatus,
    TruthValue
        FROM SNMPv2-TC

    telstrat,
    osiIShelf,
    iShelfPm,
    iShelfModules
        FROM ISHELF-ARCS-MIB

    IShelfLabel,
    IShelfLocation,
    IShelfOntLogicalId,
    IShelfPerfInvalidFlag,
    IShelfThresholdCrossingIndex,
    IShelfThresholdCrossingPointer,
    IShelfDateTime,
    IShelfOntSubscriberLineCardIndex,
    IShelfLocationType,
    IShelfCircuit,
    IShelfOltTrafficShaperIndex
        FROM ISHELF-TC
    ;

iShelfPmMIB MODULE-IDENTITY
    LAST-UPDATED "200604280000Z"
    ORGANIZATION "TelStrat"
    CONTACT-INFO "
        TelStrat
        6900 K Avenue
        Plano, TX, USA 75074

        Main Phone: 972-543-3500
        Main Fax: 972-424-2909
        Support Phone: 888-658-8572
        Support Fax: 918-610-9975
        Email:  AccessCustomerSupport@telstrat.com"
    DESCRIPTION
        "The MIB module for managing the PM, Statistics and Traffic Counts."
    REVISION "200604280000Z"
    DESCRIPTION "Beta Release"
    ::= { iShelfModules 10 }

-- %CLICMDPREFIX pm
-- %CLICMDABBR group
iShelfThresholdCrossing OBJECT IDENTIFIER ::= { iShelfPm 1 }

-- %CLICMDPREFIX pm:traffic
iShelfTraffic OBJECT IDENTIFIER ::= { iShelfPm 2 }

-- %CLICMDPREFIX pm:idlc
iShelfIdlcPm OBJECT IDENTIFIER ::= { iShelfPm 3 }

-- %CLICMDPREFIX pm:ont
iShelfOntPm OBJECT IDENTIFIER ::= { iShelfPm 4 }

-- %CLICMDPREFIX pm:t1
iShelfT1Pm OBJECT IDENTIFIER ::= { iShelfPm 5 }

-- %CLICMDPREFIX pm:sdv
iShelfSdvPm OBJECT IDENTIFIER ::= { iShelfPm 6 }

-- %CLICMDPREFIX pm:olt
iShelfOltPm OBJECT IDENTIFIER ::= { iShelfPm 7 }

-- %CLICMDPREFIX pm:egw
iShelfEgwPm OBJECT IDENTIFIER ::= { iShelfPm 8 }

-- %CLICMDPREFIX pm:egw:trap
iShelfEgwPmTrap OBJECT IDENTIFIER ::= { iShelfEgwPm 1 }

-- ++++++++++++++++++++++++++++++++++++++++++++++++++++++++++++++++++++++++
--
-- iShelfThresholdCrossingTable - 
--
-- ++++++++++++++++++++++++++++++++++++++++++++++++++++++++++++++++++++++++

-- %CLICMDABBR tcatable
-- %CLISHOWGROUP tcatable
iShelfThresholdCrossingTable OBJECT-TYPE
    SYNTAX      SEQUENCE OF IShelfThresholdCrossingEntry
    MAX-ACCESS  not-accessible
    STATUS      current
    DESCRIPTION
        "This table contains threshold values for the
         performance monitoring parameters maintained by other
         entities.  Ohter entities may point to this table.
         Multiple other entities may point to a single entry in
         this table.

         The convention for threshold crossing values is a value
         of 0 means the threshold value is not being checked, i.e.
         the TCA is disabled."
    ::= { iShelfThresholdCrossing 1 }

iShelfThresholdCrossingEntry OBJECT-TYPE
    SYNTAX      IShelfThresholdCrossingEntry
    MAX-ACCESS  not-accessible
    STATUS      current
    DESCRIPTION "Each entry contains one set of threshold crossing values."
    INDEX       { iShelfThresholdCrossingIndex }
    ::= { iShelfThresholdCrossingTable 1 }

IShelfThresholdCrossingEntry ::=
    SEQUENCE {
        iShelfThresholdCrossingIndex
            IShelfThresholdCrossingIndex,
        iShelfThresholdCrossingLabel
            IShelfLabel,
        iShelfThresholdCrossingValue1
            Gauge32,
        iShelfThresholdCrossingValue2
            Gauge32,
        iShelfThresholdCrossingValue3
            Gauge32,
        iShelfThresholdCrossingValue4
            Gauge32,
        iShelfThresholdCrossingValue5
            Gauge32,
        iShelfThresholdCrossingValue6
            Gauge32,
        iShelfThresholdCrossingValue7
            Gauge32,
        iShelfThresholdCrossingValue8
            Gauge32,
        iShelfThresholdCrossingValue9
            Gauge32,
        iShelfThresholdCrossingValue10
            Gauge32,
        iShelfThresholdCrossingValue11
            Gauge32,
        iShelfThresholdCrossingValue12
            Gauge32,
        iShelfThresholdCrossingValue13
            Gauge32,
        iShelfThresholdCrossingValue14
            Gauge32,
        iShelfThresholdCrossingValue15
            Gauge32,
        iShelfThresholdCrossingValue16
            Gauge32,
        iShelfThresholdCrossingRowStatus
            RowStatus
    }

-- %CLISHOWGROUP tcatable.1
-- %CLISHOWGROUP tcatable.2
-- %CLISHOWGROUP tcatable.3
-- %CLISHOWGROUP tcatable.4
iShelfThresholdCrossingIndex OBJECT-TYPE
    SYNTAX      IShelfThresholdCrossingIndex
    MAX-ACCESS  read-only
    STATUS      current
    DESCRIPTION
        "This object identifies the index for the
         threshold crossing table."
    ::= { iShelfThresholdCrossingEntry 1 }

-- %SETINACTIVE
-- %CLISHOWGROUP tcatable.1
iShelfThresholdCrossingLabel OBJECT-TYPE
    SYNTAX      IShelfLabel
    MAX-ACCESS  read-write
    STATUS      current
    DESCRIPTION
        "This object identifies the label for the
         threshold crossing table.
         NOTE:  this object can only be modified with a non-active rowStatus."
    ::= { iShelfThresholdCrossingEntry 2 }


-- %SETINACTIVE
-- %CLIOPTION
-- %CLICOLLABEL Value1
-- %CLIWIDTH 10
-- %CLISHOWGROUP tcatable.1
iShelfThresholdCrossingValue1 OBJECT-TYPE
    SYNTAX      Gauge32
    MAX-ACCESS  read-write
    STATUS      current
    DESCRIPTION
        "This object identifies the threshold value
         for the 1st thresholded counter.  A value of zero
         indicates no threshold value.
         NOTE:  this object can only be modified with a non-active rowStatus."
    DEFVAL      { 0 }
    ::= { iShelfThresholdCrossingEntry 3 }

-- %SETINACTIVE
-- %CLIOPTION
-- %CLICOLLABEL Value2
-- %CLIWIDTH 10
-- %CLISHOWGROUP tcatable.1
iShelfThresholdCrossingValue2 OBJECT-TYPE
    SYNTAX      Gauge32
    MAX-ACCESS  read-write
    STATUS      current
    DESCRIPTION
        "This object identifies the threshold value
         for the 2nd thresholded counter.  A value of zero
         indicates no threshold value.
         NOTE:  this object can only be modified with a non-active rowStatus."
    DEFVAL      { 0 }
    ::= { iShelfThresholdCrossingEntry 4 }

-- %SETINACTIVE
-- %CLIOPTION
-- %CLICOLLABEL Value3
-- %CLIWIDTH 10
-- %CLISHOWGROUP tcatable.1
iShelfThresholdCrossingValue3 OBJECT-TYPE
    SYNTAX      Gauge32
    MAX-ACCESS  read-write
    STATUS      current
    DESCRIPTION
        "This object identifies the threshold value
         for the 3rd thresholded counter.  A value of zero
         indicates no threshold value.
         NOTE:  this object can only be modified with a non-active rowStatus."
    DEFVAL      { 0 }
    ::= { iShelfThresholdCrossingEntry 5 }

-- %SETINACTIVE
-- %CLIOPTION
-- %CLICOLLABEL Value4
-- %CLIWIDTH 10
-- %CLISHOWGROUP tcatable.1
iShelfThresholdCrossingValue4 OBJECT-TYPE
    SYNTAX      Gauge32
    MAX-ACCESS  read-write
    STATUS      current
    DESCRIPTION
        "This object identifies the threshold value
         for the 4th thresholded counter.  A value of zero
         indicates no threshold value.
         NOTE:  this object can only be modified with a non-active rowStatus."
    DEFVAL      { 0 }
    ::= { iShelfThresholdCrossingEntry 6 }

-- %SETINACTIVE
-- %CLIOPTION
-- %CLICOLLABEL Value5
-- %CLIWIDTH 10
-- %CLISHOWGROUP tcatable.2
iShelfThresholdCrossingValue5 OBJECT-TYPE
    SYNTAX      Gauge32
    MAX-ACCESS  read-write
    STATUS      current
    DESCRIPTION
        "This object identifies the threshold value
         for the 5th thresholded counter.  A value of zero
         indicates no threshold value.
         NOTE:  this object can only be modified with a non-active rowStatus."
    DEFVAL      { 0 }
    ::= { iShelfThresholdCrossingEntry 7 }

-- %SETINACTIVE
-- %CLIOPTION
-- %CLICOLLABEL Value6
-- %CLIWIDTH 10
-- %CLISHOWGROUP tcatable.2
iShelfThresholdCrossingValue6 OBJECT-TYPE
    SYNTAX      Gauge32
    MAX-ACCESS  read-write
    STATUS      current
    DESCRIPTION
        "This object identifies the threshold value
         for the 6th thresholded counter.  A value of zero
         indicates no threshold value.
         NOTE:  this object can only be modified with a non-active rowStatus."
    DEFVAL      { 0 }
    ::= { iShelfThresholdCrossingEntry 8 }

-- %SETINACTIVE
-- %CLIOPTION
-- %CLICOLLABEL Value7
-- %CLIWIDTH 10
-- %CLISHOWGROUP tcatable.2
iShelfThresholdCrossingValue7 OBJECT-TYPE
    SYNTAX      Gauge32
    MAX-ACCESS  read-write
    STATUS      current
    DESCRIPTION
        "This object identifies the threshold value
         for the 7th thresholded counter.  A value of zero
         indicates no threshold value.
         NOTE:  this object can only be modified with a non-active rowStatus."
    DEFVAL      { 0 }
    ::= { iShelfThresholdCrossingEntry 9 }

-- %SETINACTIVE
-- %CLIOPTION
-- %CLICOLLABEL Value8
-- %CLIWIDTH 10
-- %CLISHOWGROUP tcatable.2
iShelfThresholdCrossingValue8 OBJECT-TYPE
    SYNTAX      Gauge32
    MAX-ACCESS  read-write
    STATUS      current
    DESCRIPTION
        "This object identifies the threshold value
         for the 8th thresholded counter.  A value of zero
         indicates no threshold value.
         NOTE:  this object can only be modified with a non-active rowStatus."
    DEFVAL      { 0 }
    ::= { iShelfThresholdCrossingEntry 10 }

-- %SETINACTIVE
-- %CLIOPTION
-- %CLICOLLABEL Value9
-- %CLIWIDTH 10
-- %CLISHOWGROUP tcatable.3
iShelfThresholdCrossingValue9 OBJECT-TYPE
    SYNTAX      Gauge32
    MAX-ACCESS  read-write
    STATUS      current
    DESCRIPTION
        "This object identifies the threshold value
         for the 9th thresholded counter.  A value of zero
         indicates no threshold value.
         NOTE:  this object can only be modified with a non-active rowStatus."
    DEFVAL      { 0 }
    ::= { iShelfThresholdCrossingEntry 11 }

-- %SETINACTIVE
-- %CLIOPTION
-- %CLICOLLABEL Value10
-- %CLIWIDTH 10
-- %CLISHOWGROUP tcatable.3
iShelfThresholdCrossingValue10 OBJECT-TYPE
    SYNTAX      Gauge32
    MAX-ACCESS  read-write
    STATUS      current
    DESCRIPTION
        "This object identifies the threshold value
         for the 10th thresholded counter.  A value of zero
         indicates no threshold value.
         NOTE:  this object can only be modified with a non-active rowStatus."
    DEFVAL      { 0 }
    ::= { iShelfThresholdCrossingEntry 12 }

-- %SETINACTIVE
-- %CLIOPTION
-- %CLICOLLABEL Value11
-- %CLIWIDTH 10
-- %CLISHOWGROUP tcatable.3
iShelfThresholdCrossingValue11 OBJECT-TYPE
    SYNTAX      Gauge32
    MAX-ACCESS  read-write
    STATUS      current
    DESCRIPTION
        "This object identifies the threshold value
         for the 11th thresholded counter.  A value of zero
         indicates no threshold value.
         NOTE:  this object can only be modified with a non-active rowStatus."
    DEFVAL      { 0 }
    ::= { iShelfThresholdCrossingEntry 13 }

-- %SETINACTIVE
-- %CLIOPTION
-- %CLICOLLABEL Value12
-- %CLIWIDTH 10
-- %CLISHOWGROUP tcatable.3
iShelfThresholdCrossingValue12 OBJECT-TYPE
    SYNTAX      Gauge32
    MAX-ACCESS  read-write
    STATUS      current
    DESCRIPTION
        "This object identifies the threshold value
         for the 12th thresholded counter.  A value of zero
         indicates no threshold value.
         NOTE:  this object can only be modified with a non-active rowStatus."
    DEFVAL      { 0 }
    ::= { iShelfThresholdCrossingEntry 14 }

-- %SETINACTIVE
-- %CLIOPTION
-- %CLICOLLABEL Value13
-- %CLIWIDTH 10
-- %CLISHOWGROUP tcatable.4
iShelfThresholdCrossingValue13 OBJECT-TYPE
    SYNTAX      Gauge32
    MAX-ACCESS  read-write
    STATUS      current
    DESCRIPTION
        "This object identifies the threshold value
         for the 13th thresholded counter.  A value of zero
         indicates no threshold value.
         NOTE:  this object can only be modified with a non-active rowStatus."
    DEFVAL      { 0 }
    ::= { iShelfThresholdCrossingEntry 15 }

-- %SETINACTIVE
-- %CLIOPTION
-- %CLICOLLABEL Value14
-- %CLIWIDTH 10
-- %CLISHOWGROUP tcatable.4
iShelfThresholdCrossingValue14 OBJECT-TYPE
    SYNTAX      Gauge32
    MAX-ACCESS  read-write
    STATUS      current
    DESCRIPTION
        "This object identifies the threshold value
         for the 14th thresholded counter.  A value of zero
         indicates no threshold value.
         NOTE:  this object can only be modified with a non-active rowStatus."
    DEFVAL      { 0 }
    ::= { iShelfThresholdCrossingEntry 16 }

-- %SETINACTIVE
-- %CLIOPTION
-- %CLICOLLABEL Value15
-- %CLIWIDTH 10
-- %CLISHOWGROUP tcatable.4
iShelfThresholdCrossingValue15 OBJECT-TYPE
    SYNTAX      Gauge32
    MAX-ACCESS  read-write
    STATUS      current
    DESCRIPTION
        "This object identifies the threshold value
         for the 15th thresholded counter.  A value of zero
         indicates no threshold value.
         NOTE:  this object can only be modified with a non-active rowStatus."
    DEFVAL      { 0 }
    ::= { iShelfThresholdCrossingEntry 17 }

-- %SETINACTIVE
-- %CLIOPTION
-- %CLICOLLABEL Value16
-- %CLIWIDTH 10
-- %CLISHOWGROUP tcatable.4
iShelfThresholdCrossingValue16 OBJECT-TYPE
    SYNTAX      Gauge32
    MAX-ACCESS  read-write
    STATUS      current
    DESCRIPTION
        "This object identifies the threshold value
         for the 16th thresholded counter.  A value of zero
         indicates no threshold value.
         NOTE:  this object can only be modified with a non-active rowStatus."
    DEFVAL      { 0 }
    ::= { iShelfThresholdCrossingEntry 18 }

-- %ROWSTATUSTYPE RFC
-- %CLICOLLABEL RowStatus
-- %CLIWIDTH 12
iShelfThresholdCrossingRowStatus OBJECT-TYPE
    SYNTAX      RowStatus
    MAX-ACCESS  read-write
    STATUS      current
    DESCRIPTION
        "This object is used for row creation, modification and
         deletion. Modification of objects within the row is only allowed
         when the row is not in the active state. In the case of an active
         row (already created), the row must be made notInService prior to
         modifying any settable objects. The notInService setting has no
         impact on the underlying object but is used to cause atomic updates
         of the row once it is moved to the active state.

         The supported values of RowStatus are:
            active (1)
            notInService (2)
            notReady (3)
            createAndGo (4)
            createAndWait (5)
            destroy (6)

         At least one of the 16 threshold crossing values must be set for
         a valid row."
    ::= { iShelfThresholdCrossingEntry 19 }

-- ++++++++++++++++++++++++++++++++++++++++++++++++++++++++++++++++++++++++
--
-- iShelfTrafficDataTable - 
--
-- ++++++++++++++++++++++++++++++++++++++++++++++++++++++++++++++++++++++++

iShelfTrafficDataTable OBJECT-TYPE
    SYNTAX      SEQUENCE OF IShelfTrafficDataEntry
    MAX-ACCESS  not-accessible
    STATUS      current
    DESCRIPTION ""
    ::= { iShelfTraffic 1 }

iShelfTrafficDataEntry OBJECT-TYPE
    SYNTAX      IShelfTrafficDataEntry
    MAX-ACCESS  not-accessible
    STATUS      current
    DESCRIPTION
        "Each row in the traffic data table includes information
         above a given Node in the system."
    INDEX       { iShelfTrafficDataLocation }
    ::= { iShelfTrafficDataTable 1 }

IShelfTrafficDataEntry ::=
    SEQUENCE {
        iShelfTrafficDataLocation
            IShelfLocation,
        iShelfTrafficDataActiveCalls64kbps
            Counter32,
        iShelfTrafficDataActiveCalls32kbps
            Counter32,
        iShelfTrafficDataActiveCalls16kbps
            Counter32,
        iShelfTrafficDataDataCalls
            Counter32,
        iShelfTrafficDataCcsVoice
            Counter32,
        iShelfTrafficDataCcsData
            Counter32
    }

iShelfTrafficDataLocation OBJECT-TYPE
    SYNTAX      IShelfLocation
    MAX-ACCESS  read-only
    STATUS      current
    DESCRIPTION "This object indicates the Node for the associated data."
    ::= { iShelfTrafficDataEntry 1 }

iShelfTrafficDataActiveCalls64kbps OBJECT-TYPE
    SYNTAX      Counter32
    MAX-ACCESS  read-only
    STATUS      current
    DESCRIPTION
        "This object indicates the number of calls currently being
         handled at 64 kbps."
    ::= { iShelfTrafficDataEntry 2 }

iShelfTrafficDataActiveCalls32kbps OBJECT-TYPE
    SYNTAX      Counter32
    MAX-ACCESS  read-only
    STATUS      current
    DESCRIPTION
        "This object indicates the number of calls currently being
         handled at 32 kbps."
    ::= { iShelfTrafficDataEntry 3 }

iShelfTrafficDataActiveCalls16kbps OBJECT-TYPE
    SYNTAX      Counter32
    MAX-ACCESS  read-only
    STATUS      current
    DESCRIPTION
        "This object indicates the number of calls currently being
         handled at 16 kbps."
    ::= { iShelfTrafficDataEntry 4 }

iShelfTrafficDataDataCalls OBJECT-TYPE
    SYNTAX      Counter32
    MAX-ACCESS  read-only
    STATUS      current
    DESCRIPTION
        "This object indicates the number of data calls currently
         being handled."
    ::= { iShelfTrafficDataEntry 5 }

iShelfTrafficDataCcsVoice OBJECT-TYPE
    SYNTAX      Counter32
    MAX-ACCESS  read-only
    STATUS      current
    DESCRIPTION
        "This object indicates the number of Centi Call Seconds (CCS)
         of voice calls handled during the last hour."
    ::= { iShelfTrafficDataEntry 6 }

iShelfTrafficDataCcsData OBJECT-TYPE
    SYNTAX      Counter32
    MAX-ACCESS  read-only
    STATUS      current
    DESCRIPTION
        "This object indicates the number of Centi Call Seconds (CCS)
         of data calls handled during the last hour."
    ::= { iShelfTrafficDataEntry 7 }

-- ++++++++++++++++++++++++++++++++++++++++++++++++++++++++++++++++++++++++
--
-- iShelfTrafficStatisticsTable - 
--
-- ++++++++++++++++++++++++++++++++++++++++++++++++++++++++++++++++++++++++

iShelfTrafficStatisticsTable OBJECT-TYPE
    SYNTAX      SEQUENCE OF IShelfTrafficStatisticsEntry
    MAX-ACCESS  not-accessible
    STATUS      current
    DESCRIPTION ""
    ::= { iShelfTraffic 2 }

iShelfTrafficStatisticsEntry OBJECT-TYPE
    SYNTAX      IShelfTrafficStatisticsEntry
    MAX-ACCESS  not-accessible
    STATUS      current
    DESCRIPTION
        "Each row in the traffic statistics table includes information
         above a given Node in the system for a specific period."
    INDEX       { iShelfTrafficStatisticsLocation,
                  iShelfTrafficStatisticsPeriod }
    ::= { iShelfTrafficStatisticsTable 1 }

IShelfTrafficStatisticsEntry ::=
    SEQUENCE {
        iShelfTrafficStatisticsLocation
            IShelfLocation,
        iShelfTrafficStatisticsPeriod
            INTEGER,
        iShelfTrafficStatisticsEndDateAndTime
            IShelfDateTime,
        iShelfTrafficStatisticsDuration
            Counter32,
        iShelfTrafficStatisticsCalls64kbps
            Counter32,
        iShelfTrafficStatisticsCalls32kbps
            Counter32,
        iShelfTrafficStatisticsCalls16kbps
            Counter32,
        iShelfTrafficStatisticsForcedCalls
            Counter32,
        iShelfTrafficStatisticsDataCalls
            Counter32,
        iShelfTrafficStatisticsDataCallsPercent
            Counter32,
        iShelfTrafficStatisticsAllTrunksBusy
            Counter32,
        iShelfTrafficStatisticsAllTrunksBusyDuration
            Counter32,
        iShelfTrafficStatisticsOriginating
            Counter32,
        iShelfTrafficStatisticsTerminating
            Counter32,
        iShelfTrafficStatisticsPeakHourlyCcsLoad
            Counter32,
        iShelfTrafficStatisticsPeakCcsLoadDateAndTime
            IShelfDateTime,
        iShelfTrafficStatisticsPeakCalls
            Counter32,
        iShelfTrafficStatisticsPeakCallsDateAndTime
            IShelfDateTime,
        iShelfTrafficStatisticsCumulativeCcsVoice
            Counter32,
        iShelfTrafficStatisticsCumulativeCcsData
            Counter32,
        iShelfTrafficStatisticsCumulativeCcsDataPercent
            Counter32,
        iShelfTrafficStatisticsOriginatingCallsBlocked
            Counter32,
        iShelfTrafficStatisticsTerminatingCallsBlocked
            Counter32
    }

iShelfTrafficStatisticsLocation OBJECT-TYPE
    SYNTAX      IShelfLocation
    MAX-ACCESS  read-only
    STATUS      current
    DESCRIPTION
        "This object identifies the Node to which the statistics
         apply."
    ::= { iShelfTrafficStatisticsEntry 1 }

iShelfTrafficStatisticsPeriod OBJECT-TYPE
    SYNTAX      INTEGER {
                    today(1),
                    lastHour(2),
                    yesterday(3),
                    cumulative(4)
                }
    MAX-ACCESS  read-only
    STATUS      current
    DESCRIPTION "This object identifies the time period to be retrieved."
    ::= { iShelfTrafficStatisticsEntry 2 }

iShelfTrafficStatisticsEndDateAndTime OBJECT-TYPE
    SYNTAX      IShelfDateTime
    MAX-ACCESS  read-only
    STATUS      current
    DESCRIPTION "This object identifies the ending date/time of the report."
    ::= { iShelfTrafficStatisticsEntry 3 }

iShelfTrafficStatisticsDuration OBJECT-TYPE
    SYNTAX      Counter32
    MAX-ACCESS  read-only
    STATUS      current
    DESCRIPTION "This object identifies duration in seconds for the report."
    ::= { iShelfTrafficStatisticsEntry 4 }

iShelfTrafficStatisticsCalls64kbps OBJECT-TYPE
    SYNTAX      Counter32
    MAX-ACCESS  read-only
    STATUS      current
    DESCRIPTION
        "This object indicates the total calls handled at 64 kbps
         during the period."
    ::= { iShelfTrafficStatisticsEntry 5 }

iShelfTrafficStatisticsCalls32kbps OBJECT-TYPE
    SYNTAX      Counter32
    MAX-ACCESS  read-only
    STATUS      current
    DESCRIPTION
        "This object indicates the total calls handled at 32 kbps
         during the period."
    ::= { iShelfTrafficStatisticsEntry 6 }

iShelfTrafficStatisticsCalls16kbps OBJECT-TYPE
    SYNTAX      Counter32
    MAX-ACCESS  read-only
    STATUS      current
    DESCRIPTION
        "This object indicates the total calls handled at 16 kbps
         during the period."
    ::= { iShelfTrafficStatisticsEntry 7 }

iShelfTrafficStatisticsForcedCalls OBJECT-TYPE
    SYNTAX      Counter32
    MAX-ACCESS  read-only
    STATUS      current
    DESCRIPTION
        "This object indicates the number of forced calls
         during the period."
    ::= { iShelfTrafficStatisticsEntry 8 }

iShelfTrafficStatisticsDataCalls OBJECT-TYPE
    SYNTAX      Counter32
    MAX-ACCESS  read-only
    STATUS      current
    DESCRIPTION
        "This object indicates the number of data calls
         during the period."
    ::= { iShelfTrafficStatisticsEntry 9 }

iShelfTrafficStatisticsDataCallsPercent OBJECT-TYPE
    SYNTAX      Counter32
    MAX-ACCESS  read-only
    STATUS      current
    DESCRIPTION
        "This object indicates the percentage of total
         calls handled during the reporting period that were data calls."
    ::= { iShelfTrafficStatisticsEntry 10 }

iShelfTrafficStatisticsAllTrunksBusy OBJECT-TYPE
    SYNTAX      Counter32
    MAX-ACCESS  read-only
    STATUS      current
    DESCRIPTION
        "This object indicates the number of times all trunks
         in the node were busy during the reporting period."
    ::= { iShelfTrafficStatisticsEntry 11 }

iShelfTrafficStatisticsAllTrunksBusyDuration OBJECT-TYPE
    SYNTAX      Counter32
    MAX-ACCESS  read-only
    STATUS      current
    DESCRIPTION
        "This object indicates the all trunks busy duration in
         seconds."
    ::= { iShelfTrafficStatisticsEntry 12 }

iShelfTrafficStatisticsOriginating OBJECT-TYPE
    SYNTAX      Counter32
    MAX-ACCESS  read-only
    STATUS      current
    DESCRIPTION
        "This object indicates the number of calls originated
         within the system during the reporting period."
    ::= { iShelfTrafficStatisticsEntry 13 }

iShelfTrafficStatisticsTerminating OBJECT-TYPE
    SYNTAX      Counter32
    MAX-ACCESS  read-only
    STATUS      current
    DESCRIPTION
        "This object indicates the number of calls terminated
         within the system during the reporting period."
    ::= { iShelfTrafficStatisticsEntry 14 }

iShelfTrafficStatisticsPeakHourlyCcsLoad OBJECT-TYPE
    SYNTAX      Counter32
    MAX-ACCESS  read-only
    STATUS      current
    DESCRIPTION
        "This object indicates the highest number of calls
         handled during any one hour during the reporting period."
    ::= { iShelfTrafficStatisticsEntry 15 }

iShelfTrafficStatisticsPeakCcsLoadDateAndTime OBJECT-TYPE
    SYNTAX      IShelfDateTime
    MAX-ACCESS  read-only
    STATUS      current
    DESCRIPTION
        "This object indicates the date and time
         that the peak hourly CCS load occurred."
    ::= { iShelfTrafficStatisticsEntry 16 }

iShelfTrafficStatisticsPeakCalls OBJECT-TYPE
    SYNTAX      Counter32
    MAX-ACCESS  read-only
    STATUS      current
    DESCRIPTION
        "This object indicates the peak calls during the
         period."
    ::= { iShelfTrafficStatisticsEntry 17 }

iShelfTrafficStatisticsPeakCallsDateAndTime OBJECT-TYPE
    SYNTAX      IShelfDateTime
    MAX-ACCESS  read-only
    STATUS      current
    DESCRIPTION
        "This object indicates the date and time that the peak
         calls occurred."
    ::= { iShelfTrafficStatisticsEntry 18 }

iShelfTrafficStatisticsCumulativeCcsVoice OBJECT-TYPE
    SYNTAX      Counter32
    MAX-ACCESS  read-only
    STATUS      current
    DESCRIPTION
        "This object indicates the total voice calls during the
         reporting period."
    ::= { iShelfTrafficStatisticsEntry 19 }

iShelfTrafficStatisticsCumulativeCcsData OBJECT-TYPE
    SYNTAX      Counter32
    MAX-ACCESS  read-only
    STATUS      current
    DESCRIPTION
        "This object indicates the total data calls during the
         reporting period."
    ::= { iShelfTrafficStatisticsEntry 20 }

iShelfTrafficStatisticsCumulativeCcsDataPercent OBJECT-TYPE
    SYNTAX      Counter32
    MAX-ACCESS  read-only
    STATUS      current
    DESCRIPTION
        "This object indicates the percentage of total calls
         that were data calls."
    ::= { iShelfTrafficStatisticsEntry 21 }

iShelfTrafficStatisticsOriginatingCallsBlocked OBJECT-TYPE
    SYNTAX      Counter32
    MAX-ACCESS  read-only
    STATUS      current
    DESCRIPTION
        "This object indicates the number of calls originating
         in the system that were blocked during the reporting period."
    ::= { iShelfTrafficStatisticsEntry 22 }

iShelfTrafficStatisticsTerminatingCallsBlocked OBJECT-TYPE
    SYNTAX      Counter32
    MAX-ACCESS  read-only
    STATUS      current
    DESCRIPTION
        "This object indicates the number of calls terminating
         in the system that were blocked during the reporting period."
    ::= { iShelfTrafficStatisticsEntry 23 }

-- ++++++++++++++++++++++++++++++++++++++++++++++++++++++++++++++++++++++++
--
-- iShelfTrafficTroubleStatsTable - 
--
-- ++++++++++++++++++++++++++++++++++++++++++++++++++++++++++++++++++++++++

iShelfTrafficTroubleStatsTable OBJECT-TYPE
    SYNTAX      SEQUENCE OF IShelfTrafficTroubleStatsEntry
    MAX-ACCESS  not-accessible
    STATUS      current
    DESCRIPTION ""
    ::= { iShelfTraffic 3 }

iShelfTrafficTroubleStatsEntry OBJECT-TYPE
    SYNTAX      IShelfTrafficTroubleStatsEntry
    MAX-ACCESS  not-accessible
    STATUS      current
    DESCRIPTION "Each row in this table indicates a specific Node and time period."
    INDEX       { iShelfTrafficTroubleStatsLocation,
                  iShelfTrafficTroubleStatsPeriod }
    ::= { iShelfTrafficTroubleStatsTable 1 }

IShelfTrafficTroubleStatsEntry ::=
    SEQUENCE {
        iShelfTrafficTroubleStatsLocation
            IShelfLocation,
        iShelfTrafficTroubleStatsPeriod
            INTEGER,
        iShelfTrafficTroubleStatsDateAndTime
            IShelfDateTime,
        iShelfTrafficTroubleStatsDuration
            INTEGER,
        iShelfTrafficTroubleStatsCauseOffHook
            Counter32,
        iShelfTrafficTroubleStatsCausePathLossIndication
            Counter32,
        iShelfTrafficTroubleStatsCausePathLossError
            Counter32,
        iShelfTrafficTroubleStatsCauseOnHookError
            Counter32,
        iShelfTrafficTroubleStatsCauseUnknownRelease
            Counter32,
        iShelfTrafficTroubleStatsCauseT303Release
            Counter32,
        iShelfTrafficTroubleStatsCauseT313Release
            Counter32,
        iShelfTrafficTroubleStatsCausePrimaryTsMismatch
            Counter32,
        iShelfTrafficTroubleStatsCauseSecondaryTsMismatch
            Counter32,
        iShelfTrafficTroubleStatsCauseIncompleteCompression
            Counter32,
        iShelfTrafficTroubleStatsCauseEquipmentFailOrRemove
            Counter32,
        iShelfTrafficTroubleStatsCauseEquipmentNoResponse
            Counter32,
        iShelfTrafficTroubleStatsCauseDs1Ds0AssignError
            Counter32,
        iShelfTrafficTroubleStatsCauseDs1Ds0DeleteError
            Counter32,
        iShelfTrafficTroubleStatsCausePermSignalState
            Counter32,
        iShelfTrafficTroubleStatsCauseT303Timeout
            Counter32,
        iShelfTrafficTroubleStatsCauseT308Timeout
            Counter32,
        iShelfTrafficTroubleStatsCauseT313Timeout
            Counter32,
        iShelfTrafficTroubleStatsCauseT303TimerError
            Counter32,
        iShelfTrafficTroubleStatsCauseT308TimerError
            Counter32,
        iShelfTrafficTroubleStatsCauseT313TimerError
            Counter32,
        iShelfTrafficTroubleStatsCauseCCTimeout
            Counter32,
        iShelfTrafficTroubleStatsCauseCCTimerError
            Counter32,
        iShelfTrafficTroubleStatsCauseCCTimeoutRelease
            Counter32,
        iShelfTrafficTroubleStatsCauseBMConnectTimeout
            Counter32,
        iShelfTrafficTroubleStatsCauseBMConnectTimerError
            Counter32,
        iShelfTrafficTroubleStatsCauseBMConnectMaxRetrans
            Counter32,
        iShelfTrafficTroubleStatsCauseBMReleaseTimeout
            Counter32,
        iShelfTrafficTroubleStatsCauseBMReleaseTimerError
            Counter32,
        iShelfTrafficTroubleStatsCauseBMReleaseMaxRetrans
            Counter32,
        iShelfTrafficTroubleStatsCauseBMConRelIdxError
            Counter32,
        iShelfTrafficTroubleStatsCauseBMTimerError
            Counter32,
        iShelfTrafficTroubleStatsTMCStatusEnquiries
            Counter32,
        iShelfTrafficTroubleStatsEOCLineStatusRequests
            Counter32,
        iShelfTrafficTroubleStatsDiscardedIframes
            Counter32,
        iShelfTrafficTroubleStatsActivePathLossIndication
            Counter32,
        iShelfTrafficTroubleStatsActivePathLossError
            Counter32,
        iShelfTrafficTroubleStatsActiveIncompleteCompression
            Counter32,
        iShelfTrafficTroubleStatsActiveOnHookError
            Counter32
    }

iShelfTrafficTroubleStatsLocation OBJECT-TYPE
    SYNTAX      IShelfLocation
    MAX-ACCESS  read-only
    STATUS      current
    DESCRIPTION "This object indicates the Node of the statistics"
    ::= { iShelfTrafficTroubleStatsEntry 1 }

iShelfTrafficTroubleStatsPeriod OBJECT-TYPE
    SYNTAX      INTEGER {
                    today(1),
                    lastHour(2),
                    yesterday(3),
                    cumulative(4)
                }
    MAX-ACCESS  read-only
    STATUS      current
    DESCRIPTION "This object indicates the period of the statistics"
    ::= { iShelfTrafficTroubleStatsEntry 2 }

iShelfTrafficTroubleStatsDateAndTime OBJECT-TYPE
    SYNTAX      IShelfDateTime
    MAX-ACCESS  read-only
    STATUS      current
    DESCRIPTION "This object indicates the end date and time for the period."
    ::= { iShelfTrafficTroubleStatsEntry 3 }

iShelfTrafficTroubleStatsDuration OBJECT-TYPE
    SYNTAX      INTEGER (0..3600)
    MAX-ACCESS  read-only
    STATUS      current
    DESCRIPTION "This object indicates the duration of the period in minutes."
    ::= { iShelfTrafficTroubleStatsEntry 4 }

iShelfTrafficTroubleStatsCauseOffHook OBJECT-TYPE
    SYNTAX      Counter32
    MAX-ACCESS  read-only
    STATUS      current
    DESCRIPTION ""
    ::= { iShelfTrafficTroubleStatsEntry 5 }

iShelfTrafficTroubleStatsCausePathLossIndication OBJECT-TYPE
    SYNTAX      Counter32
    MAX-ACCESS  read-only
    STATUS      current
    DESCRIPTION ""
    ::= { iShelfTrafficTroubleStatsEntry 6 }

iShelfTrafficTroubleStatsCausePathLossError OBJECT-TYPE
    SYNTAX      Counter32
    MAX-ACCESS  read-only
    STATUS      current
    DESCRIPTION ""
    ::= { iShelfTrafficTroubleStatsEntry 7 }

iShelfTrafficTroubleStatsCauseOnHookError OBJECT-TYPE
    SYNTAX      Counter32
    MAX-ACCESS  read-only
    STATUS      current
    DESCRIPTION ""
    ::= { iShelfTrafficTroubleStatsEntry 8 }

iShelfTrafficTroubleStatsCauseUnknownRelease OBJECT-TYPE
    SYNTAX      Counter32
    MAX-ACCESS  read-only
    STATUS      current
    DESCRIPTION ""
    ::= { iShelfTrafficTroubleStatsEntry 9 }

iShelfTrafficTroubleStatsCauseT303Release OBJECT-TYPE
    SYNTAX      Counter32
    MAX-ACCESS  read-only
    STATUS      current
    DESCRIPTION ""
    ::= { iShelfTrafficTroubleStatsEntry 10 }

iShelfTrafficTroubleStatsCauseT313Release OBJECT-TYPE
    SYNTAX      Counter32
    MAX-ACCESS  read-only
    STATUS      current
    DESCRIPTION ""
    ::= { iShelfTrafficTroubleStatsEntry 11 }

iShelfTrafficTroubleStatsCausePrimaryTsMismatch OBJECT-TYPE
    SYNTAX      Counter32
    MAX-ACCESS  read-only
    STATUS      current
    DESCRIPTION ""
    ::= { iShelfTrafficTroubleStatsEntry 12 }

iShelfTrafficTroubleStatsCauseSecondaryTsMismatch OBJECT-TYPE
    SYNTAX      Counter32
    MAX-ACCESS  read-only
    STATUS      current
    DESCRIPTION ""
    ::= { iShelfTrafficTroubleStatsEntry 13 }

iShelfTrafficTroubleStatsCauseIncompleteCompression OBJECT-TYPE
    SYNTAX      Counter32
    MAX-ACCESS  read-only
    STATUS      current
    DESCRIPTION ""
    ::= { iShelfTrafficTroubleStatsEntry 14 }

iShelfTrafficTroubleStatsCauseEquipmentFailOrRemove OBJECT-TYPE
    SYNTAX      Counter32
    MAX-ACCESS  read-only
    STATUS      current
    DESCRIPTION ""
    ::= { iShelfTrafficTroubleStatsEntry 15 }

iShelfTrafficTroubleStatsCauseEquipmentNoResponse OBJECT-TYPE
    SYNTAX      Counter32
    MAX-ACCESS  read-only
    STATUS      current
    DESCRIPTION ""
    ::= { iShelfTrafficTroubleStatsEntry 16 }

iShelfTrafficTroubleStatsCauseDs1Ds0AssignError OBJECT-TYPE
    SYNTAX      Counter32
    MAX-ACCESS  read-only
    STATUS      current
    DESCRIPTION ""
    ::= { iShelfTrafficTroubleStatsEntry 17 }

iShelfTrafficTroubleStatsCauseDs1Ds0DeleteError OBJECT-TYPE
    SYNTAX      Counter32
    MAX-ACCESS  read-only
    STATUS      current
    DESCRIPTION ""
    ::= { iShelfTrafficTroubleStatsEntry 18 }

iShelfTrafficTroubleStatsCausePermSignalState OBJECT-TYPE
    SYNTAX      Counter32
    MAX-ACCESS  read-only
    STATUS      current
    DESCRIPTION ""
    ::= { iShelfTrafficTroubleStatsEntry 19 }

iShelfTrafficTroubleStatsCauseT303Timeout OBJECT-TYPE
    SYNTAX      Counter32
    MAX-ACCESS  read-only
    STATUS      current
    DESCRIPTION ""
    ::= { iShelfTrafficTroubleStatsEntry 20 }

iShelfTrafficTroubleStatsCauseT308Timeout OBJECT-TYPE
    SYNTAX      Counter32
    MAX-ACCESS  read-only
    STATUS      current
    DESCRIPTION ""
    ::= { iShelfTrafficTroubleStatsEntry 21 }

iShelfTrafficTroubleStatsCauseT313Timeout OBJECT-TYPE
    SYNTAX      Counter32
    MAX-ACCESS  read-only
    STATUS      current
    DESCRIPTION ""
    ::= { iShelfTrafficTroubleStatsEntry 22 }

iShelfTrafficTroubleStatsCauseT303TimerError OBJECT-TYPE
    SYNTAX      Counter32
    MAX-ACCESS  read-only
    STATUS      current
    DESCRIPTION ""
    ::= { iShelfTrafficTroubleStatsEntry 23 }

iShelfTrafficTroubleStatsCauseT308TimerError OBJECT-TYPE
    SYNTAX      Counter32
    MAX-ACCESS  read-only
    STATUS      current
    DESCRIPTION ""
    ::= { iShelfTrafficTroubleStatsEntry 24 }

iShelfTrafficTroubleStatsCauseT313TimerError OBJECT-TYPE
    SYNTAX      Counter32
    MAX-ACCESS  read-only
    STATUS      current
    DESCRIPTION ""
    ::= { iShelfTrafficTroubleStatsEntry 25 }

iShelfTrafficTroubleStatsCauseCCTimeout OBJECT-TYPE
    SYNTAX      Counter32
    MAX-ACCESS  read-only
    STATUS      current
    DESCRIPTION ""
    ::= { iShelfTrafficTroubleStatsEntry 26 }

iShelfTrafficTroubleStatsCauseCCTimerError OBJECT-TYPE
    SYNTAX      Counter32
    MAX-ACCESS  read-only
    STATUS      current
    DESCRIPTION ""
    ::= { iShelfTrafficTroubleStatsEntry 27 }

iShelfTrafficTroubleStatsCauseCCTimeoutRelease OBJECT-TYPE
    SYNTAX      Counter32
    MAX-ACCESS  read-only
    STATUS      current
    DESCRIPTION ""
    ::= { iShelfTrafficTroubleStatsEntry 28 }

iShelfTrafficTroubleStatsCauseBMConnectTimeout OBJECT-TYPE
    SYNTAX      Counter32
    MAX-ACCESS  read-only
    STATUS      current
    DESCRIPTION ""
    ::= { iShelfTrafficTroubleStatsEntry 29 }

iShelfTrafficTroubleStatsCauseBMConnectTimerError OBJECT-TYPE
    SYNTAX      Counter32
    MAX-ACCESS  read-only
    STATUS      current
    DESCRIPTION ""
    ::= { iShelfTrafficTroubleStatsEntry 30 }

iShelfTrafficTroubleStatsCauseBMConnectMaxRetrans OBJECT-TYPE
    SYNTAX      Counter32
    MAX-ACCESS  read-only
    STATUS      current
    DESCRIPTION ""
    ::= { iShelfTrafficTroubleStatsEntry 31 }

iShelfTrafficTroubleStatsCauseBMReleaseTimeout OBJECT-TYPE
    SYNTAX      Counter32
    MAX-ACCESS  read-only
    STATUS      current
    DESCRIPTION ""
    ::= { iShelfTrafficTroubleStatsEntry 32 }

iShelfTrafficTroubleStatsCauseBMReleaseTimerError OBJECT-TYPE
    SYNTAX      Counter32
    MAX-ACCESS  read-only
    STATUS      current
    DESCRIPTION ""
    ::= { iShelfTrafficTroubleStatsEntry 33 }

iShelfTrafficTroubleStatsCauseBMReleaseMaxRetrans OBJECT-TYPE
    SYNTAX      Counter32
    MAX-ACCESS  read-only
    STATUS      current
    DESCRIPTION ""
    ::= { iShelfTrafficTroubleStatsEntry 34 }

iShelfTrafficTroubleStatsCauseBMConRelIdxError OBJECT-TYPE
    SYNTAX      Counter32
    MAX-ACCESS  read-only
    STATUS      current
    DESCRIPTION ""
    ::= { iShelfTrafficTroubleStatsEntry 35 }

iShelfTrafficTroubleStatsCauseBMTimerError OBJECT-TYPE
    SYNTAX      Counter32
    MAX-ACCESS  read-only
    STATUS      current
    DESCRIPTION ""
    ::= { iShelfTrafficTroubleStatsEntry 36 }

iShelfTrafficTroubleStatsTMCStatusEnquiries OBJECT-TYPE
    SYNTAX      Counter32
    MAX-ACCESS  read-only
    STATUS      current
    DESCRIPTION ""
    ::= { iShelfTrafficTroubleStatsEntry 37 }

iShelfTrafficTroubleStatsEOCLineStatusRequests OBJECT-TYPE
    SYNTAX      Counter32
    MAX-ACCESS  read-only
    STATUS      current
    DESCRIPTION ""
    ::= { iShelfTrafficTroubleStatsEntry 38 }

iShelfTrafficTroubleStatsDiscardedIframes OBJECT-TYPE
    SYNTAX      Counter32
    MAX-ACCESS  read-only
    STATUS      current
    DESCRIPTION ""
    ::= { iShelfTrafficTroubleStatsEntry 39 }

iShelfTrafficTroubleStatsActivePathLossIndication OBJECT-TYPE
    SYNTAX      Counter32
    MAX-ACCESS  read-only
    STATUS      current
    DESCRIPTION ""
    ::= { iShelfTrafficTroubleStatsEntry 40 }

iShelfTrafficTroubleStatsActivePathLossError OBJECT-TYPE
    SYNTAX      Counter32
    MAX-ACCESS  read-only
    STATUS      current
    DESCRIPTION ""
    ::= { iShelfTrafficTroubleStatsEntry 41 }

iShelfTrafficTroubleStatsActiveIncompleteCompression OBJECT-TYPE
    SYNTAX      Counter32
    MAX-ACCESS  read-only
    STATUS      current
    DESCRIPTION ""
    ::= { iShelfTrafficTroubleStatsEntry 42 }

iShelfTrafficTroubleStatsActiveOnHookError OBJECT-TYPE
    SYNTAX      Counter32
    MAX-ACCESS  read-only
    STATUS      current
    DESCRIPTION ""
    ::= { iShelfTrafficTroubleStatsEntry 43 }

-- ++++++++++++++++++++++++++++++++++++++++++++++++++++++++++++++++++++++++
--
-- iShelfTrafficGpsStatsTable - 
--
-- ++++++++++++++++++++++++++++++++++++++++++++++++++++++++++++++++++++++++

iShelfTrafficGpsStatsTable OBJECT-TYPE
    SYNTAX      SEQUENCE OF IShelfTrafficGpsStatsEntry
    MAX-ACCESS  not-accessible
    STATUS      current
    DESCRIPTION ""
    ::= { iShelfTraffic 4 }

iShelfTrafficGpsStatsEntry OBJECT-TYPE
    SYNTAX      IShelfTrafficGpsStatsEntry
    MAX-ACCESS  not-accessible
    STATUS      current
    DESCRIPTION "Each row in this table indicates a specific Node and time period."
    INDEX       { iShelfTrafficGpsStatsLocation,
                  iShelfTrafficGpsStatsPeriod }
    ::= { iShelfTrafficGpsStatsTable 1 }

IShelfTrafficGpsStatsEntry ::=
    SEQUENCE {
        iShelfTrafficGpsStatsLocation
            IShelfLocation,
        iShelfTrafficGpsStatsPeriod
            INTEGER,
        iShelfTrafficGpsStatsDateAndTime
            IShelfDateTime,
        iShelfTrafficGpsStatsDuration
            INTEGER,
        iShelfTrafficGpsStatsResponseTimeout
            Counter32,
        iShelfTrafficGpsStatsCallReleaseFailure
            Counter32,
        iShelfTrafficGpsStatsCallConnectFailure
            Counter32,
        iShelfTrafficGpsStatsCallOnHookError
            Counter32,
        iShelfTrafficGpsStatsCallPathLossError
            Counter32,
        iShelfTrafficGpsStatsCallCompressionFailure
            Counter32
    }

iShelfTrafficGpsStatsLocation OBJECT-TYPE
    SYNTAX      IShelfLocation
    MAX-ACCESS  read-only
    STATUS      current
    DESCRIPTION "This object identifies the node for the statistics."
    ::= { iShelfTrafficGpsStatsEntry 1 }

iShelfTrafficGpsStatsPeriod OBJECT-TYPE
    SYNTAX      INTEGER {
                    today(1),
                    lastHour(2),
                    yesterday(3),
                    cumulative(4)
                }
    MAX-ACCESS  read-only
    STATUS      current
    DESCRIPTION "This object identifies the time period for the statistics."
    ::= { iShelfTrafficGpsStatsEntry 2 }

iShelfTrafficGpsStatsDateAndTime OBJECT-TYPE
    SYNTAX      IShelfDateTime
    MAX-ACCESS  read-only
    STATUS      current
    DESCRIPTION
        "This object identifies the end date and time for the
         statistics."
    ::= { iShelfTrafficGpsStatsEntry 3 }

iShelfTrafficGpsStatsDuration OBJECT-TYPE
    SYNTAX      INTEGER (0..3600)
    MAX-ACCESS  read-only
    STATUS      current
    DESCRIPTION "This object identifies the duration of the period in minutes."
    ::= { iShelfTrafficGpsStatsEntry 4 }

iShelfTrafficGpsStatsResponseTimeout OBJECT-TYPE
    SYNTAX      Counter32
    MAX-ACCESS  read-only
    STATUS      current
    DESCRIPTION ""
    ::= { iShelfTrafficGpsStatsEntry 5 }

iShelfTrafficGpsStatsCallReleaseFailure OBJECT-TYPE
    SYNTAX      Counter32
    MAX-ACCESS  read-only
    STATUS      current
    DESCRIPTION ""
    ::= { iShelfTrafficGpsStatsEntry 6 }

iShelfTrafficGpsStatsCallConnectFailure OBJECT-TYPE
    SYNTAX      Counter32
    MAX-ACCESS  read-only
    STATUS      current
    DESCRIPTION ""
    ::= { iShelfTrafficGpsStatsEntry 7 }

iShelfTrafficGpsStatsCallOnHookError OBJECT-TYPE
    SYNTAX      Counter32
    MAX-ACCESS  read-only
    STATUS      current
    DESCRIPTION ""
    ::= { iShelfTrafficGpsStatsEntry 8 }

iShelfTrafficGpsStatsCallPathLossError OBJECT-TYPE
    SYNTAX      Counter32
    MAX-ACCESS  read-only
    STATUS      current
    DESCRIPTION ""
    ::= { iShelfTrafficGpsStatsEntry 9 }

iShelfTrafficGpsStatsCallCompressionFailure OBJECT-TYPE
    SYNTAX      Counter32
    MAX-ACCESS  read-only
    STATUS      current
    DESCRIPTION ""
    ::= { iShelfTrafficGpsStatsEntry 10 }

-- ++++++++++++++++++++++++++++++++++++++++++++++++++++++++++++++++++++++++
--
-- iShelfIdlcLapdPmTable - 
--
-- ++++++++++++++++++++++++++++++++++++++++++++++++++++++++++++++++++++++++

iShelfIdlcLapdPmTable OBJECT-TYPE
    SYNTAX      SEQUENCE OF IShelfIdlcLapdPmEntry
    MAX-ACCESS  not-accessible
    STATUS      current
    DESCRIPTION ""
    ::= { iShelfIdlcPm 1 }

iShelfIdlcLapdPmEntry OBJECT-TYPE
    SYNTAX      IShelfIdlcLapdPmEntry
    MAX-ACCESS  not-accessible
    STATUS      current
    DESCRIPTION "Each row in this table indicates a specific LAPD channel."
    INDEX       { iShelfIdlcLapdPmInterfaceId,
                  iShelfIdlcLapdPmPathLocation,
                  iShelfIdlcLapdPmProtocolChannel }
    ::= { iShelfIdlcLapdPmTable 1 }

IShelfIdlcLapdPmEntry ::=
    SEQUENCE {
        iShelfIdlcLapdPmInterfaceId
            INTEGER,
        iShelfIdlcLapdPmPathLocation
            INTEGER,
        iShelfIdlcLapdPmProtocolChannel
            INTEGER,
        iShelfIdlcLapdPmReset
            TruthValue,
        iShelfIdlcLapdPmInLayer2
            Counter32,
        iShelfIdlcLapdPmOutLayer2
            Counter32,
        iShelfIdlcLapdPmInLayer3
            Counter32,
        iShelfIdlcLapdPmOutLayer3
            Counter32,
        iShelfIdlcLapdPmInIFrame
            Counter32,
        iShelfIdlcLapdPmOutIFrame
            Counter32,
        iShelfIdlcLapdPmNumEstablish
            Counter32,
        iShelfIdlcLapdPmLastEstablish
            Unsigned32,
        iShelfIdlcLapdPmAvgIQueue
            Counter32,
        iShelfIdlcLapdPmMaxIQueue
            Counter32,
        iShelfIdlcLapdPmCurrIQueue
            Counter32,
        iShelfIdlcLapdPmAvgRetry
            Counter32,
        iShelfIdlcLapdPmMaxRetry
            Counter32,
        iShelfIdlcLapdPmNumErrorA
            Counter32,
        iShelfIdlcLapdPmNumErrorB
            Counter32,
        iShelfIdlcLapdPmNumErrorC
            Counter32,
        iShelfIdlcLapdPmNumErrorD
            Counter32,
        iShelfIdlcLapdPmNumErrorE
            Counter32,
        iShelfIdlcLapdPmNumErrorF
            Counter32,
        iShelfIdlcLapdPmNumErrorG
            Counter32,
        iShelfIdlcLapdPmNumErrorH
            Counter32,
        iShelfIdlcLapdPmNumErrorI
            Counter32,
        iShelfIdlcLapdPmNumErrorJ
            Counter32,
        iShelfIdlcLapdPmNumErrorK
            Counter32,
        iShelfIdlcLapdPmNumErrorL
            Counter32,
        iShelfIdlcLapdPmNumErrorM
            Counter32,
        iShelfIdlcLapdPmNumErrorN
            Counter32,
        iShelfIdlcLapdPmNumErrorO
            Counter32
    }

iShelfIdlcLapdPmInterfaceId OBJECT-TYPE
    SYNTAX      INTEGER (1..4)
    MAX-ACCESS  read-only
    STATUS      current
    DESCRIPTION "This object indicates which IDLC Interface group."
    ::= { iShelfIdlcLapdPmEntry 1 }

iShelfIdlcLapdPmPathLocation OBJECT-TYPE
    SYNTAX      INTEGER {
                    primary(1),
                    secondary(2)
                }
    MAX-ACCESS  read-only
    STATUS      current
    DESCRIPTION
        "This object indicates if the associated data relates
         to the primary or secondary link."
    ::= { iShelfIdlcLapdPmEntry 2 }

iShelfIdlcLapdPmProtocolChannel OBJECT-TYPE
    SYNTAX      INTEGER {
                    tmcSapi0Tei0(1),
                    tmcSapi1Tei0(2),
                    eocSapi1Tei0(3),
                    eocSapi1Tei4(4)
                }
    MAX-ACCESS  read-only
    STATUS      current
    DESCRIPTION
        "This object indicates the channel for the statistics.
         It indicates if it is a TMC or EOC link and if it is the COM or PPS
         channel (based on the Sapi/Tei)."
    ::= { iShelfIdlcLapdPmEntry 3 }

iShelfIdlcLapdPmReset OBJECT-TYPE
    SYNTAX      TruthValue
    MAX-ACCESS  read-write
    STATUS      current
    DESCRIPTION
        "This object when set to true will result in setting all
         counts to zero."
    ::= { iShelfIdlcLapdPmEntry 4 }

iShelfIdlcLapdPmInLayer2 OBJECT-TYPE
    SYNTAX      Counter32
    MAX-ACCESS  read-only
    STATUS      current
    DESCRIPTION "The number of messages received over layer 2."
    ::= { iShelfIdlcLapdPmEntry 5 }

iShelfIdlcLapdPmOutLayer2 OBJECT-TYPE
    SYNTAX      Counter32
    MAX-ACCESS  read-only
    STATUS      current
    DESCRIPTION "The number of messages sent over layer 2."
    ::= { iShelfIdlcLapdPmEntry 6 }

iShelfIdlcLapdPmInLayer3 OBJECT-TYPE
    SYNTAX      Counter32
    MAX-ACCESS  read-only
    STATUS      current
    DESCRIPTION "The number of messages received over layer 3."
    ::= { iShelfIdlcLapdPmEntry 7 }

iShelfIdlcLapdPmOutLayer3 OBJECT-TYPE
    SYNTAX      Counter32
    MAX-ACCESS  read-only
    STATUS      current
    DESCRIPTION "The number of messages sent over layer 3."
    ::= { iShelfIdlcLapdPmEntry 8 }

iShelfIdlcLapdPmInIFrame OBJECT-TYPE
    SYNTAX      Counter32
    MAX-ACCESS  read-only
    STATUS      current
    DESCRIPTION "Number of LAPD Info Frames received."
    ::= { iShelfIdlcLapdPmEntry 9 }

iShelfIdlcLapdPmOutIFrame OBJECT-TYPE
    SYNTAX      Counter32
    MAX-ACCESS  read-only
    STATUS      current
    DESCRIPTION "Number of LAPD Info Frames transmitted."
    ::= { iShelfIdlcLapdPmEntry 10 }

iShelfIdlcLapdPmNumEstablish OBJECT-TYPE
    SYNTAX      Counter32
    MAX-ACCESS  read-only
    STATUS      current
    DESCRIPTION
        "Number of times a data link was estabilished between
         the system and the switch since the LAPD statistics were last reset."
    ::= { iShelfIdlcLapdPmEntry 11 }

iShelfIdlcLapdPmLastEstablish OBJECT-TYPE
    SYNTAX      Unsigned32
    MAX-ACCESS  read-only
    STATUS      current
    DESCRIPTION
        "The number of ticks since the most recent data link was
         established."
    ::= { iShelfIdlcLapdPmEntry 12 }

iShelfIdlcLapdPmAvgIQueue OBJECT-TYPE
    SYNTAX      Counter32
    MAX-ACCESS  read-only
    STATUS      current
    DESCRIPTION
        "This object indicates the average number of messages
         waiting in queue for transmission over the data link."
    ::= { iShelfIdlcLapdPmEntry 13 }

iShelfIdlcLapdPmMaxIQueue OBJECT-TYPE
    SYNTAX      Counter32
    MAX-ACCESS  read-only
    STATUS      current
    DESCRIPTION
        "This object indicates the maximum number of messages
         waiting in queue for transmission over the data link."
    ::= { iShelfIdlcLapdPmEntry 14 }

iShelfIdlcLapdPmCurrIQueue OBJECT-TYPE
    SYNTAX      Counter32
    MAX-ACCESS  read-only
    STATUS      current
    DESCRIPTION
        "This object indicates the current number of messages
         waiting in queue for transmission over the data link."
    ::= { iShelfIdlcLapdPmEntry 15 }

iShelfIdlcLapdPmAvgRetry OBJECT-TYPE
    SYNTAX      Counter32
    MAX-ACCESS  read-only
    STATUS      current
    DESCRIPTION
        "This object indicates the average number of times
         transmissions were retried."
    ::= { iShelfIdlcLapdPmEntry 16 }

iShelfIdlcLapdPmMaxRetry OBJECT-TYPE
    SYNTAX      Counter32
    MAX-ACCESS  read-only
    STATUS      current
    DESCRIPTION
        "This object indicates the maximum number of times
         transmissions were retried."
    ::= { iShelfIdlcLapdPmEntry 17 }

iShelfIdlcLapdPmNumErrorA OBJECT-TYPE
    SYNTAX      Counter32
    MAX-ACCESS  read-only
    STATUS      current
    DESCRIPTION
        "This object indicates the number of Receipt of unsolicited
         responses - Supervisory"
    ::= { iShelfIdlcLapdPmEntry 18 }

iShelfIdlcLapdPmNumErrorB OBJECT-TYPE
    SYNTAX      Counter32
    MAX-ACCESS  read-only
    STATUS      current
    DESCRIPTION
        "This object indicates the number of Receipt of unsolicited
         responses - DM (F=1)"
    ::= { iShelfIdlcLapdPmEntry 19 }

iShelfIdlcLapdPmNumErrorC OBJECT-TYPE
    SYNTAX      Counter32
    MAX-ACCESS  read-only
    STATUS      current
    DESCRIPTION
        "This object indicates the number of Receipt of unsolicited
         responses - UA (F=1)"
    ::= { iShelfIdlcLapdPmEntry 20 }

iShelfIdlcLapdPmNumErrorD OBJECT-TYPE
    SYNTAX      Counter32
    MAX-ACCESS  read-only
    STATUS      current
    DESCRIPTION
        "This object indicates the number of Receipt of unsolicited
         responses - UA (F=0)"
    ::= { iShelfIdlcLapdPmEntry 21 }

iShelfIdlcLapdPmNumErrorE OBJECT-TYPE
    SYNTAX      Counter32
    MAX-ACCESS  read-only
    STATUS      current
    DESCRIPTION
        "This object indicates the number of Receipt of unsolicited
         responses - DM (F=0)"
    ::= { iShelfIdlcLapdPmEntry 22 }

iShelfIdlcLapdPmNumErrorF OBJECT-TYPE
    SYNTAX      Counter32
    MAX-ACCESS  read-only
    STATUS      current
    DESCRIPTION
        "This object indicates the number of Peer initiated
         re-establishment - SABME"
    ::= { iShelfIdlcLapdPmEntry 23 }

iShelfIdlcLapdPmNumErrorG OBJECT-TYPE
    SYNTAX      Counter32
    MAX-ACCESS  read-only
    STATUS      current
    DESCRIPTION
        "This object indicates the number of Unsuccessful
         retransmission (N200 times) - SABME"
    ::= { iShelfIdlcLapdPmEntry 24 }

iShelfIdlcLapdPmNumErrorH OBJECT-TYPE
    SYNTAX      Counter32
    MAX-ACCESS  read-only
    STATUS      current
    DESCRIPTION
        "This object indicates the number of Unsuccessful
         retransmission (N200 times) - DISC"
    ::= { iShelfIdlcLapdPmEntry 25 }

iShelfIdlcLapdPmNumErrorI OBJECT-TYPE
    SYNTAX      Counter32
    MAX-ACCESS  read-only
    STATUS      current
    DESCRIPTION
        "This object indicates the number of Unsuccessful
         retransmission (N200 times) - Status Enquiry"
    ::= { iShelfIdlcLapdPmEntry 26 }

iShelfIdlcLapdPmNumErrorJ OBJECT-TYPE
    SYNTAX      Counter32
    MAX-ACCESS  read-only
    STATUS      current
    DESCRIPTION "This object indicates the number of N(R) Error"
    ::= { iShelfIdlcLapdPmEntry 27 }

iShelfIdlcLapdPmNumErrorK OBJECT-TYPE
    SYNTAX      Counter32
    MAX-ACCESS  read-only
    STATUS      current
    DESCRIPTION
        "This object indicates the number of Receipt of
         FRMR response"
    ::= { iShelfIdlcLapdPmEntry 28 }

iShelfIdlcLapdPmNumErrorL OBJECT-TYPE
    SYNTAX      Counter32
    MAX-ACCESS  read-only
    STATUS      current
    DESCRIPTION
        "This object indicates the number of Receipt of
         non-implemented frame"
    ::= { iShelfIdlcLapdPmEntry 29 }

iShelfIdlcLapdPmNumErrorM OBJECT-TYPE
    SYNTAX      Counter32
    MAX-ACCESS  read-only
    STATUS      current
    DESCRIPTION
        "This object indicates the number of Receipt of
         I-field not permitted"
    ::= { iShelfIdlcLapdPmEntry 30 }

iShelfIdlcLapdPmNumErrorN OBJECT-TYPE
    SYNTAX      Counter32
    MAX-ACCESS  read-only
    STATUS      current
    DESCRIPTION
        "This object indicates the number of Receipt of
         Frame with wrong size"
    ::= { iShelfIdlcLapdPmEntry 31 }

iShelfIdlcLapdPmNumErrorO OBJECT-TYPE
    SYNTAX      Counter32
    MAX-ACCESS  read-only
    STATUS      current
    DESCRIPTION "This object indicates the number of N201 Error"
    ::= { iShelfIdlcLapdPmEntry 32 }

-- ++++++++++++++++++++++++++++++++++++++++++++++++++++++++++++++++++++++++
--
-- iShelfOntPonNearCurrent15Table
--
-- ++++++++++++++++++++++++++++++++++++++++++++++++++++++++++++++++++++++++

-- %CLICMDPREFIX ont:pm:pon
-- %CLICMDABBR c15neartable
iShelfOntPonNearCurrent15Table OBJECT-TYPE
    SYNTAX      SEQUENCE OF IShelfOntPonNearCurrent15Entry
    MAX-ACCESS  not-accessible
    STATUS      current
    DESCRIPTION
        "This table contains the Near-End PON performance data
         on a per ONT basis for the current 15 minute interval.

         This is calculated and maintained on the OLT based on
         the following counters maintained by the OLT hardware:

         1) BIP8 Errors - Bit Interleaved Parity
         2) Missing Errors - Cell from ONT was missed in required
            timeslot.

         The following PM values will be computed from the above
         counters. These values will be computed each second.

         1) BESs - BIP8 Errored Seconds. This is defined as any
            second containing a non-zero BIP8 error count.
         2) MESs - Missing Errored Seconds. This is defined as any
            second containing a non-zero Missing Errors count.
         3) SESs - Severely Errored Seconds. This is defined as any
            second containing a non-zero BIP8 error count exceeding
            a specific threshold (which is TBD), or a second
            containing a pegged Missing Errors Counter. A pegged
            Missing Errors counter is computed as follows. Each ONT
            is given a certain number of upstream grants. By this,
            the software can compute the total number of expected
            cells per second from that ONT. If the Missing Errors
            counter equals this value it is considered to be pegged.
         4) UASs - Unavailable Seconds. This is defined as N
            consecutive SES. Once unavailable, N consecutive seconds
            must pass without SES before coming available again. The
            value of N is TBD.

         Rows in this table are automatically created when the ONT
         is provisioned."
    ::= { iShelfOntPm 1 }

iShelfOntPonNearCurrent15Entry OBJECT-TYPE
    SYNTAX      IShelfOntPonNearCurrent15Entry
    MAX-ACCESS  not-accessible
    STATUS      current
    DESCRIPTION
        "Each entry corresponds to the near-end ONT performance
         data for the current 15 minute interval."
    INDEX       { iShelfOntPonNearCurrent15LogicalId }
    ::= { iShelfOntPonNearCurrent15Table 1 }

IShelfOntPonNearCurrent15Entry ::=
    SEQUENCE {
        iShelfOntPonNearCurrent15LogicalId
            IShelfOntLogicalId,
        iShelfOntPonNearCurrent15Bip8
            Counter32,
        iShelfOntPonNearCurrent15Missing
            Counter32,
        iShelfOntPonNearCurrent15BESs
            Gauge32,
        iShelfOntPonNearCurrent15MESs
            Gauge32,
        iShelfOntPonNearCurrent15SESs
            Gauge32,
        iShelfOntPonNearCurrent15UASs
            Gauge32,
        iShelfOntPonNearCurrent15ValidData
            IShelfPerfInvalidFlag,
        iShelfOntPonNearCurrent15ThresholdCrossingPointer
            IShelfThresholdCrossingPointer
    }

iShelfOntPonNearCurrent15LogicalId OBJECT-TYPE
    SYNTAX      IShelfOntLogicalId
    MAX-ACCESS  read-only
    STATUS      current
    DESCRIPTION "This object identifies the logical ID of the ONT."
    ::= { iShelfOntPonNearCurrent15Entry 1 }

-- %CLICOLLABEL Bip8Errs
iShelfOntPonNearCurrent15Bip8 OBJECT-TYPE
    SYNTAX      Counter32
    MAX-ACCESS  read-only
    STATUS      current
    DESCRIPTION
        "This object contains the number of BIP8 errors for the
         ONT in the current interval."
    ::= { iShelfOntPonNearCurrent15Entry 2 }

-- %CLICOLLABEL Missing
iShelfOntPonNearCurrent15Missing OBJECT-TYPE
    SYNTAX      Counter32
    MAX-ACCESS  read-only
    STATUS      current
    DESCRIPTION
        "This object contains the number of Missing errors for
         the ONT in the current interval."
    ::= { iShelfOntPonNearCurrent15Entry 3 }

-- %CLICOLLABEL BipES
-- %CLIWIDTH 5
iShelfOntPonNearCurrent15BESs OBJECT-TYPE
    SYNTAX      Gauge32
    MAX-ACCESS  read-only
    STATUS      current
    DESCRIPTION
        "This object contains the number BIP8 Errored Seconds
         for the ONT in the current interval."
    ::= { iShelfOntPonNearCurrent15Entry 4 }

-- %CLICOLLABEL MisES
-- %CLIWIDTH 5
iShelfOntPonNearCurrent15MESs OBJECT-TYPE
    SYNTAX      Gauge32
    MAX-ACCESS  read-only
    STATUS      current
    DESCRIPTION
        "This object contains the number of Missing Errored
         Seconds for the ONT in the current interval."
    ::= { iShelfOntPonNearCurrent15Entry 5 }

-- %PMPARAMTYPE ES
-- %CLICOLLABEL SES
-- %CLIWIDTH 5
iShelfOntPonNearCurrent15SESs OBJECT-TYPE
    SYNTAX      Gauge32
    MAX-ACCESS  read-only
    STATUS      current
    DESCRIPTION
        "This object contains the number of Severely Errored
         Seconds for the ONT in the current interval."
    ::= { iShelfOntPonNearCurrent15Entry 6 }

-- %PMPARAMTYPE US
-- %CLICOLLABEL UAS
-- %CLIWIDTH 5
iShelfOntPonNearCurrent15UASs OBJECT-TYPE
    SYNTAX      Gauge32
    MAX-ACCESS  read-only
    STATUS      current
    DESCRIPTION
        "This object contains the number of Unavailable Seconds
         for the ONT in the current interval."
    ::= { iShelfOntPonNearCurrent15Entry 7 }

-- %CLIWIDTH 5
iShelfOntPonNearCurrent15ValidData OBJECT-TYPE
    SYNTAX      IShelfPerfInvalidFlag
    MAX-ACCESS  read-only
    STATUS      current
    DESCRIPTION
        "This object indicates if the data for this interval
         is valid."
    ::= { iShelfOntPonNearCurrent15Entry 8 }

iShelfOntPonNearCurrent15ThresholdCrossingPointer OBJECT-TYPE
    SYNTAX      IShelfThresholdCrossingPointer
    MAX-ACCESS  read-write
    STATUS      current
    DESCRIPTION
        "This object points to the threshold crossing entry
         (in IShelfThresholdCrossingTable). A value of zero
         indicates threshold crossing are not being generated."
    DEFVAL      { 0 }
    ::= { iShelfOntPonNearCurrent15Entry 9 }

-- ++++++++++++++++++++++++++++++++++++++++++++++++++++++++++++++++++++++++
--
-- iShelfOntPonNearInterval15Table
--
-- ++++++++++++++++++++++++++++++++++++++++++++++++++++++++++++++++++++++++

-- %CLICMDPREFIX ont:pm:pon
-- %CLICMDABBR i15neartable
iShelfOntPonNearInterval15Table OBJECT-TYPE
    SYNTAX      SEQUENCE OF IShelfOntPonNearInterval15Entry
    MAX-ACCESS  not-accessible
    STATUS      current
    DESCRIPTION
        "This table contains the Near-End PON performance data
         on a per ONT basis for the previous 15 minute intervals.

         Rows in this table are automatically created when the ONT
         is provisioned."
    ::= { iShelfOntPm 2 }

iShelfOntPonNearInterval15Entry OBJECT-TYPE
    SYNTAX      IShelfOntPonNearInterval15Entry
    MAX-ACCESS  not-accessible
    STATUS      current
    DESCRIPTION
        "Each entry corresponds to the near-end ONT performance
         data for a previous 15 minute interval."
    INDEX       { iShelfOntPonNearInterval15LogicalId,
                  iShelfOntPonNearInterval15Number }
    ::= { iShelfOntPonNearInterval15Table 1 }

IShelfOntPonNearInterval15Entry ::=
    SEQUENCE {
        iShelfOntPonNearInterval15LogicalId
            IShelfOntLogicalId,
        iShelfOntPonNearInterval15Number
            INTEGER,
        iShelfOntPonNearInterval15Bip8
            Counter32,
        iShelfOntPonNearInterval15Missing
            Counter32,
        iShelfOntPonNearInterval15BESs
            Gauge32,
        iShelfOntPonNearInterval15MESs
            Gauge32,
        iShelfOntPonNearInterval15SESs
            Gauge32,
        iShelfOntPonNearInterval15UASs
            Gauge32,
        iShelfOntPonNearInterval15ValidData
            IShelfPerfInvalidFlag
    }

iShelfOntPonNearInterval15LogicalId OBJECT-TYPE
    SYNTAX      IShelfOntLogicalId
    MAX-ACCESS  read-only
    STATUS      current
    DESCRIPTION "This object identifies the logical ID of the ONT."
    ::= { iShelfOntPonNearInterval15Entry 1 }

-- %CLICOLLABEL Int
-- %CLIWIDTH 2
iShelfOntPonNearInterval15Number OBJECT-TYPE
    SYNTAX      INTEGER(1..32)
    MAX-ACCESS  read-only
    STATUS      current
    DESCRIPTION
        "This object identifies the interval for which this set
         of statistics is available. The interval identified
         by 1 is the most recently completed 15 minute interval."
    ::= { iShelfOntPonNearInterval15Entry 2 }

-- %CLICOLLABEL Bip8Errs
iShelfOntPonNearInterval15Bip8 OBJECT-TYPE
    SYNTAX      Counter32
    MAX-ACCESS  read-only
    STATUS      current
    DESCRIPTION
        "This object contains the number of BIP8 errors for the
         ONT in the current interval."
    ::= { iShelfOntPonNearInterval15Entry 3 }

-- %CLICOLLABEL Missing
iShelfOntPonNearInterval15Missing OBJECT-TYPE
    SYNTAX      Counter32
    MAX-ACCESS  read-only
    STATUS      current
    DESCRIPTION
        "This object contains the number of Missing errors for
         the ONT in the current interval."
    ::= { iShelfOntPonNearInterval15Entry 4 }

-- %CLICOLLABEL BipES
-- %CLIWIDTH 5
iShelfOntPonNearInterval15BESs OBJECT-TYPE
    SYNTAX      Gauge32
    MAX-ACCESS  read-only
    STATUS      current
    DESCRIPTION
        "This object contains the number BIP8 Errored Seconds
         for the ONT in the current interval."
    ::= { iShelfOntPonNearInterval15Entry 5 }

-- %CLICOLLABEL MisES
-- %CLIWIDTH 5
iShelfOntPonNearInterval15MESs OBJECT-TYPE
    SYNTAX      Gauge32
    MAX-ACCESS  read-only
    STATUS      current
    DESCRIPTION
        "This object contains the number of Missing Errored
         Seconds for the ONT in the current interval."
    ::= { iShelfOntPonNearInterval15Entry 6 }

-- %CLICOLLABEL SES
-- %CLIWIDTH 5
iShelfOntPonNearInterval15SESs OBJECT-TYPE
    SYNTAX      Gauge32
    MAX-ACCESS  read-only
    STATUS      current
    DESCRIPTION
        "This object contains the number of Severely Errored
         Seconds for the ONT in the current interval."
    ::= { iShelfOntPonNearInterval15Entry 7 }

-- %CLICOLLABEL UAS
-- %CLIWIDTH 5
iShelfOntPonNearInterval15UASs OBJECT-TYPE
    SYNTAX      Gauge32
    MAX-ACCESS  read-only
    STATUS      current
    DESCRIPTION
        "This object contains the number of Unavailable Seconds
         for the ONT in the current interval."
    ::= { iShelfOntPonNearInterval15Entry 8 }

-- %CLIWIDTH 5
iShelfOntPonNearInterval15ValidData OBJECT-TYPE
    SYNTAX      IShelfPerfInvalidFlag
    MAX-ACCESS  read-only
    STATUS      current
    DESCRIPTION
        "This object indicates if the data for this interval
         is valid."
    ::= { iShelfOntPonNearInterval15Entry 9 }

-- ++++++++++++++++++++++++++++++++++++++++++++++++++++++++++++++++++++++++
--
-- iShelfOntPonNearCurrent24Table
--
-- ++++++++++++++++++++++++++++++++++++++++++++++++++++++++++++++++++++++++

-- %CLICMDPREFIX ont:pm:pon
-- %CLICMDABBR c24neartable
iShelfOntPonNearCurrent24Table OBJECT-TYPE
    SYNTAX      SEQUENCE OF IShelfOntPonNearCurrent24Entry
    MAX-ACCESS  not-accessible
    STATUS      current
    DESCRIPTION
        "This table contains the Near-End PON performance data
         on a per ONT basis for the current 24 hour interval.

         Rows in this table are automatically created when the ONT
         is provisioned."
    ::= { iShelfOntPm 3 }

iShelfOntPonNearCurrent24Entry OBJECT-TYPE
    SYNTAX      IShelfOntPonNearCurrent24Entry
    MAX-ACCESS  not-accessible
    STATUS      current
    DESCRIPTION
        "Each entry corresponds to the near-end ONT performance
         data for the current 24 hour interval."
    INDEX       { iShelfOntPonNearCurrent24LogicalId }
    ::= { iShelfOntPonNearCurrent24Table 1 }

IShelfOntPonNearCurrent24Entry ::=
    SEQUENCE {
        iShelfOntPonNearCurrent24LogicalId
            IShelfOntLogicalId,
        iShelfOntPonNearCurrent24Bip8
            Counter32,
        iShelfOntPonNearCurrent24Missing
            Counter32,
        iShelfOntPonNearCurrent24BESs
            Gauge32,
        iShelfOntPonNearCurrent24MESs
            Gauge32,
        iShelfOntPonNearCurrent24SESs
            Gauge32,
        iShelfOntPonNearCurrent24UASs
            Gauge32,
        iShelfOntPonNearCurrent24ValidData
            IShelfPerfInvalidFlag,
        iShelfOntPonNearCurrent24ThresholdCrossingPointer
            IShelfThresholdCrossingPointer
    }

iShelfOntPonNearCurrent24LogicalId OBJECT-TYPE
    SYNTAX      IShelfOntLogicalId
    MAX-ACCESS  read-only
    STATUS      current
    DESCRIPTION "This object identifies the logical ID of the ONT."
    ::= { iShelfOntPonNearCurrent24Entry 1 }

-- %CLICOLLABEL Bip8Errs
iShelfOntPonNearCurrent24Bip8 OBJECT-TYPE
    SYNTAX      Counter32
    MAX-ACCESS  read-only
    STATUS      current
    DESCRIPTION
        "This object contains the number of BIP8 errors for the
         ONT in the current interval."
    ::= { iShelfOntPonNearCurrent24Entry 2 }

-- %CLICOLLABEL Missing
iShelfOntPonNearCurrent24Missing OBJECT-TYPE
    SYNTAX      Counter32
    MAX-ACCESS  read-only
    STATUS      current
    DESCRIPTION
        "This object contains the number of Missing errors for
         the ONT in the current interval."
    ::= { iShelfOntPonNearCurrent24Entry 3 }

-- %CLICOLLABEL BipES
-- %CLIWIDTH 5
iShelfOntPonNearCurrent24BESs OBJECT-TYPE
    SYNTAX      Gauge32
    MAX-ACCESS  read-only
    STATUS      current
    DESCRIPTION
        "This object contains the number BIP8 Errored Seconds
         for the ONT in the current interval."
    ::= { iShelfOntPonNearCurrent24Entry 4 }

-- %CLICOLLABEL MisES
-- %CLIWIDTH 5
iShelfOntPonNearCurrent24MESs OBJECT-TYPE
    SYNTAX      Gauge32
    MAX-ACCESS  read-only
    STATUS      current
    DESCRIPTION
        "This object contains the number of Missing Errored
         Seconds for the ONT in the current interval."
    ::= { iShelfOntPonNearCurrent24Entry 5 }

-- %CLICOLLABEL SES
-- %CLIWIDTH 5
iShelfOntPonNearCurrent24SESs OBJECT-TYPE
    SYNTAX      Gauge32
    MAX-ACCESS  read-only
    STATUS      current
    DESCRIPTION
        "This object contains the number of Severely Errored
         Seconds for the ONT in the current interval."
    ::= { iShelfOntPonNearCurrent24Entry 6 }

-- %CLICOLLABEL UAS
-- %CLIWIDTH 5
iShelfOntPonNearCurrent24UASs OBJECT-TYPE
    SYNTAX      Gauge32
    MAX-ACCESS  read-only
    STATUS      current
    DESCRIPTION
        "This object contains the number of Unavailable Seconds
         for the ONT in the current interval."
    ::= { iShelfOntPonNearCurrent24Entry 7 }

-- %CLIWIDTH 5
iShelfOntPonNearCurrent24ValidData OBJECT-TYPE
    SYNTAX      IShelfPerfInvalidFlag
    MAX-ACCESS  read-only
    STATUS      current
    DESCRIPTION
        "This object indicates if the data for this interval
         is valid."
    ::= { iShelfOntPonNearCurrent24Entry 8 }

iShelfOntPonNearCurrent24ThresholdCrossingPointer OBJECT-TYPE
    SYNTAX      IShelfThresholdCrossingPointer
    MAX-ACCESS  read-write
    STATUS      current
    DESCRIPTION
        "This object points to the threshold crossing entry
         (in IShelfThresholdCrossingTable). A value of zero
         indicates threshold crossing are not being generated."
    DEFVAL      { 0 }
    ::= { iShelfOntPonNearCurrent24Entry 9 }

-- ++++++++++++++++++++++++++++++++++++++++++++++++++++++++++++++++++++++++
--
-- iShelfOntPonNearInterval24Table
--
-- ++++++++++++++++++++++++++++++++++++++++++++++++++++++++++++++++++++++++

-- %CLICMDPREFIX ont:pm:pon
-- %CLICMDABBR i24neartable
iShelfOntPonNearInterval24Table OBJECT-TYPE
    SYNTAX      SEQUENCE OF IShelfOntPonNearInterval24Entry
    MAX-ACCESS  not-accessible
    STATUS      current
    DESCRIPTION
        "This table contains the Near-End PON performance data
         on a per ONT basis for the previous 24 hour intervals.

         Rows in this table are automatically created when the ONT
         is provisioned."
    ::= { iShelfOntPm 4 }

iShelfOntPonNearInterval24Entry OBJECT-TYPE
    SYNTAX      IShelfOntPonNearInterval24Entry
    MAX-ACCESS  not-accessible
    STATUS      current
    DESCRIPTION
        "Each entry corresponds to the near-end ONT performance
         data for a previous 24 hour interval."
    INDEX       { iShelfOntPonNearInterval24LogicalId,
                  iShelfOntPonNearInterval24Number }
    ::= { iShelfOntPonNearInterval24Table 1 }

IShelfOntPonNearInterval24Entry ::=
    SEQUENCE {
        iShelfOntPonNearInterval24LogicalId
            IShelfOntLogicalId,
        iShelfOntPonNearInterval24Number
            INTEGER,
        iShelfOntPonNearInterval24Bip8
            Counter32,
        iShelfOntPonNearInterval24Missing
            Counter32,
        iShelfOntPonNearInterval24BESs
            Gauge32,
        iShelfOntPonNearInterval24MESs
            Gauge32,
        iShelfOntPonNearInterval24SESs
            Gauge32,
        iShelfOntPonNearInterval24UASs
            Gauge32,
        iShelfOntPonNearInterval24ValidData
            IShelfPerfInvalidFlag
    }

iShelfOntPonNearInterval24LogicalId OBJECT-TYPE
    SYNTAX      IShelfOntLogicalId
    MAX-ACCESS  read-only
    STATUS      current
    DESCRIPTION "This object identifies the logical ID of the ONT."
    ::= { iShelfOntPonNearInterval24Entry 1 }

-- %CLICOLLABEL Int
-- %CLIWIDTH 2
iShelfOntPonNearInterval24Number OBJECT-TYPE
    SYNTAX      INTEGER(1..6)
    MAX-ACCESS  read-only
    STATUS      current
    DESCRIPTION
        "This object identifies the interval for which set set
         of statistics is available. The interval identified
         by 1 is the most recently completed 24 hour interval."
    ::= { iShelfOntPonNearInterval24Entry 2 }

-- %CLICOLLABEL Bip8Errs
iShelfOntPonNearInterval24Bip8 OBJECT-TYPE
    SYNTAX      Counter32
    MAX-ACCESS  read-only
    STATUS      current
    DESCRIPTION
        "This object contains the number of BIP8 errors for the
         ONT in the current interval."
    ::= { iShelfOntPonNearInterval24Entry 3 }

-- %CLICOLLABEL Missing
iShelfOntPonNearInterval24Missing OBJECT-TYPE
    SYNTAX      Counter32
    MAX-ACCESS  read-only
    STATUS      current
    DESCRIPTION
        "This object contains the number of Missing errors for
         the ONT in the current interval."
    ::= { iShelfOntPonNearInterval24Entry 4 }

-- %CLICOLLABEL BipES
-- %CLIWIDTH 5
iShelfOntPonNearInterval24BESs OBJECT-TYPE
    SYNTAX      Gauge32
    MAX-ACCESS  read-only
    STATUS      current
    DESCRIPTION
        "This object contains the number BIP8 Errored Seconds
         for the ONT in the current interval."
    ::= { iShelfOntPonNearInterval24Entry 5 }

-- %CLICOLLABEL MisES
-- %CLIWIDTH 5
iShelfOntPonNearInterval24MESs OBJECT-TYPE
    SYNTAX      Gauge32
    MAX-ACCESS  read-only
    STATUS      current
    DESCRIPTION
        "This object contains the number of Missing Errored
         Seconds for the ONT in the current interval."
    ::= { iShelfOntPonNearInterval24Entry 6 }

-- %CLICOLLABEL SES
-- %CLIWIDTH 5
iShelfOntPonNearInterval24SESs OBJECT-TYPE
    SYNTAX      Gauge32
    MAX-ACCESS  read-only
    STATUS      current
    DESCRIPTION
        "This object contains the number of Severely Errored
         Seconds for the ONT in the current interval."
    ::= { iShelfOntPonNearInterval24Entry 7 }

-- %CLICOLLABEL UAS
-- %CLIWIDTH 5
iShelfOntPonNearInterval24UASs OBJECT-TYPE
    SYNTAX      Gauge32
    MAX-ACCESS  read-only
    STATUS      current
    DESCRIPTION
        "This object contains the number of Unavailable Seconds
         for the ONT in the current interval."
    ::= { iShelfOntPonNearInterval24Entry 8 }

-- %CLIWIDTH 5
iShelfOntPonNearInterval24ValidData OBJECT-TYPE
    SYNTAX      IShelfPerfInvalidFlag
    MAX-ACCESS  read-only
    STATUS      current
    DESCRIPTION
        "This object indicates if the data for this interval
         is valid."
    ::= { iShelfOntPonNearInterval24Entry 9 }

-- ++++++++++++++++++++++++++++++++++++++++++++++++++++++++++++++++++++++++
--
-- iShelfOntPonFarCurrent15Table
--
-- ++++++++++++++++++++++++++++++++++++++++++++++++++++++++++++++++++++++++

-- %CLICMDPREFIX ont:pm:pon
-- %CLICMDABBR c15fartable
iShelfOntPonFarCurrent15Table OBJECT-TYPE
    SYNTAX      SEQUENCE OF IShelfOntPonFarCurrent15Entry
    MAX-ACCESS  not-accessible
    STATUS      current
    DESCRIPTION
        "This table contains the Far-End PON performance data
         on a per ONT basis for the current 15 minute interval.

         This is calculated and maintained on the OLT based on
         the following counters maintained by the OLT hardware:

         1) BIP8 Errors - Bit Interleaved Parity

         The following PM values will be computed from the above
         counters. These values will be computed each second.

         1) ESs - Errored Seconds. This is defined as any second
            containing a non-zero BIP8 error count.
         2) SESs - Severely Errored Seconds. This is defined as any
            second containing a non-zero BIP8 error count exceeding
            a specific threshold (which is TBD).
         3) UASs - Unavailable Seconds. This is defined as N
            consecutive SES. Once unavailable, N consecutive seconds
            must pass without SES before coming available again. The
            value of N is TBD.

         Rows in this table are automatically created when the ONT
         is provisioned."
    ::= { iShelfOntPm 5 }

iShelfOntPonFarCurrent15Entry OBJECT-TYPE
    SYNTAX      IShelfOntPonFarCurrent15Entry
    MAX-ACCESS  not-accessible
    STATUS      current
    DESCRIPTION
        "Each entry corresponds to the far-end ONT performance
         data for the current 15 minute interval."
    INDEX       { iShelfOntPonFarCurrent15LogicalId }
    ::= { iShelfOntPonFarCurrent15Table 1 }

IShelfOntPonFarCurrent15Entry ::=
    SEQUENCE {
        iShelfOntPonFarCurrent15LogicalId
            IShelfOntLogicalId,
        iShelfOntPonFarCurrent15Bip8
            Counter32,
        iShelfOntPonFarCurrent15ESs
            Gauge32,
        iShelfOntPonFarCurrent15SESs
            Gauge32,
        iShelfOntPonFarCurrent15UASs
            Gauge32,
        iShelfOntPonFarCurrent15ValidData
            IShelfPerfInvalidFlag,
        iShelfOntPonFarCurrent15ThresholdCrossingPointer
            IShelfThresholdCrossingPointer
    }

iShelfOntPonFarCurrent15LogicalId OBJECT-TYPE
    SYNTAX      IShelfOntLogicalId
    MAX-ACCESS  read-only
    STATUS      current
    DESCRIPTION "This object identifies the logical ID of the ONT."
    ::= { iShelfOntPonFarCurrent15Entry 1 }

-- %CLICOLLABEL Bip8Errs
iShelfOntPonFarCurrent15Bip8 OBJECT-TYPE
    SYNTAX      Counter32
    MAX-ACCESS  read-only
    STATUS      current
    DESCRIPTION
        "This object contains the number of BIP8 errors for the
         ONT in the current interval."
    ::= { iShelfOntPonFarCurrent15Entry 2 }

-- %CLICOLLABEL BipES
-- %CLIWIDTH 5
iShelfOntPonFarCurrent15ESs OBJECT-TYPE
    SYNTAX      Gauge32
    MAX-ACCESS  read-only
    STATUS      current
    DESCRIPTION
        "This object contains the number BIP8 Errored Seconds
         for the ONT in the current interval."
    ::= { iShelfOntPonFarCurrent15Entry 3 }

-- %PMPARAMTYPE ES
-- %CLICOLLABEL SES
-- %CLIWIDTH 5
iShelfOntPonFarCurrent15SESs OBJECT-TYPE
    SYNTAX      Gauge32
    MAX-ACCESS  read-only
    STATUS      current
    DESCRIPTION
        "This object contains the number of Severely Errored
         Seconds for the ONT in the current interval."
    ::= { iShelfOntPonFarCurrent15Entry 4 }

-- %PMPARAMTYPE US
-- %CLICOLLABEL UAS
-- %CLIWIDTH 5
iShelfOntPonFarCurrent15UASs OBJECT-TYPE
    SYNTAX      Gauge32
    MAX-ACCESS  read-only
    STATUS      current
    DESCRIPTION
        "This object contains the number of Unavailable Seconds
         for the ONT in the current interval."
    ::= { iShelfOntPonFarCurrent15Entry 5 }

-- %CLIWIDTH 5
iShelfOntPonFarCurrent15ValidData OBJECT-TYPE
    SYNTAX      IShelfPerfInvalidFlag
    MAX-ACCESS  read-only
    STATUS      current
    DESCRIPTION
        "This object indicates if the data for this interval
         is valid."
    ::= { iShelfOntPonFarCurrent15Entry 6 }

iShelfOntPonFarCurrent15ThresholdCrossingPointer OBJECT-TYPE
    SYNTAX      IShelfThresholdCrossingPointer
    MAX-ACCESS  read-write
    STATUS      current
    DESCRIPTION
        "This object points to the threshold crossing entry
         (in IShelfThresholdCrossingTable). A value of zero
         indicates threshold crossing are not being generated."
    DEFVAL      { 0 }
    ::= { iShelfOntPonFarCurrent15Entry 7 }

-- ++++++++++++++++++++++++++++++++++++++++++++++++++++++++++++++++++++++++
--
-- iShelfOntPonFarInterval15Table
--
-- ++++++++++++++++++++++++++++++++++++++++++++++++++++++++++++++++++++++++

-- %CLICMDPREFIX ont:pm:pon
-- %CLICMDABBR i15fartable
iShelfOntPonFarInterval15Table OBJECT-TYPE
    SYNTAX      SEQUENCE OF IShelfOntPonFarInterval15Entry
    MAX-ACCESS  not-accessible
    STATUS      current
    DESCRIPTION
        "This table contains the Far-End PON performance data
         on a per ONT basis for the previous 15 minute intervals.

         Rows in this table are automatically created when the ONT
         is provisioned."
    ::= { iShelfOntPm 6 }

iShelfOntPonFarInterval15Entry OBJECT-TYPE
    SYNTAX      IShelfOntPonFarInterval15Entry
    MAX-ACCESS  not-accessible
    STATUS      current
    DESCRIPTION
        "Each entry corresponds to the far-end ONT performance
         data for a previous 15 minute interval."
    INDEX       { iShelfOntPonFarInterval15LogicalId,
                  iShelfOntPonFarInterval15Number }
    ::= { iShelfOntPonFarInterval15Table 1 }

IShelfOntPonFarInterval15Entry ::=
    SEQUENCE {
        iShelfOntPonFarInterval15LogicalId
            IShelfOntLogicalId,
        iShelfOntPonFarInterval15Number
            INTEGER,
        iShelfOntPonFarInterval15Bip8
            Counter32,
        iShelfOntPonFarInterval15ESs
            Gauge32,
        iShelfOntPonFarInterval15SESs
            Gauge32,
        iShelfOntPonFarInterval15UASs
            Gauge32,
        iShelfOntPonFarInterval15ValidData
            IShelfPerfInvalidFlag
    }

iShelfOntPonFarInterval15LogicalId OBJECT-TYPE
    SYNTAX      IShelfOntLogicalId
    MAX-ACCESS  read-only
    STATUS      current
    DESCRIPTION "This object identifies the logical ID of the ONT."
    ::= { iShelfOntPonFarInterval15Entry 1 }

-- %CLICOLLABEL Int
-- %CLIWIDTH 2
iShelfOntPonFarInterval15Number OBJECT-TYPE
    SYNTAX      INTEGER(1..32)
    MAX-ACCESS  read-only
    STATUS      current
    DESCRIPTION
        "This object identifies the interval for which set set
         of statistics is available. The interval identified
         by 1 is the most recently completed 15 minute interval."
    ::= { iShelfOntPonFarInterval15Entry 2 }

-- %CLICOLLABEL Bip8Errs
iShelfOntPonFarInterval15Bip8 OBJECT-TYPE
    SYNTAX      Counter32
    MAX-ACCESS  read-only
    STATUS      current
    DESCRIPTION
        "This object contains the number of BIP8 errors for the
         ONT in the current interval."
    ::= { iShelfOntPonFarInterval15Entry 3 }

-- %CLICOLLABEL BipES
-- %CLIWIDTH 5
iShelfOntPonFarInterval15ESs OBJECT-TYPE
    SYNTAX      Gauge32
    MAX-ACCESS  read-only
    STATUS      current
    DESCRIPTION
        "This object contains the number BIP8 Errored Seconds
         for the ONT in the current interval."
    ::= { iShelfOntPonFarInterval15Entry 4 }

-- %CLICOLLABEL SES
-- %CLIWIDTH 5
iShelfOntPonFarInterval15SESs OBJECT-TYPE
    SYNTAX      Gauge32
    MAX-ACCESS  read-only
    STATUS      current
    DESCRIPTION
        "This object contains the number of Severely Errored
         Seconds for the ONT in the current interval."
    ::= { iShelfOntPonFarInterval15Entry 5 }

-- %CLICOLLABEL UAS
-- %CLIWIDTH 5
iShelfOntPonFarInterval15UASs OBJECT-TYPE
    SYNTAX      Gauge32
    MAX-ACCESS  read-only
    STATUS      current
    DESCRIPTION
        "This object contains the number of Unavailable Seconds
         for the ONT in the current interval."
    ::= { iShelfOntPonFarInterval15Entry 6 }

-- %CLIWIDTH 5
iShelfOntPonFarInterval15ValidData OBJECT-TYPE
    SYNTAX      IShelfPerfInvalidFlag
    MAX-ACCESS  read-only
    STATUS      current
    DESCRIPTION
        "This object indicates if the data for this interval
         is valid."
    ::= { iShelfOntPonFarInterval15Entry 7 }

-- ++++++++++++++++++++++++++++++++++++++++++++++++++++++++++++++++++++++++
--
-- iShelfOntPonFarCurrent24Table
--
-- ++++++++++++++++++++++++++++++++++++++++++++++++++++++++++++++++++++++++

-- %CLICMDPREFIX ont:pm:pon
-- %CLICMDABBR c24fartable
iShelfOntPonFarCurrent24Table OBJECT-TYPE
    SYNTAX      SEQUENCE OF IShelfOntPonFarCurrent24Entry
    MAX-ACCESS  not-accessible
    STATUS      current
    DESCRIPTION
        "This table contains the Far-End PON performance data
         on a per ONT basis for the current 24 hour interval.

         Rows in this table are automatically created when the ONT
         is provisioned."
    ::= { iShelfOntPm 7 }

iShelfOntPonFarCurrent24Entry OBJECT-TYPE
    SYNTAX      IShelfOntPonFarCurrent24Entry
    MAX-ACCESS  not-accessible
    STATUS      current
    DESCRIPTION
        "Each entry corresponds to the far-end ONT performance
         data for the current 24 hour interval."
    INDEX       { iShelfOntPonFarCurrent24LogicalId }
    ::= { iShelfOntPonFarCurrent24Table 1 }

IShelfOntPonFarCurrent24Entry ::=
    SEQUENCE {
        iShelfOntPonFarCurrent24LogicalId
            IShelfOntLogicalId,
        iShelfOntPonFarCurrent24Bip8
            Counter32,
        iShelfOntPonFarCurrent24ESs
            Gauge32,
        iShelfOntPonFarCurrent24SESs
            Gauge32,
        iShelfOntPonFarCurrent24UASs
            Gauge32,
        iShelfOntPonFarCurrent24ValidData
            IShelfPerfInvalidFlag,
        iShelfOntPonFarCurrent24ThresholdCrossingPointer
            IShelfThresholdCrossingPointer
    }

iShelfOntPonFarCurrent24LogicalId OBJECT-TYPE
    SYNTAX      IShelfOntLogicalId
    MAX-ACCESS  read-only
    STATUS      current
    DESCRIPTION "This object identifies the logical ID of the ONT."
    ::= { iShelfOntPonFarCurrent24Entry 1 }

-- %CLICOLLABEL Bip8Errs
iShelfOntPonFarCurrent24Bip8 OBJECT-TYPE
    SYNTAX      Counter32
    MAX-ACCESS  read-only
    STATUS      current
    DESCRIPTION
        "This object contains the number of BIP8 errors for the
         ONT in the current interval."
    ::= { iShelfOntPonFarCurrent24Entry 2 }

-- %CLICOLLABEL BipES
-- %CLIWIDTH 5
iShelfOntPonFarCurrent24ESs OBJECT-TYPE
    SYNTAX      Gauge32
    MAX-ACCESS  read-only
    STATUS      current
    DESCRIPTION
        "This object contains the number BIP8 Errored Seconds
         for the ONT in the current interval."
    ::= { iShelfOntPonFarCurrent24Entry 3 }

-- %CLICOLLABEL SES
-- %CLIWIDTH 5
iShelfOntPonFarCurrent24SESs OBJECT-TYPE
    SYNTAX      Gauge32
    MAX-ACCESS  read-only
    STATUS      current
    DESCRIPTION
        "This object contains the number of Severely Errored
         Seconds for the ONT in the current interval."
    ::= { iShelfOntPonFarCurrent24Entry 4 }

-- %CLICOLLABEL UAS
-- %CLIWIDTH 5
iShelfOntPonFarCurrent24UASs OBJECT-TYPE
    SYNTAX      Gauge32
    MAX-ACCESS  read-only
    STATUS      current
    DESCRIPTION
        "This object contains the number of Unavailable Seconds
         for the ONT in the current interval."
    ::= { iShelfOntPonFarCurrent24Entry 5 }

-- %CLIWIDTH 5
iShelfOntPonFarCurrent24ValidData OBJECT-TYPE
    SYNTAX      IShelfPerfInvalidFlag
    MAX-ACCESS  read-only
    STATUS      current
    DESCRIPTION
        "This object indicates if the data for this interval
         is valid."
    ::= { iShelfOntPonFarCurrent24Entry 6 }

iShelfOntPonFarCurrent24ThresholdCrossingPointer OBJECT-TYPE
    SYNTAX      IShelfThresholdCrossingPointer
    MAX-ACCESS  read-write
    STATUS      current
    DESCRIPTION
        "This object points to the threshold crossing entry
         (in IShelfThresholdCrossingTable). A value of zero
         indicates threshold crossing are not being generated."
    DEFVAL      { 0 }
    ::= { iShelfOntPonFarCurrent24Entry 7 }

-- ++++++++++++++++++++++++++++++++++++++++++++++++++++++++++++++++++++++++
--
-- iShelfOntPonFarInterval24Table
--
-- ++++++++++++++++++++++++++++++++++++++++++++++++++++++++++++++++++++++++

-- %CLICMDPREFIX ont:pm:pon
-- %CLICMDABBR i24fartable
iShelfOntPonFarInterval24Table OBJECT-TYPE
    SYNTAX      SEQUENCE OF IShelfOntPonFarInterval24Entry
    MAX-ACCESS  not-accessible
    STATUS      current
    DESCRIPTION
        "This table contains the Far-End PON performance data
         on a per ONT basis for the previous 24 hour intervals.

         Rows in this table are automatically created when the ONT
         is provisioned."
    ::= { iShelfOntPm 8 }

iShelfOntPonFarInterval24Entry OBJECT-TYPE
    SYNTAX      IShelfOntPonFarInterval24Entry
    MAX-ACCESS  not-accessible
    STATUS      current
    DESCRIPTION
        "Each entry corresponds to the far-end ONT performance
         data for a previous 24 hour interval."
    INDEX       { iShelfOntPonFarInterval24LogicalId,
                  iShelfOntPonFarInterval24Number }
    ::= { iShelfOntPonFarInterval24Table 1 }

IShelfOntPonFarInterval24Entry ::=
    SEQUENCE {
        iShelfOntPonFarInterval24LogicalId
            IShelfOntLogicalId,
        iShelfOntPonFarInterval24Number
            INTEGER,
        iShelfOntPonFarInterval24Bip8
            Counter32,
        iShelfOntPonFarInterval24ESs
            Gauge32,
        iShelfOntPonFarInterval24SESs
            Gauge32,
        iShelfOntPonFarInterval24UASs
            Gauge32,
        iShelfOntPonFarInterval24ValidData
            IShelfPerfInvalidFlag
    }

iShelfOntPonFarInterval24LogicalId OBJECT-TYPE
    SYNTAX      IShelfOntLogicalId
    MAX-ACCESS  read-only
    STATUS      current
    DESCRIPTION "This object identifies the logical ID of the ONT."
    ::= { iShelfOntPonFarInterval24Entry 1 }

-- %CLICOLLABEL Int
-- %CLIWIDTH 2
iShelfOntPonFarInterval24Number OBJECT-TYPE
    SYNTAX      INTEGER(1..6)
    MAX-ACCESS  read-only
    STATUS      current
    DESCRIPTION
        "This object identifies the interval for which set set
         of statistics is available. The interval identified
         by 1 is the most recently completed 24 hour interval."
    ::= { iShelfOntPonFarInterval24Entry 2 }

-- %CLICOLLABEL Bip8Errs
iShelfOntPonFarInterval24Bip8 OBJECT-TYPE
    SYNTAX      Counter32
    MAX-ACCESS  read-only
    STATUS      current
    DESCRIPTION
        "This object contains the number of BIP8 errors for the
         ONT in the current interval."
    ::= { iShelfOntPonFarInterval24Entry 3 }

-- %CLICOLLABEL BipES
-- %CLIWIDTH 5
iShelfOntPonFarInterval24ESs OBJECT-TYPE
    SYNTAX      Gauge32
    MAX-ACCESS  read-only
    STATUS      current
    DESCRIPTION
        "This object contains the number BIP8 Errored Seconds
         for the ONT in the current interval."
    ::= { iShelfOntPonFarInterval24Entry 4 }

-- %CLICOLLABEL SES
-- %CLIWIDTH 5
iShelfOntPonFarInterval24SESs OBJECT-TYPE
    SYNTAX      Gauge32
    MAX-ACCESS  read-only
    STATUS      current
    DESCRIPTION
        "This object contains the number of Severely Errored
         Seconds for the ONT in the current interval."
    ::= { iShelfOntPonFarInterval24Entry 5 }

-- %CLICOLLABEL UAS
-- %CLIWIDTH 5
iShelfOntPonFarInterval24UASs OBJECT-TYPE
    SYNTAX      Gauge32
    MAX-ACCESS  read-only
    STATUS      current
    DESCRIPTION
        "This object contains the number of Unavailable Seconds
         for the ONT in the current interval."
    ::= { iShelfOntPonFarInterval24Entry 6 }

-- %CLIWIDTH 5
iShelfOntPonFarInterval24ValidData OBJECT-TYPE
    SYNTAX      IShelfPerfInvalidFlag
    MAX-ACCESS  read-only
    STATUS      current
    DESCRIPTION
        "This object indicates if the data for this interval
         is valid."
    ::= { iShelfOntPonFarInterval24Entry 7 }

-- ++++++++++++++++++++++++++++++++++++++++++++++++++++++++++++++++++++++++
--
-- iShelfOntEthernetCurrent15Table - 
--
-- ++++++++++++++++++++++++++++++++++++++++++++++++++++++++++++++++++++++++

-- %CLICMDPREFIX ont:pm:eth
-- %CLICMDABBR c15table
iShelfOntEthernetCurrent15Table OBJECT-TYPE
    SYNTAX      SEQUENCE OF IShelfOntEthernetCurrent15Entry
    MAX-ACCESS  not-accessible
    STATUS      current
    DESCRIPTION
        "This table contains performance history data pertaining
         to the ONT ethernet port for the current 15 minute
         interval. Error counters are maintained in this table
         and threshold crossing alerts may be generated if any
         of the error counters cross the threshold.

         Rows in this table are automatically created."
    ::= { iShelfOntPm 9 }

iShelfOntEthernetCurrent15Entry OBJECT-TYPE
    SYNTAX      IShelfOntEthernetCurrent15Entry
    MAX-ACCESS  not-accessible
    STATUS      current
    DESCRIPTION
        "Each entry contains performance history data for one
         ONT ethernet port."
    INDEX       { iShelfOntEthernetCurrent15LogicalId,
                  iShelfOntEthernetCurrent15SLCIndex,
                  iShelfOntEthernetCurrent15Port }
    ::= { iShelfOntEthernetCurrent15Table 1 }

IShelfOntEthernetCurrent15Entry ::=
    SEQUENCE {
        iShelfOntEthernetCurrent15LogicalId
            IShelfOntLogicalId,
        iShelfOntEthernetCurrent15SLCIndex
            IShelfOntSubscriberLineCardIndex,
        iShelfOntEthernetCurrent15Port
            INTEGER,
        iShelfOntEthernetCurrent15Crc
            Counter32,
        iShelfOntEthernetCurrent15ShortPkts
            Counter32,
        iShelfOntEthernetCurrent15Overflow
            Counter32,
        iShelfOntEthernetCurrent15Underflow
            Counter32,
        iShelfOntEthernetCurrent15ValidData
            IShelfPerfInvalidFlag,
        iShelfOntEthernetCurrent15ThresholdCrossingPointer
            IShelfThresholdCrossingPointer
    }

iShelfOntEthernetCurrent15LogicalId OBJECT-TYPE
    SYNTAX      IShelfOntLogicalId
    MAX-ACCESS  read-only
    STATUS      current
    DESCRIPTION "This object identifies the logical ID of the ONT."
    ::= { iShelfOntEthernetCurrent15Entry 1 }

iShelfOntEthernetCurrent15SLCIndex OBJECT-TYPE
    SYNTAX      IShelfOntSubscriberLineCardIndex
    MAX-ACCESS  read-only
    STATUS      current
    DESCRIPTION
        "This object identifies the ONT subscriber line card
         index."
    ::= { iShelfOntEthernetCurrent15Entry 2 }

iShelfOntEthernetCurrent15Port OBJECT-TYPE
    SYNTAX      INTEGER (1..4)
    MAX-ACCESS  read-only
    STATUS      current
    DESCRIPTION "This object identifies the ethernet port number."
    ::= { iShelfOntEthernetCurrent15Entry 3 }

-- %CLICOLLABEL CRCErrs
iShelfOntEthernetCurrent15Crc OBJECT-TYPE
    SYNTAX      Counter32
    MAX-ACCESS  read-only
    STATUS      current
    DESCRIPTION
        "This counter is the number of received frames with
         CRC errors."
    ::= { iShelfOntEthernetCurrent15Entry 4 }

-- %CLICOLLABEL ShortPkts
iShelfOntEthernetCurrent15ShortPkts OBJECT-TYPE
    SYNTAX      Counter32
    MAX-ACCESS  read-only
    STATUS      current
    DESCRIPTION
        "This counter is the number of received frames that
         were too short (i.e., less than 64 bytes)."
    ::= { iShelfOntEthernetCurrent15Entry 5 }

-- %CLICOLLABEL Overflow
iShelfOntEthernetCurrent15Overflow OBJECT-TYPE
    SYNTAX      Counter32
    MAX-ACCESS  read-only
    STATUS      current
    DESCRIPTION
        "This counter is the number of input overflow
         conditions detected."
    ::= { iShelfOntEthernetCurrent15Entry 6 }

-- %CLICOLLABEL Underflow
iShelfOntEthernetCurrent15Underflow OBJECT-TYPE
    SYNTAX      Counter32
    MAX-ACCESS  read-only
    STATUS      current
    DESCRIPTION
        "This counter is the number of output underflow
         conditions detected."
    ::= { iShelfOntEthernetCurrent15Entry 7 }

-- %CLIWIDTH 5
iShelfOntEthernetCurrent15ValidData OBJECT-TYPE
    SYNTAX      IShelfPerfInvalidFlag
    MAX-ACCESS  read-only
    STATUS      current
    DESCRIPTION
        "This object indicates if the data for this interval
         is valid."
    ::= { iShelfOntEthernetCurrent15Entry 8 }

iShelfOntEthernetCurrent15ThresholdCrossingPointer OBJECT-TYPE
    SYNTAX      IShelfThresholdCrossingPointer
    MAX-ACCESS  read-write
    STATUS      current
    DESCRIPTION
        "This object points to the threshold crossing entry
         (in iShelfThresholdCrossingTable). A value of zero
         indicates threshold crossing are not being generated."
    DEFVAL      { 0 }
    ::= { iShelfOntEthernetCurrent15Entry 9 }

-- ++++++++++++++++++++++++++++++++++++++++++++++++++++++++++++++++++++++++
--
-- iShelfOntEthernetInterval15Table - 
--
-- ++++++++++++++++++++++++++++++++++++++++++++++++++++++++++++++++++++++++

-- %CLICMDPREFIX ont:pm:eth
-- %CLICMDABBR i15table
iShelfOntEthernetInterval15Table OBJECT-TYPE
    SYNTAX      SEQUENCE OF IShelfOntEthernetInterval15Entry
    MAX-ACCESS  not-accessible
    STATUS      current
    DESCRIPTION
        "This table contains performance history data pertaining
         the the ONT ethernet port for previous 15 minute
         intervals.

         Rows in this table are automatically created."
    ::= { iShelfOntPm 10 }

iShelfOntEthernetInterval15Entry OBJECT-TYPE
    SYNTAX      IShelfOntEthernetInterval15Entry
    MAX-ACCESS  not-accessible
    STATUS      current
    DESCRIPTION
        "Each entry contains performance history data for one
         ONT ethernet port."
    INDEX       { iShelfOntEthernetInterval15LogicalId,
                  iShelfOntEthernetInterval15SLCIndex,
                  iShelfOntEthernetInterval15Port,
                  iShelfOntEthernetInterval15Number }
    ::= { iShelfOntEthernetInterval15Table 1 }

IShelfOntEthernetInterval15Entry ::=
    SEQUENCE {
        iShelfOntEthernetInterval15LogicalId
            IShelfOntLogicalId,
        iShelfOntEthernetInterval15SLCIndex
            IShelfOntSubscriberLineCardIndex,
        iShelfOntEthernetInterval15Port
            INTEGER,
        iShelfOntEthernetInterval15Number
            INTEGER,
        iShelfOntEthernetInterval15Crc
            Counter32,
        iShelfOntEthernetInterval15ShortPkts
            Counter32,
        iShelfOntEthernetInterval15Overflow
            Counter32,
        iShelfOntEthernetInterval15Underflow
            Counter32,
        iShelfOntEthernetInterval15ValidData
            IShelfPerfInvalidFlag
    }

iShelfOntEthernetInterval15LogicalId OBJECT-TYPE
    SYNTAX      IShelfOntLogicalId
    MAX-ACCESS  read-only
    STATUS      current
    DESCRIPTION "This object identifies the logical ID of the ONT."
    ::= { iShelfOntEthernetInterval15Entry 1 }

iShelfOntEthernetInterval15SLCIndex OBJECT-TYPE
    SYNTAX      IShelfOntSubscriberLineCardIndex
    MAX-ACCESS  read-only
    STATUS      current
    DESCRIPTION
        "This object identifies the ONT subscriber line card
         index."
    ::= { iShelfOntEthernetInterval15Entry 2 }

iShelfOntEthernetInterval15Port OBJECT-TYPE
    SYNTAX      INTEGER (1..4)
    MAX-ACCESS  read-only
    STATUS      current
    DESCRIPTION "This object identifies the ethernet port number."
    ::= { iShelfOntEthernetInterval15Entry 3 }

-- %CLICOLLABEL Int
-- %CLIWIDTH 3
iShelfOntEthernetInterval15Number OBJECT-TYPE
    SYNTAX      INTEGER(1..32)
    MAX-ACCESS  read-only
    STATUS      current
    DESCRIPTION
        "This object identifies the interval for which this set
         of statistics is available. The interval identified
         by 1 is the most recently completed 15 minute interval."
    ::= { iShelfOntEthernetInterval15Entry 4 }

-- %CLICOLLABEL CRCErrs
iShelfOntEthernetInterval15Crc OBJECT-TYPE
    SYNTAX      Counter32
    MAX-ACCESS  read-only
    STATUS      current
    DESCRIPTION
        "This counter is the number of received frames with
         CRC errors."
    ::= { iShelfOntEthernetInterval15Entry 5 }

-- %CLICOLLABEL ShortPkts
iShelfOntEthernetInterval15ShortPkts OBJECT-TYPE
    SYNTAX      Counter32
    MAX-ACCESS  read-only
    STATUS      current
    DESCRIPTION
        "This counter is the number of received frames that
         were too short (i.e., less than 64 bytes)."
    ::= { iShelfOntEthernetInterval15Entry 6 }

-- %CLICOLLABEL Overflow
iShelfOntEthernetInterval15Overflow OBJECT-TYPE
    SYNTAX      Counter32
    MAX-ACCESS  read-only
    STATUS      current
    DESCRIPTION
        "This counter is the number of input overflow
         conditions detected."
    ::= { iShelfOntEthernetInterval15Entry 7 }

-- %CLICOLLABEL Underflow
iShelfOntEthernetInterval15Underflow OBJECT-TYPE
    SYNTAX      Counter32
    MAX-ACCESS  read-only
    STATUS      current
    DESCRIPTION
        "This counter is the number of output underflow
         conditions detected."
    ::= { iShelfOntEthernetInterval15Entry 8 }

-- %CLIWIDTH 5
iShelfOntEthernetInterval15ValidData OBJECT-TYPE
    SYNTAX      IShelfPerfInvalidFlag
    MAX-ACCESS  read-only
    STATUS      current
    DESCRIPTION
        "This object indicates if the data for this interval
         is valid."
    ::= { iShelfOntEthernetInterval15Entry 9 }

-- ++++++++++++++++++++++++++++++++++++++++++++++++++++++++++++++++++++++++
--
-- iShelfOntEthernetCurrent24Table - 
--
-- ++++++++++++++++++++++++++++++++++++++++++++++++++++++++++++++++++++++++

-- %CLICMDPREFIX pm:eth
-- %CLICMDPREFIX ont:pm:eth
-- %CLICMDABBR c24table
iShelfOntEthernetCurrent24Table OBJECT-TYPE
    SYNTAX      SEQUENCE OF IShelfOntEthernetCurrent24Entry
    MAX-ACCESS  not-accessible
    STATUS      current
    DESCRIPTION
        "This table contains performance history data pertaining
         to the ONT ethernet port for the current 24 hour
         interval. Threshold crossing alerts may be applied to
         the error counters in this table."
    ::= { iShelfOntPm 11 }

iShelfOntEthernetCurrent24Entry OBJECT-TYPE
    SYNTAX      IShelfOntEthernetCurrent24Entry
    MAX-ACCESS  not-accessible
    STATUS      current
    DESCRIPTION
        "Each entry contains performance history data for one
         ONT ethernet port."
    INDEX       { iShelfOntEthernetCurrent24LogicalId,
                  iShelfOntEthernetCurrent24SLCIndex,
                  iShelfOntEthernetCurrent24Port }
    ::= { iShelfOntEthernetCurrent24Table 1 }

IShelfOntEthernetCurrent24Entry ::=
    SEQUENCE {
        iShelfOntEthernetCurrent24LogicalId
            IShelfOntLogicalId,
        iShelfOntEthernetCurrent24SLCIndex
            IShelfOntSubscriberLineCardIndex,
        iShelfOntEthernetCurrent24Port
            INTEGER,
        iShelfOntEthernetCurrent24Crc
            Counter32,
        iShelfOntEthernetCurrent24ShortPkts
            Counter32,
        iShelfOntEthernetCurrent24Overflow
            Counter32,
        iShelfOntEthernetCurrent24Underflow
            Counter32,
        iShelfOntEthernetCurrent24ValidData
            IShelfPerfInvalidFlag,
        iShelfOntEthernetCurrent24ThresholdCrossingPointer
            IShelfThresholdCrossingPointer
    }

iShelfOntEthernetCurrent24LogicalId OBJECT-TYPE
    SYNTAX      IShelfOntLogicalId
    MAX-ACCESS  read-only
    STATUS      current
    DESCRIPTION "This object identifies the logical ID of the ONT."
    ::= { iShelfOntEthernetCurrent24Entry 1 }

iShelfOntEthernetCurrent24SLCIndex OBJECT-TYPE
    SYNTAX      IShelfOntSubscriberLineCardIndex
    MAX-ACCESS  read-only
    STATUS      current
    DESCRIPTION
        "This object identifies the ONT subscriber line card
         index."
    ::= { iShelfOntEthernetCurrent24Entry 2 }

iShelfOntEthernetCurrent24Port OBJECT-TYPE
    SYNTAX      INTEGER (1..4)
    MAX-ACCESS  read-only
    STATUS      current
    DESCRIPTION "This object identifies the ethernet port number."
    ::= { iShelfOntEthernetCurrent24Entry 3 }

-- %CLICOLLABEL CRCErrs
iShelfOntEthernetCurrent24Crc OBJECT-TYPE
    SYNTAX      Counter32
    MAX-ACCESS  read-only
    STATUS      current
    DESCRIPTION
        "This counter is the number of received frames with
         CRC errors."
    ::= { iShelfOntEthernetCurrent24Entry 4 }

-- %CLICOLLABEL ShortPkts
iShelfOntEthernetCurrent24ShortPkts OBJECT-TYPE
    SYNTAX      Counter32
    MAX-ACCESS  read-only
    STATUS      current
    DESCRIPTION
        "This counter is the number of received frames that
         were too short (i.e., less than 64 bytes)."
    ::= { iShelfOntEthernetCurrent24Entry 5 }

-- %CLICOLLABEL Overflow
iShelfOntEthernetCurrent24Overflow OBJECT-TYPE
    SYNTAX      Counter32
    MAX-ACCESS  read-only
    STATUS      current
    DESCRIPTION
        "This counter is the number of input overflow
         conditions detected."
    ::= { iShelfOntEthernetCurrent24Entry 6 }

-- %CLICOLLABEL Underflow
iShelfOntEthernetCurrent24Underflow OBJECT-TYPE
    SYNTAX      Counter32
    MAX-ACCESS  read-only
    STATUS      current
    DESCRIPTION
        "This counter is the number of output underflow
         conditions detected."
    ::= { iShelfOntEthernetCurrent24Entry 7 }

-- %CLIWIDTH 5
iShelfOntEthernetCurrent24ValidData OBJECT-TYPE
    SYNTAX      IShelfPerfInvalidFlag
    MAX-ACCESS  read-only
    STATUS      current
    DESCRIPTION
        "This object indicates if the data for this interval
         is valid."
    ::= { iShelfOntEthernetCurrent24Entry 8 }

iShelfOntEthernetCurrent24ThresholdCrossingPointer OBJECT-TYPE
    SYNTAX      IShelfThresholdCrossingPointer
    MAX-ACCESS  read-write
    STATUS      current
    DESCRIPTION
        "This object points to the threshold crossing entry
         (in iShelfThresholdCrossingTable). A value of zero
         indicates threshold crossing are not being generated."
    DEFVAL      { 0 }
    ::= { iShelfOntEthernetCurrent24Entry 9 }

-- ++++++++++++++++++++++++++++++++++++++++++++++++++++++++++++++++++++++++
--
-- iShelfOntEthernetInterval24Table - 
--
-- ++++++++++++++++++++++++++++++++++++++++++++++++++++++++++++++++++++++++

-- %CLICMDPREFIX ont:pm:eth
-- %CLICMDABBR i24table
iShelfOntEthernetInterval24Table OBJECT-TYPE
    SYNTAX      SEQUENCE OF IShelfOntEthernetInterval24Entry
    MAX-ACCESS  not-accessible
    STATUS      current
    DESCRIPTION
        "The table contains performance history data pertaining
         the ONT ethernet port for previous 24 hour intervals.

         Rows in this table are automatically created."
    ::= { iShelfOntPm 12 }

iShelfOntEthernetInterval24Entry OBJECT-TYPE
    SYNTAX      IShelfOntEthernetInterval24Entry
    MAX-ACCESS  not-accessible
    STATUS      current
    DESCRIPTION
        "Each entry contains performance history data for one
         ONT ethernet port."
    INDEX       { iShelfOntEthernetInterval24LogicalId,
                  iShelfOntEthernetInterval24SLCIndex,
                  iShelfOntEthernetInterval24Port,
                  iShelfOntEthernetInterval24Number }
    ::= { iShelfOntEthernetInterval24Table 1 }

IShelfOntEthernetInterval24Entry ::=
    SEQUENCE {
        iShelfOntEthernetInterval24LogicalId
            IShelfOntLogicalId,
        iShelfOntEthernetInterval24SLCIndex
            IShelfOntSubscriberLineCardIndex,
        iShelfOntEthernetInterval24Port
            INTEGER,
        iShelfOntEthernetInterval24Number
            INTEGER,
        iShelfOntEthernetInterval24Crc
            Counter32,
        iShelfOntEthernetInterval24ShortPkts
            Counter32,
        iShelfOntEthernetInterval24Overflow
            Counter32,
        iShelfOntEthernetInterval24Underflow
            Counter32,
        iShelfOntEthernetInterval24ValidData
            IShelfPerfInvalidFlag
    }

iShelfOntEthernetInterval24LogicalId OBJECT-TYPE
    SYNTAX      IShelfOntLogicalId
    MAX-ACCESS  read-only
    STATUS      current
    DESCRIPTION "This object identifies the logical ID of the ONT."
    ::= { iShelfOntEthernetInterval24Entry 1 }

iShelfOntEthernetInterval24SLCIndex OBJECT-TYPE
    SYNTAX      IShelfOntSubscriberLineCardIndex
    MAX-ACCESS  read-only
    STATUS      current
    DESCRIPTION
        "This object identifies the ONT subscriber line card
         index."
    ::= { iShelfOntEthernetInterval24Entry 2 }

iShelfOntEthernetInterval24Port OBJECT-TYPE
    SYNTAX      INTEGER (1..4)
    MAX-ACCESS  read-only
    STATUS      current
    DESCRIPTION "This object identifies the ethernet port number."
    ::= { iShelfOntEthernetInterval24Entry 3 }

-- %CLICOLLABEL Int
-- %CLIWIDTH 3
iShelfOntEthernetInterval24Number OBJECT-TYPE
    SYNTAX      INTEGER(1..6)
    MAX-ACCESS  read-only
    STATUS      current
    DESCRIPTION
        "This object identifies the interval for which this set
         of statistics is available. The interval identified
         by 1 is the most recently completed 24 hour interval."
    ::= { iShelfOntEthernetInterval24Entry 4 }

-- %CLICOLLABEL CRCErrs
iShelfOntEthernetInterval24Crc OBJECT-TYPE
    SYNTAX      Counter32
    MAX-ACCESS  read-only
    STATUS      current
    DESCRIPTION
        "This counter is the number of received frames with
         CRC errors."
    ::= { iShelfOntEthernetInterval24Entry 5 }

-- %CLICOLLABEL ShortPkts
iShelfOntEthernetInterval24ShortPkts OBJECT-TYPE
    SYNTAX      Counter32
    MAX-ACCESS  read-only
    STATUS      current
    DESCRIPTION
        "This counter is the number of received frames that
         were too short (i.e., less than 64 bytes)."
    ::= { iShelfOntEthernetInterval24Entry 6 }

-- %CLICOLLABEL Overflow
iShelfOntEthernetInterval24Overflow OBJECT-TYPE
    SYNTAX      Counter32
    MAX-ACCESS  read-only
    STATUS      current
    DESCRIPTION
        "This counter is the number of input overflow
         conditions detected."
    ::= { iShelfOntEthernetInterval24Entry 7 }

-- %CLICOLLABEL Underflow
iShelfOntEthernetInterval24Underflow OBJECT-TYPE
    SYNTAX      Counter32
    MAX-ACCESS  read-only
    STATUS      current
    DESCRIPTION
        "This counter is the number of output underflow
         conditions detected."
    ::= { iShelfOntEthernetInterval24Entry 8 }

-- %CLIWIDTH 5
iShelfOntEthernetInterval24ValidData OBJECT-TYPE
    SYNTAX      IShelfPerfInvalidFlag
    MAX-ACCESS  read-only
    STATUS      current
    DESCRIPTION
        "This object indicates if the data for this interval
         is valid."
    ::= { iShelfOntEthernetInterval24Entry 9 }

-- ++++++++++++++++++++++++++++++++++++++++++++++++++++++++++++++++++++++++
--
-- iShelfOntSdvCurrent15Table - 
--
-- ++++++++++++++++++++++++++++++++++++++++++++++++++++++++++++++++++++++++

-- %CLICMDPREFIX ont:pm:sdv
-- %CLICMDABBR c15table
-- %CLISHOWGROUP c15table
iShelfOntSdvCurrent15Table OBJECT-TYPE
    SYNTAX      SEQUENCE OF IShelfOntSdvCurrent15Entry
    MAX-ACCESS  not-accessible
    STATUS      current
    DESCRIPTION
        "This table contains performance history data pertaining
         to ONT SDV Services for the current 15 minute interval.
         Threshold crossing alerts may be applied to
         the counters in this table.
         Rows in this table are automatically created."
    ::= { iShelfOntPm 13 }

iShelfOntSdvCurrent15Entry OBJECT-TYPE
    SYNTAX      IShelfOntSdvCurrent15Entry
    MAX-ACCESS  not-accessible
    STATUS      current
    DESCRIPTION
        "Each entry contains performance history data for one
         instance of SDV Service."
    INDEX       { iShelfOntSdvCurrent15LogicalId,
                  iShelfOntSdvCurrent15SLCIndex,
                  iShelfOntSdvCurrent15Port }
    ::= { iShelfOntSdvCurrent15Table 1 }

IShelfOntSdvCurrent15Entry ::=
    SEQUENCE {
        iShelfOntSdvCurrent15LogicalId
            IShelfOntLogicalId,
        iShelfOntSdvCurrent15SLCIndex
            IShelfOntSubscriberLineCardIndex,
        iShelfOntSdvCurrent15Port
            INTEGER,
        iShelfOntSdvCurrent15PeakStreams
            Counter32,
        iShelfOntSdvCurrent15Queries
            Counter32,
        iShelfOntSdvCurrent15Joins
            Counter32,
        iShelfOntSdvCurrent15Leaves
            Counter32,
        iShelfOntSdvCurrent15Timeout
            Counter32,
        iShelfOntSdvCurrent15JoinsForced
            Counter32,
        iShelfOntSdvCurrent15JoinErrlimit
            Counter32,
        iShelfOntSdvCurrent15JoinErrAccess
            Counter32,
        iShelfOntSdvCurrent15JoinErrNotsdv
            Counter32,
        iShelfOntSdvCurrent15Inactivate
            Counter32,
        iShelfOntSdvCurrent15ValidData
            IShelfPerfInvalidFlag,
        iShelfOntSdvCurrent15ThresholdCrossingPointer
            IShelfThresholdCrossingPointer
    }

-- %CLISHOWGROUP c15table.1
-- %CLISHOWGROUP c15table.2
-- %CLIWIDTH 3
iShelfOntSdvCurrent15LogicalId OBJECT-TYPE
    SYNTAX      IShelfOntLogicalId
    MAX-ACCESS  read-only
    STATUS      current
    DESCRIPTION "This object identifies the logical ID of the ONT."
    ::= { iShelfOntSdvCurrent15Entry 1 }

-- %CLISHOWGROUP c15table.1
-- %CLISHOWGROUP c15table.2
iShelfOntSdvCurrent15SLCIndex OBJECT-TYPE
    SYNTAX      IShelfOntSubscriberLineCardIndex
    MAX-ACCESS  read-only
    STATUS      current
    DESCRIPTION
        "This object identifies the ONT subscriber line card
         index."
    ::= { iShelfOntSdvCurrent15Entry 2 }

-- %CLISHOWGROUP c15table.1
-- %CLISHOWGROUP c15table.2
iShelfOntSdvCurrent15Port OBJECT-TYPE
    SYNTAX      INTEGER (1..4)
    MAX-ACCESS  read-only
    STATUS      current
    DESCRIPTION "This object identifies the ethernet port number."
    ::= { iShelfOntSdvCurrent15Entry 3 }


-- //PMPARAMTYPE PEAK
-- %CLISHOWGROUP c15table.1
-- %CLICOLLABEL Peak-Strms
iShelfOntSdvCurrent15PeakStreams OBJECT-TYPE
    SYNTAX      Counter32
    MAX-ACCESS  read-only
    STATUS      current
    DESCRIPTION
        "This counter is the maximum concurent streams
         joined during the interval."
    ::= { iShelfOntSdvCurrent15Entry 4 }

-- %CLISHOWGROUP c15table.1
-- %CLICOLLABEL Queries
iShelfOntSdvCurrent15Queries OBJECT-TYPE
    SYNTAX      Counter32
    MAX-ACCESS  read-only
    STATUS      current
    DESCRIPTION
        "This counter is the number of membership queries
         sent during the interval."
    ::= { iShelfOntSdvCurrent15Entry 5 }

-- %CLISHOWGROUP c15table.1
-- %CLICOLLABEL Joins
iShelfOntSdvCurrent15Joins OBJECT-TYPE
    SYNTAX      Counter32
    MAX-ACCESS  read-only
    STATUS      current
    DESCRIPTION
        "This counter is the number of membership reports
         received during the interval."
    ::= { iShelfOntSdvCurrent15Entry 6 }

-- %CLISHOWGROUP c15table.1
-- %CLICOLLABEL Leaves
iShelfOntSdvCurrent15Leaves OBJECT-TYPE
    SYNTAX      Counter32
    MAX-ACCESS  read-only
    STATUS      current
    DESCRIPTION
        "This counter is the number of leave requests
         received during the interval."
    ::= { iShelfOntSdvCurrent15Entry 7 }

-- %CLISHOWGROUP c15table.2
-- %CLICOLLABEL Timeout
-- %CLIWIDTH 8
iShelfOntSdvCurrent15Timeout OBJECT-TYPE
    SYNTAX      Counter32
    MAX-ACCESS  read-only
    STATUS      current
    DESCRIPTION
        "This counter is the number of membership timeouts
         during the interval."
    ::= { iShelfOntSdvCurrent15Entry 8 }

-- %CLISHOWGROUP c15table.2
-- %CLICOLLABEL Forced
-- %CLIWIDTH 8
iShelfOntSdvCurrent15JoinsForced OBJECT-TYPE
    SYNTAX      Counter32
    MAX-ACCESS  read-only
    STATUS      current
    DESCRIPTION
        "This counter is the total of forced joins
         during the interval."
    ::= { iShelfOntSdvCurrent15Entry 9 }

-- %CLISHOWGROUP c15table.2
-- %CLICOLLABEL Limit
-- %CLIWIDTH 8
iShelfOntSdvCurrent15JoinErrlimit OBJECT-TYPE
    SYNTAX      Counter32
    MAX-ACCESS  read-only
    STATUS      current
    DESCRIPTION
        "This counter is the number of join attempts denied
         because they exceeded the provisioned stream limit
         during the interval."
    ::= { iShelfOntSdvCurrent15Entry 10 }

-- %CLISHOWGROUP c15table.2
-- %CLICOLLABEL Access
-- %CLIWIDTH 8
iShelfOntSdvCurrent15JoinErrAccess OBJECT-TYPE
    SYNTAX      Counter32
    MAX-ACCESS  read-only
    STATUS      current
    DESCRIPTION
        "This counter is the number of join attempts denied
         because the cannel was not in the provisioned maps
         during the interval."
    ::= { iShelfOntSdvCurrent15Entry 11 }

-- %CLISHOWGROUP c15table.2
-- %CLICOLLABEL non-sdv
-- %CLIWIDTH 8
iShelfOntSdvCurrent15JoinErrNotsdv OBJECT-TYPE
    SYNTAX      Counter32
    MAX-ACCESS  read-only
    STATUS      current
    DESCRIPTION
        "This counter is the number of join attempts denied
         because the source of the request was on a configured
         sdv device during the interval."
    ::= { iShelfOntSdvCurrent15Entry 12 }

-- %CLISHOWGROUP c15table.2
-- %CLICOLLABEL inactive
-- %CLIWIDTH 7
iShelfOntSdvCurrent15Inactivate OBJECT-TYPE
    SYNTAX      Counter32
    MAX-ACCESS  read-only
    STATUS      current
    DESCRIPTION
        "This counter is the number of inactivated stream
         due to system resource limitations during the interval."
    ::= { iShelfOntSdvCurrent15Entry 13 }


-- %CLISHOWGROUP c15table.1
-- %CLIWIDTH 5
iShelfOntSdvCurrent15ValidData OBJECT-TYPE
    SYNTAX      IShelfPerfInvalidFlag
    MAX-ACCESS  read-only
    STATUS      current
    DESCRIPTION
        "This object indicates if the data for this interval
         is valid."
    ::= { iShelfOntSdvCurrent15Entry 14 }

-- %CLISHOWGROUP c15table.1
iShelfOntSdvCurrent15ThresholdCrossingPointer OBJECT-TYPE
    SYNTAX      IShelfThresholdCrossingPointer
    MAX-ACCESS  read-write
    STATUS      current
    DESCRIPTION
        "This object points to the threshold crossing entry
         (in iShelfThresholdCrossingTable). A value of zero
         indicates threshold crossing are not being generated."
    DEFVAL      { 0 }
    ::= { iShelfOntSdvCurrent15Entry 15 }


-- ++++++++++++++++++++++++++++++++++++++++++++++++++++++++++++++++++++++++
--
-- iShelfOntSdvInterval15Table - 
--
-- ++++++++++++++++++++++++++++++++++++++++++++++++++++++++++++++++++++++++

-- %CLICMDPREFIX ont:pm:sdv
-- %CLICMDABBR i15table
-- %CLISHOWGROUP i15table
iShelfOntSdvInterval15Table OBJECT-TYPE
    SYNTAX      SEQUENCE OF IShelfOntSdvInterval15Entry
    MAX-ACCESS  not-accessible
    STATUS      current
    DESCRIPTION
        "This table contains performance history data pertaining
         to ONT SDV Services for the previous 15 minute intervals.
         Rows in this table are automatically created."
    ::= { iShelfOntPm 14 }

iShelfOntSdvInterval15Entry OBJECT-TYPE
    SYNTAX      IShelfOntSdvInterval15Entry
    MAX-ACCESS  not-accessible
    STATUS      current
    DESCRIPTION
        "Each entry contains performance history data for one
         instance of SDV Service."
    INDEX       { iShelfOntSdvInterval15LogicalId,
                  iShelfOntSdvInterval15SLCIndex,
                  iShelfOntSdvInterval15Port,
                  iShelfOntSdvInterval15Number }
    ::= { iShelfOntSdvInterval15Table 1 }

IShelfOntSdvInterval15Entry ::=
    SEQUENCE {
        iShelfOntSdvInterval15LogicalId
            IShelfOntLogicalId,
        iShelfOntSdvInterval15SLCIndex
            IShelfOntSubscriberLineCardIndex,
        iShelfOntSdvInterval15Port
            INTEGER,
        iShelfOntSdvInterval15Number
            INTEGER,
        iShelfOntSdvInterval15PeakStreams
            Counter32,
        iShelfOntSdvInterval15Queries
            Counter32,
        iShelfOntSdvInterval15Joins
            Counter32,
        iShelfOntSdvInterval15Leaves
            Counter32,
        iShelfOntSdvInterval15Timeout
            Counter32,
        iShelfOntSdvInterval15JoinsForced
            Counter32,
        iShelfOntSdvInterval15JoinErrlimit
            Counter32,
        iShelfOntSdvInterval15JoinErrAccess
            Counter32,
        iShelfOntSdvInterval15JoinErrNotsdv
            Counter32,
        iShelfOntSdvInterval15Inactivate
            Counter32,
        iShelfOntSdvInterval15ValidData
            IShelfPerfInvalidFlag
    }

-- %CLISHOWGROUP i15table.1
-- %CLISHOWGROUP i15table.2
-- %CLIWIDTH 3
iShelfOntSdvInterval15LogicalId OBJECT-TYPE
    SYNTAX      IShelfOntLogicalId
    MAX-ACCESS  read-only
    STATUS      current
    DESCRIPTION "This object identifies the logical ID of the ONT."
    ::= { iShelfOntSdvInterval15Entry 1 }

-- %CLISHOWGROUP i15table.1
-- %CLISHOWGROUP i15table.2
iShelfOntSdvInterval15SLCIndex OBJECT-TYPE
    SYNTAX      IShelfOntSubscriberLineCardIndex
    MAX-ACCESS  read-only
    STATUS      current
    DESCRIPTION
        "This object identifies the ONT subscriber line card
         index."
    ::= { iShelfOntSdvInterval15Entry 2 }

-- %CLISHOWGROUP i15table.1
-- %CLISHOWGROUP i15table.2
iShelfOntSdvInterval15Port OBJECT-TYPE
    SYNTAX      INTEGER (1..4)
    MAX-ACCESS  read-only
    STATUS      current
    DESCRIPTION "This object identifies the ethernet port number."
    ::= { iShelfOntSdvInterval15Entry 3 }

-- %CLISHOWGROUP i15table.1
-- %CLISHOWGROUP i15table.2
-- %CLICOLLABEL Int
-- %CLIWIDTH 3
iShelfOntSdvInterval15Number OBJECT-TYPE
    SYNTAX      INTEGER(1..32)
    MAX-ACCESS  read-only
    STATUS      current
    DESCRIPTION
        "This object identifies the interval for which this set
         of statistics is available. The interval identified
         by 1 is the most recently completed 15 minute interval."
    ::= { iShelfOntSdvInterval15Entry 4 }


-- //PMPARAMTYPE PEAK
-- %CLISHOWGROUP i15table.1
-- %CLICOLLABEL Peak-Strms
iShelfOntSdvInterval15PeakStreams OBJECT-TYPE
    SYNTAX      Counter32
    MAX-ACCESS  read-only
    STATUS      current
    DESCRIPTION
        "This counter is the maximum concurent streams
         joined during the interval."
    ::= { iShelfOntSdvInterval15Entry 5 }

-- %CLISHOWGROUP i15table.1
-- %CLICOLLABEL Queries
iShelfOntSdvInterval15Queries OBJECT-TYPE
    SYNTAX      Counter32
    MAX-ACCESS  read-only
    STATUS      current
    DESCRIPTION
        "This counter is the number of membership queries
         sent during the interval."
    ::= { iShelfOntSdvInterval15Entry 6 }

-- %CLISHOWGROUP i15table.1
-- %CLICOLLABEL Joins
iShelfOntSdvInterval15Joins OBJECT-TYPE
    SYNTAX      Counter32
    MAX-ACCESS  read-only
    STATUS      current
    DESCRIPTION
        "This counter is the number of membership reports
         received during the interval."
    ::= { iShelfOntSdvInterval15Entry 7 }

-- %CLISHOWGROUP i15table.1
-- %CLICOLLABEL Leaves
iShelfOntSdvInterval15Leaves OBJECT-TYPE
    SYNTAX      Counter32
    MAX-ACCESS  read-only
    STATUS      current
    DESCRIPTION
        "This counter is the number of leave requests
         received during the interval."
    ::= { iShelfOntSdvInterval15Entry 8 }

-- %CLISHOWGROUP i15table.2
-- %CLICOLLABEL Timeout
-- %CLIWIDTH 8
iShelfOntSdvInterval15Timeout OBJECT-TYPE
    SYNTAX      Counter32
    MAX-ACCESS  read-only
    STATUS      current
    DESCRIPTION
        "This counter is the number of membership timeouts
         during the interval."
    ::= { iShelfOntSdvInterval15Entry 9 }

-- %CLISHOWGROUP i15table.2
-- %CLICOLLABEL Forced
-- %CLIWIDTH 8
iShelfOntSdvInterval15JoinsForced OBJECT-TYPE
    SYNTAX      Counter32
    MAX-ACCESS  read-only
    STATUS      current
    DESCRIPTION
        "This counter is the total of forced joins
         during the interval."
    ::= { iShelfOntSdvInterval15Entry 10 }

-- %CLISHOWGROUP i15table.2
-- %CLICOLLABEL Limit
-- %CLIWIDTH 8
iShelfOntSdvInterval15JoinErrlimit OBJECT-TYPE
    SYNTAX      Counter32
    MAX-ACCESS  read-only
    STATUS      current
    DESCRIPTION
        "This counter is the number of join attempts denied
         because they exceeded the provisioned stream limit
         during the interval."
    ::= { iShelfOntSdvInterval15Entry 11 }

-- %CLISHOWGROUP i15table.2
-- %CLICOLLABEL Access
-- %CLIWIDTH 8
iShelfOntSdvInterval15JoinErrAccess OBJECT-TYPE
    SYNTAX      Counter32
    MAX-ACCESS  read-only
    STATUS      current
    DESCRIPTION
        "This counter is the number of join attempts denied
         because the cannel was not in the provisioned maps
         during the interval."
    ::= { iShelfOntSdvInterval15Entry 12 }

-- %CLISHOWGROUP i15table.2
-- %CLICOLLABEL non-sdv
-- %CLIWIDTH 8
iShelfOntSdvInterval15JoinErrNotsdv OBJECT-TYPE
    SYNTAX      Counter32
    MAX-ACCESS  read-only
    STATUS      current
    DESCRIPTION
        "This counter is the number of join attempts denied
         because the source of the request was on a configured
         sdv device during the interval."
    ::= { iShelfOntSdvInterval15Entry 13 }

-- %CLISHOWGROUP i15table.2
-- %CLICOLLABEL inactive
-- %CLIWIDTH 7
iShelfOntSdvInterval15Inactivate OBJECT-TYPE
    SYNTAX      Counter32
    MAX-ACCESS  read-only
    STATUS      current
    DESCRIPTION
        "This counter is the number of inactivated stream
         due to system resource limitations during the interval."
    ::= { iShelfOntSdvInterval15Entry 14 }


-- %CLISHOWGROUP i15table.1
-- %CLIWIDTH 5
iShelfOntSdvInterval15ValidData OBJECT-TYPE
    SYNTAX      IShelfPerfInvalidFlag
    MAX-ACCESS  read-only
    STATUS      current
    DESCRIPTION
        "This object indicates if the data for this interval
         is valid."
    ::= { iShelfOntSdvInterval15Entry 15 }


-- ++++++++++++++++++++++++++++++++++++++++++++++++++++++++++++++++++++++++
--
-- iShelfOntSdvCurrent24Table - 
--
-- ++++++++++++++++++++++++++++++++++++++++++++++++++++++++++++++++++++++++

-- %CLICMDPREFIX ont:pm:sdv
-- %CLICMDABBR c24table
-- %CLISHOWGROUP c24table
iShelfOntSdvCurrent24Table OBJECT-TYPE
    SYNTAX      SEQUENCE OF IShelfOntSdvCurrent24Entry
    MAX-ACCESS  not-accessible
    STATUS      current
    DESCRIPTION
        "This table contains performance history data pertaining
         to ONT SDV Services for the current 24 hour interval.
         Threshold crossing alerts may be applied to
         the counters in this table.
         Rows in this table are automatically created."
    ::= { iShelfOntPm 15 }

iShelfOntSdvCurrent24Entry OBJECT-TYPE
    SYNTAX      IShelfOntSdvCurrent24Entry
    MAX-ACCESS  not-accessible
    STATUS      current
    DESCRIPTION
        "Each entry contains performance history data for one
         instance of SDV Service."
    INDEX       { iShelfOntSdvCurrent24LogicalId,
                  iShelfOntSdvCurrent24SLCIndex,
                  iShelfOntSdvCurrent24Port }
    ::= { iShelfOntSdvCurrent24Table 1 }

IShelfOntSdvCurrent24Entry ::=
    SEQUENCE {
        iShelfOntSdvCurrent24LogicalId
            IShelfOntLogicalId,
        iShelfOntSdvCurrent24SLCIndex
            IShelfOntSubscriberLineCardIndex,
        iShelfOntSdvCurrent24Port
            INTEGER,
        iShelfOntSdvCurrent24PeakStreams
            Counter32,
        iShelfOntSdvCurrent24Queries
            Counter32,
        iShelfOntSdvCurrent24Joins
            Counter32,
        iShelfOntSdvCurrent24Leaves
            Counter32,
        iShelfOntSdvCurrent24Timeout
            Counter32,
        iShelfOntSdvCurrent24JoinsForced
            Counter32,
        iShelfOntSdvCurrent24JoinErrlimit
            Counter32,
        iShelfOntSdvCurrent24JoinErrAccess
            Counter32,
        iShelfOntSdvCurrent24JoinErrNotsdv
            Counter32,
        iShelfOntSdvCurrent24Inactivate
            Counter32,
        iShelfOntSdvCurrent24ValidData
            IShelfPerfInvalidFlag,
        iShelfOntSdvCurrent24ThresholdCrossingPointer
            IShelfThresholdCrossingPointer
    }

-- %CLISHOWGROUP c24table.1
-- %CLISHOWGROUP c24table.2
-- %CLIWIDTH 3
iShelfOntSdvCurrent24LogicalId OBJECT-TYPE
    SYNTAX      IShelfOntLogicalId
    MAX-ACCESS  read-only
    STATUS      current
    DESCRIPTION "This object identifies the logical ID of the ONT."
    ::= { iShelfOntSdvCurrent24Entry 1 }

-- %CLISHOWGROUP c24table.1
-- %CLISHOWGROUP c24table.2
iShelfOntSdvCurrent24SLCIndex OBJECT-TYPE
    SYNTAX      IShelfOntSubscriberLineCardIndex
    MAX-ACCESS  read-only
    STATUS      current
    DESCRIPTION
        "This object identifies the ONT subscriber line card
         index."
    ::= { iShelfOntSdvCurrent24Entry 2 }

-- %CLISHOWGROUP c24table.1
-- %CLISHOWGROUP c24table.2
iShelfOntSdvCurrent24Port OBJECT-TYPE
    SYNTAX      INTEGER (1..4)
    MAX-ACCESS  read-only
    STATUS      current
    DESCRIPTION "This object identifies the ethernet port number."
    ::= { iShelfOntSdvCurrent24Entry 3 }


-- //PMPARAMTYPE PEAK
-- %CLISHOWGROUP c24table.1
-- %CLICOLLABEL Peak-Strms
iShelfOntSdvCurrent24PeakStreams OBJECT-TYPE
    SYNTAX      Counter32
    MAX-ACCESS  read-only
    STATUS      current
    DESCRIPTION
        "This counter is the maximum concurent streams
         joined during the interval."
    ::= { iShelfOntSdvCurrent24Entry 4 }

-- %CLISHOWGROUP c24table.1
-- %CLICOLLABEL Queries
iShelfOntSdvCurrent24Queries OBJECT-TYPE
    SYNTAX      Counter32
    MAX-ACCESS  read-only
    STATUS      current
    DESCRIPTION
        "This counter is the number of membership queries
         sent during the interval."
    ::= { iShelfOntSdvCurrent24Entry 5 }

-- %CLISHOWGROUP c24table.1
-- %CLICOLLABEL Joins
iShelfOntSdvCurrent24Joins OBJECT-TYPE
    SYNTAX      Counter32
    MAX-ACCESS  read-only
    STATUS      current
    DESCRIPTION
        "This counter is the number of membership reports
         received during the interval."
    ::= { iShelfOntSdvCurrent24Entry 6 }

-- %CLISHOWGROUP c24table.1
-- %CLICOLLABEL Leaves
iShelfOntSdvCurrent24Leaves OBJECT-TYPE
    SYNTAX      Counter32
    MAX-ACCESS  read-only
    STATUS      current
    DESCRIPTION
        "This counter is the number of leave requests
         received during the interval."
    ::= { iShelfOntSdvCurrent24Entry 7 }

-- %CLISHOWGROUP c24table.2
-- %CLICOLLABEL Timeout
-- %CLIWIDTH 8
iShelfOntSdvCurrent24Timeout OBJECT-TYPE
    SYNTAX      Counter32
    MAX-ACCESS  read-only
    STATUS      current
    DESCRIPTION
        "This counter is the number of membership timeouts
         during the interval."
    ::= { iShelfOntSdvCurrent24Entry 8 }

-- %CLISHOWGROUP c24table.2
-- %CLICOLLABEL Forced
-- %CLIWIDTH 8
iShelfOntSdvCurrent24JoinsForced OBJECT-TYPE
    SYNTAX      Counter32
    MAX-ACCESS  read-only
    STATUS      current
    DESCRIPTION
        "This counter is the total of forced joins
         during the interval."
    ::= { iShelfOntSdvCurrent24Entry 9 }

-- %CLISHOWGROUP c24table.2
-- %CLICOLLABEL Limit
-- %CLIWIDTH 8
iShelfOntSdvCurrent24JoinErrlimit OBJECT-TYPE
    SYNTAX      Counter32
    MAX-ACCESS  read-only
    STATUS      current
    DESCRIPTION
        "This counter is the number of join attempts denied
         because they exceeded the provisioned stream limit
         during the interval."
    ::= { iShelfOntSdvCurrent24Entry 10 }

-- %CLISHOWGROUP c24table.2
-- %CLICOLLABEL Access
-- %CLIWIDTH 8
iShelfOntSdvCurrent24JoinErrAccess OBJECT-TYPE
    SYNTAX      Counter32
    MAX-ACCESS  read-only
    STATUS      current
    DESCRIPTION
        "This counter is the number of join attempts denied
         because the cannel was not in the provisioned maps
         during the interval."
    ::= { iShelfOntSdvCurrent24Entry 11 }

-- %CLISHOWGROUP c24table.2
-- %CLICOLLABEL non-sdv
-- %CLIWIDTH 8
iShelfOntSdvCurrent24JoinErrNotsdv OBJECT-TYPE
    SYNTAX      Counter32
    MAX-ACCESS  read-only
    STATUS      current
    DESCRIPTION
        "This counter is the number of join attempts denied
         because the source of the request was on a configured
         sdv device during the interval."
    ::= { iShelfOntSdvCurrent24Entry 12 }

-- %CLISHOWGROUP c24table.2
-- %CLICOLLABEL inactive
-- %CLIWIDTH 7
iShelfOntSdvCurrent24Inactivate OBJECT-TYPE
    SYNTAX      Counter32
    MAX-ACCESS  read-only
    STATUS      current
    DESCRIPTION
        "This counter is the number of inactivated stream
         due to system resource limitations during the interval."
    ::= { iShelfOntSdvCurrent24Entry 13 }



-- %CLISHOWGROUP c24table.1
-- %CLIWIDTH 5
iShelfOntSdvCurrent24ValidData OBJECT-TYPE
    SYNTAX      IShelfPerfInvalidFlag
    MAX-ACCESS  read-only
    STATUS      current
    DESCRIPTION
        "This object indicates if the data for this interval
         is valid."
    ::= { iShelfOntSdvCurrent24Entry 14 }

-- %CLISHOWGROUP c24table.1
iShelfOntSdvCurrent24ThresholdCrossingPointer OBJECT-TYPE
    SYNTAX      IShelfThresholdCrossingPointer
    MAX-ACCESS  read-write
    STATUS      current
    DESCRIPTION
        "This object points to the threshold crossing entry
         (in iShelfThresholdCrossingTable). A value of zero
         indicates threshold crossing are not being generated."
    DEFVAL      { 0 }
    ::= { iShelfOntSdvCurrent24Entry 15 }

-- ++++++++++++++++++++++++++++++++++++++++++++++++++++++++++++++++++++++++
--
-- iShelfOntSdvInterval24Table - 
--
-- ++++++++++++++++++++++++++++++++++++++++++++++++++++++++++++++++++++++++

-- %CLICMDPREFIX ont:pm:sdv
-- %CLICMDABBR i24table
-- %CLISHOWGROUP i24table
iShelfOntSdvInterval24Table OBJECT-TYPE
    SYNTAX      SEQUENCE OF IShelfOntSdvInterval24Entry
    MAX-ACCESS  not-accessible
    STATUS      current
    DESCRIPTION
        "This table contains performance history data pertaining
         to ONT SDV Services for the previous 24 hour intervals.
         Rows in this table are automatically created."
    ::= { iShelfOntPm 16 }

iShelfOntSdvInterval24Entry OBJECT-TYPE
    SYNTAX      IShelfOntSdvInterval24Entry
    MAX-ACCESS  not-accessible
    STATUS      current
    DESCRIPTION
        "Each entry contains performance history data for one
         instance of SDV Service."
    INDEX       { iShelfOntSdvInterval24LogicalId,
                  iShelfOntSdvInterval24SLCIndex,
                  iShelfOntSdvInterval24Port,
                  iShelfOntSdvInterval24Number }
    ::= { iShelfOntSdvInterval24Table 1 }

IShelfOntSdvInterval24Entry ::=
    SEQUENCE {
        iShelfOntSdvInterval24LogicalId
            IShelfOntLogicalId,
        iShelfOntSdvInterval24SLCIndex
            IShelfOntSubscriberLineCardIndex,
        iShelfOntSdvInterval24Port
            INTEGER,
        iShelfOntSdvInterval24Number
            INTEGER,
        iShelfOntSdvInterval24PeakStreams
            Counter32,
        iShelfOntSdvInterval24Queries
            Counter32,
        iShelfOntSdvInterval24Joins
            Counter32,
        iShelfOntSdvInterval24Leaves
            Counter32,
        iShelfOntSdvInterval24Timeout
            Counter32,
        iShelfOntSdvInterval24JoinsForced
            Counter32,
        iShelfOntSdvInterval24JoinErrlimit
            Counter32,
        iShelfOntSdvInterval24JoinErrAccess
            Counter32,
        iShelfOntSdvInterval24JoinErrNotsdv
            Counter32,
        iShelfOntSdvInterval24Inactivate
            Counter32,
        iShelfOntSdvInterval24ValidData
            IShelfPerfInvalidFlag
    }

-- %CLISHOWGROUP i24table.1
-- %CLISHOWGROUP i24table.2
-- %CLIWIDTH 3
iShelfOntSdvInterval24LogicalId OBJECT-TYPE
    SYNTAX      IShelfOntLogicalId
    MAX-ACCESS  read-only
    STATUS      current
    DESCRIPTION "This object identifies the logical ID of the ONT."
    ::= { iShelfOntSdvInterval24Entry 1 }

-- %CLISHOWGROUP i24table.1
-- %CLISHOWGROUP i24table.2
iShelfOntSdvInterval24SLCIndex OBJECT-TYPE
    SYNTAX      IShelfOntSubscriberLineCardIndex
    MAX-ACCESS  read-only
    STATUS      current
    DESCRIPTION
        "This object identifies the ONT subscriber line card
         index."
    ::= { iShelfOntSdvInterval24Entry 2 }

-- %CLISHOWGROUP i24table.1
-- %CLISHOWGROUP i24table.2
iShelfOntSdvInterval24Port OBJECT-TYPE
    SYNTAX      INTEGER (1..4)
    MAX-ACCESS  read-only
    STATUS      current
    DESCRIPTION "This object identifies the ethernet port number."
    ::= { iShelfOntSdvInterval24Entry 3 }

-- %CLISHOWGROUP i24table.1
-- %CLISHOWGROUP i24table.2
-- %CLICOLLABEL Int
-- %CLIWIDTH 3
iShelfOntSdvInterval24Number OBJECT-TYPE
    SYNTAX      INTEGER(1..6)
    MAX-ACCESS  read-only
    STATUS      current
    DESCRIPTION
        "This object identifies the interval for which this set
         of statistics is available. The interval identified
         by 1 is the most recently completed 24 hour interval."
    ::= { iShelfOntSdvInterval24Entry 4 }



-- //PMPARAMTYPE PEAK
-- %CLISHOWGROUP i24table.1
-- %CLICOLLABEL Peak-Strms
iShelfOntSdvInterval24PeakStreams OBJECT-TYPE
    SYNTAX      Counter32
    MAX-ACCESS  read-only
    STATUS      current
    DESCRIPTION
        "This counter is the maximum concurent streams
         joined during the interval."
    ::= { iShelfOntSdvInterval24Entry 5 }

-- %CLISHOWGROUP i24table.1
-- %CLICOLLABEL Queries
iShelfOntSdvInterval24Queries OBJECT-TYPE
    SYNTAX      Counter32
    MAX-ACCESS  read-only
    STATUS      current
    DESCRIPTION
        "This counter is the number of membership queries
         sent during the interval."
    ::= { iShelfOntSdvInterval24Entry 6 }

-- %CLISHOWGROUP i24table.1
-- %CLICOLLABEL Joins
iShelfOntSdvInterval24Joins OBJECT-TYPE
    SYNTAX      Counter32
    MAX-ACCESS  read-only
    STATUS      current
    DESCRIPTION
        "This counter is the number of membership reports
         received during the interval."
    ::= { iShelfOntSdvInterval24Entry 7 }

-- %CLISHOWGROUP i24table.1
-- %CLICOLLABEL Leaves
iShelfOntSdvInterval24Leaves OBJECT-TYPE
    SYNTAX      Counter32
    MAX-ACCESS  read-only
    STATUS      current
    DESCRIPTION
        "This counter is the number of leave requests
         received during the interval."
    ::= { iShelfOntSdvInterval24Entry 8 }

-- %CLISHOWGROUP i24table.2
-- %CLICOLLABEL Timeout
-- %CLIWIDTH 8
iShelfOntSdvInterval24Timeout OBJECT-TYPE
    SYNTAX      Counter32
    MAX-ACCESS  read-only
    STATUS      current
    DESCRIPTION
        "This counter is the number of membership timeouts
         during the interval."
    ::= { iShelfOntSdvInterval24Entry 9 }

-- %CLISHOWGROUP i24table.2
-- %CLICOLLABEL Forced
-- %CLIWIDTH 8
iShelfOntSdvInterval24JoinsForced OBJECT-TYPE
    SYNTAX      Counter32
    MAX-ACCESS  read-only
    STATUS      current
    DESCRIPTION
        "This counter is the total of forced joins
         during the interval."
    ::= { iShelfOntSdvInterval24Entry 10 }

-- %CLISHOWGROUP i24table.2
-- %CLICOLLABEL Limit
-- %CLIWIDTH 8
iShelfOntSdvInterval24JoinErrlimit OBJECT-TYPE
    SYNTAX      Counter32
    MAX-ACCESS  read-only
    STATUS      current
    DESCRIPTION
        "This counter is the number of join attempts denied
         because they exceeded the provisioned stream limit
         during the interval."
    ::= { iShelfOntSdvInterval24Entry 11 }

-- %CLISHOWGROUP i24table.2
-- %CLICOLLABEL Access
-- %CLIWIDTH 8
iShelfOntSdvInterval24JoinErrAccess OBJECT-TYPE
    SYNTAX      Counter32
    MAX-ACCESS  read-only
    STATUS      current
    DESCRIPTION
        "This counter is the number of join attempts denied
         because the cannel was not in the provisioned maps
         during the interval."
    ::= { iShelfOntSdvInterval24Entry 12 }

-- %CLISHOWGROUP i24table.2
-- %CLICOLLABEL non-sdv
-- %CLIWIDTH 8
iShelfOntSdvInterval24JoinErrNotsdv OBJECT-TYPE
    SYNTAX      Counter32
    MAX-ACCESS  read-only
    STATUS      current
    DESCRIPTION
        "This counter is the number of join attempts denied
         because the source of the request was on a configured
         sdv device during the interval."
    ::= { iShelfOntSdvInterval24Entry 13 }

-- %CLISHOWGROUP i24table.2
-- %CLICOLLABEL inactive
-- %CLIWIDTH 7
iShelfOntSdvInterval24Inactivate OBJECT-TYPE
    SYNTAX      Counter32
    MAX-ACCESS  read-only
    STATUS      current
    DESCRIPTION
        "This counter is the number of inactivated stream
         due to system resource limitations during the interval."
    ::= { iShelfOntSdvInterval24Entry 14 }


-- %CLISHOWGROUP i24table.1
-- %CLIWIDTH 5
iShelfOntSdvInterval24ValidData OBJECT-TYPE
    SYNTAX      IShelfPerfInvalidFlag
    MAX-ACCESS  read-only
    STATUS      current
    DESCRIPTION
        "This object indicates if the data for this interval
         is valid."
    ::= { iShelfOntSdvInterval24Entry 15 }

-- ++++++++++++++++++++++++++++++++++++++++++++++++++++++++++++++++++++++++
--
-- iShelfOntPPPoECurrent15Table - 
--
-- ++++++++++++++++++++++++++++++++++++++++++++++++++++++++++++++++++++++++

-- %CLICMDPREFIX ont:pm:pppoe
-- %CLICMDABBR c15table
-- %CLISHOWGROUP c15table
iShelfOntPPPoECurrent15Table OBJECT-TYPE
    SYNTAX      SEQUENCE OF IShelfOntPPPoECurrent15Entry
    MAX-ACCESS  not-accessible
    STATUS      current
    DESCRIPTION
        "This table contains performance history data pertaining
         to ONT PPPoE Services for the current 15 minute interval.
         Threshold crossing alerts may be applied to
         the counters in this table.
         Rows in this table are automatically created."
    ::= { iShelfOntPm 17 }

iShelfOntPPPoECurrent15Entry OBJECT-TYPE
    SYNTAX      IShelfOntPPPoECurrent15Entry
    MAX-ACCESS  not-accessible
    STATUS      current
    DESCRIPTION
        "Each entry contains performance history data for one
         instance of PPPoE Service."
    INDEX       { iShelfOntPPPoECurrent15LogicalId,
                  iShelfOntPPPoECurrent15SLCIndex,
                  iShelfOntPPPoECurrent15Port }
    ::= { iShelfOntPPPoECurrent15Table 1 }

IShelfOntPPPoECurrent15Entry ::=
    SEQUENCE {
        iShelfOntPPPoECurrent15LogicalId
            IShelfOntLogicalId,
        iShelfOntPPPoECurrent15SLCIndex
            IShelfOntSubscriberLineCardIndex,
        iShelfOntPPPoECurrent15Port
            INTEGER,
        iShelfOntPPPoECurrent15PeakDialogs
            Counter32,
        iShelfOntPPPoECurrent15Discovries
            Counter32,
        iShelfOntPPPoECurrent15DiscoveryDrops
            Counter32,
        iShelfOntPPPoECurrent15InactivityDrops
            Counter32,
        iShelfOntPPPoECurrent15ResourceErrors
            Counter32,
        iShelfOntPPPoECurrent15InPackets
            Counter32,
        iShelfOntPPPoECurrent15InOctets
            Counter32,
        iShelfOntPPPoECurrent15OutPackets
            Counter32,
        iShelfOntPPPoECurrent15OutOctets
            Counter32,
        iShelfOntPPPoECurrent15ValidData
            IShelfPerfInvalidFlag,
        iShelfOntPPPoECurrent15ThresholdCrossingPointer
            IShelfThresholdCrossingPointer
    }

-- %CLISHOWGROUP c15table.1
-- %CLISHOWGROUP c15table.2
-- %CLIWIDTH 3
iShelfOntPPPoECurrent15LogicalId OBJECT-TYPE
    SYNTAX      IShelfOntLogicalId
    MAX-ACCESS  read-only
    STATUS      current
    DESCRIPTION "This object identifies the logical ID of the ONT."
    ::= { iShelfOntPPPoECurrent15Entry 1 }

-- %CLISHOWGROUP c15table.1
-- %CLISHOWGROUP c15table.2
iShelfOntPPPoECurrent15SLCIndex OBJECT-TYPE
    SYNTAX      IShelfOntSubscriberLineCardIndex
    MAX-ACCESS  read-only
    STATUS      current
    DESCRIPTION
        "This object identifies the ONT subscriber line card
         index."
    ::= { iShelfOntPPPoECurrent15Entry 2 }

-- %CLISHOWGROUP c15table.1
-- %CLISHOWGROUP c15table.2
iShelfOntPPPoECurrent15Port OBJECT-TYPE
    SYNTAX      INTEGER (1..4)
    MAX-ACCESS  read-only
    STATUS      current
    DESCRIPTION "This object identifies the ethernet port number."
    ::= { iShelfOntPPPoECurrent15Entry 3 }


-- //PMPARAMTYPE PEAK
-- %CLICOLLABEL Peak-Dia
-- %CLISHOWGROUP c15table.1
iShelfOntPPPoECurrent15PeakDialogs OBJECT-TYPE
    SYNTAX      Counter32
    MAX-ACCESS  read-only
    STATUS      current
    DESCRIPTION
        "This counter is the maximum concurent dialogs
         active during the interval."
    ::= { iShelfOntPPPoECurrent15Entry 4 }

-- %CLICOLLABEL Discoveries
-- %CLISHOWGROUP c15table.1
iShelfOntPPPoECurrent15Discovries OBJECT-TYPE
    SYNTAX      Counter32
    MAX-ACCESS  read-only
    STATUS      current
    DESCRIPTION
        "This counter is the number of discovery packets
         received during the interval."
    ::= { iShelfOntPPPoECurrent15Entry 5 }

-- %CLICOLLABEL DialogLimit
-- %CLISHOWGROUP c15table.1
iShelfOntPPPoECurrent15DiscoveryDrops OBJECT-TYPE
    SYNTAX      Counter32
    MAX-ACCESS  read-only
    STATUS      current
    DESCRIPTION
        "This counter is the number of discoveries that
         were dropped due to active dialogs limit exceeded
         during the interval."
    ::= { iShelfOntPPPoECurrent15Entry 6 }

-- %CLICOLLABEL Inactive
-- %CLISHOWGROUP c15table.1
iShelfOntPPPoECurrent15InactivityDrops OBJECT-TYPE
    SYNTAX      Counter32
    MAX-ACCESS  read-only
    STATUS      current
    DESCRIPTION
        "This counter is the number of dialogs that
         were dropped due to inactivity
         during the interval."
    ::= { iShelfOntPPPoECurrent15Entry 7 }

-- %CLICOLLABEL NoRes
-- %CLISHOWGROUP c15table.2
iShelfOntPPPoECurrent15ResourceErrors OBJECT-TYPE
    SYNTAX      Counter32
    MAX-ACCESS  read-only
    STATUS      current
    DESCRIPTION
        "This counter is the number of discoveries that
         were dropped due to lack of available PON bandwidth
         during the interval."
    ::= { iShelfOntPPPoECurrent15Entry 8 }

-- %CLICOLLABEL InPackets
-- %CLIWIDTH 8
-- %CLISHOWGROUP c15table.2
iShelfOntPPPoECurrent15InPackets OBJECT-TYPE
    SYNTAX      Counter32
    MAX-ACCESS  read-only
    STATUS      current
    DESCRIPTION
        "This counter is the total received packets
         during the interval."
    ::= { iShelfOntPPPoECurrent15Entry 9 }

-- %CLICOLLABEL InOctets
-- %CLISHOWGROUP c15table.2
iShelfOntPPPoECurrent15InOctets OBJECT-TYPE
    SYNTAX      Counter32
    MAX-ACCESS  read-only
    STATUS      current
    DESCRIPTION
        "This counter is the total received octets
         during the interval."
    ::= { iShelfOntPPPoECurrent15Entry 10 }

-- %CLICOLLABEL OutPackets
-- %CLISHOWGROUP c15table.2
iShelfOntPPPoECurrent15OutPackets OBJECT-TYPE
    SYNTAX      Counter32
    MAX-ACCESS  read-only
    STATUS      current
    DESCRIPTION
        "This counter is the total transmitted packets
         during the interval."
    ::= { iShelfOntPPPoECurrent15Entry 11 }

-- %CLICOLLABEL OutOctets
-- %CLISHOWGROUP c15table.2
iShelfOntPPPoECurrent15OutOctets OBJECT-TYPE
    SYNTAX      Counter32
    MAX-ACCESS  read-only
    STATUS      current
    DESCRIPTION
        "This counter is the total transmitted octets
         during the interval."
    ::= { iShelfOntPPPoECurrent15Entry 12 }


-- %CLISHOWGROUP c15table.1
-- %CLIWIDTH 5
iShelfOntPPPoECurrent15ValidData OBJECT-TYPE
    SYNTAX      IShelfPerfInvalidFlag
    MAX-ACCESS  read-only
    STATUS      current
    DESCRIPTION
        "This object indicates if the data for this interval
         is valid."
    ::= { iShelfOntPPPoECurrent15Entry 13 }

-- %CLISHOWGROUP c15table.1
iShelfOntPPPoECurrent15ThresholdCrossingPointer OBJECT-TYPE
    SYNTAX      IShelfThresholdCrossingPointer
    MAX-ACCESS  read-write
    STATUS      current
    DESCRIPTION
        "This object points to the threshold crossing entry
         (in iShelfThresholdCrossingTable). A value of zero
         indicates threshold crossing are not being generated."
    DEFVAL      { 0 }
    ::= { iShelfOntPPPoECurrent15Entry 14 }


-- ++++++++++++++++++++++++++++++++++++++++++++++++++++++++++++++++++++++++
--
-- iShelfOntPPPoEInterval15Table - 
--
-- ++++++++++++++++++++++++++++++++++++++++++++++++++++++++++++++++++++++++

-- %CLICMDPREFIX ont:pm:pppoe
-- %CLICMDABBR i15table
-- %CLISHOWGROUP i15table
iShelfOntPPPoEInterval15Table OBJECT-TYPE
    SYNTAX      SEQUENCE OF IShelfOntPPPoEInterval15Entry
    MAX-ACCESS  not-accessible
    STATUS      current
    DESCRIPTION
        "This table contains performance history data pertaining
         to ONT PPPoE Services for the previous 15 minute intervals.
         Rows in this table are automatically created."
    ::= { iShelfOntPm 18 }

iShelfOntPPPoEInterval15Entry OBJECT-TYPE
    SYNTAX      IShelfOntPPPoEInterval15Entry
    MAX-ACCESS  not-accessible
    STATUS      current
    DESCRIPTION
        "Each entry contains performance history data for one
         instance of PPPoE Service."
    INDEX       { iShelfOntPPPoEInterval15LogicalId,
                  iShelfOntPPPoEInterval15SLCIndex,
                  iShelfOntPPPoEInterval15Port,
                  iShelfOntPPPoEInterval15Number }
    ::= { iShelfOntPPPoEInterval15Table 1 }

IShelfOntPPPoEInterval15Entry ::=
    SEQUENCE {
        iShelfOntPPPoEInterval15LogicalId
            IShelfOntLogicalId,
        iShelfOntPPPoEInterval15SLCIndex
            IShelfOntSubscriberLineCardIndex,
        iShelfOntPPPoEInterval15Port
            INTEGER,
        iShelfOntPPPoEInterval15Number
            INTEGER,
        iShelfOntPPPoEInterval15PeakDialogs
            Counter32,
        iShelfOntPPPoEInterval15Discovries
            Counter32,
        iShelfOntPPPoEInterval15DiscoveryDrops
            Counter32,
        iShelfOntPPPoEInterval15InactivityDrops
            Counter32,
        iShelfOntPPPoEInterval15ResourceErrors
            Counter32,
        iShelfOntPPPoEInterval15InPackets
            Counter32,
        iShelfOntPPPoEInterval15InOctets
            Counter32,
        iShelfOntPPPoEInterval15OutPackets
            Counter32,
        iShelfOntPPPoEInterval15OutOctets
            Counter32,
        iShelfOntPPPoEInterval15ValidData
            IShelfPerfInvalidFlag
    }

-- %CLISHOWGROUP i15table.1
-- %CLISHOWGROUP i15table.2
-- %CLIWIDTH 3
iShelfOntPPPoEInterval15LogicalId OBJECT-TYPE
    SYNTAX      IShelfOntLogicalId
    MAX-ACCESS  read-only
    STATUS      current
    DESCRIPTION "This object identifies the logical ID of the ONT."
    ::= { iShelfOntPPPoEInterval15Entry 1 }

-- %CLISHOWGROUP i15table.1
-- %CLISHOWGROUP i15table.2
iShelfOntPPPoEInterval15SLCIndex OBJECT-TYPE
    SYNTAX      IShelfOntSubscriberLineCardIndex
    MAX-ACCESS  read-only
    STATUS      current
    DESCRIPTION
        "This object identifies the ONT subscriber line card
         index."
    ::= { iShelfOntPPPoEInterval15Entry 2 }

-- %CLISHOWGROUP i15table.1
-- %CLISHOWGROUP i15table.2
iShelfOntPPPoEInterval15Port OBJECT-TYPE
    SYNTAX      INTEGER (1..4)
    MAX-ACCESS  read-only
    STATUS      current
    DESCRIPTION "This object identifies the ethernet port number."
    ::= { iShelfOntPPPoEInterval15Entry 3 }

-- %CLISHOWGROUP i15table.1
-- %CLISHOWGROUP i15table.2
-- %CLICOLLABEL Int
-- %CLIWIDTH 3
iShelfOntPPPoEInterval15Number OBJECT-TYPE
    SYNTAX      INTEGER(1..32)
    MAX-ACCESS  read-only
    STATUS      current
    DESCRIPTION
        "This object identifies the interval for which this set
         of statistics is available. The interval identified
         by 1 is the most recently completed 15 minute interval."
    ::= { iShelfOntPPPoEInterval15Entry 4 }


-- //PMPARAMTYPE PEAK
-- %CLICOLLABEL Peak-Dia
-- %CLISHOWGROUP i15table.1
iShelfOntPPPoEInterval15PeakDialogs OBJECT-TYPE
    SYNTAX      Counter32
    MAX-ACCESS  read-only
    STATUS      current
    DESCRIPTION
        "This counter is the maximum concurent dialogs
         active during the interval."
    ::= { iShelfOntPPPoEInterval15Entry 5 }

-- %CLICOLLABEL Discoveries
-- %CLISHOWGROUP i15table.1
iShelfOntPPPoEInterval15Discovries OBJECT-TYPE
    SYNTAX      Counter32
    MAX-ACCESS  read-only
    STATUS      current
    DESCRIPTION
        "This counter is the number of discovery packets
         received during the interval."
    ::= { iShelfOntPPPoEInterval15Entry 6 }

-- %CLICOLLABEL DialogLimit
-- %CLISHOWGROUP i15table.1
iShelfOntPPPoEInterval15DiscoveryDrops OBJECT-TYPE
    SYNTAX      Counter32
    MAX-ACCESS  read-only
    STATUS      current
    DESCRIPTION
        "This counter is the number of discoveries that
         were dropped due to active dialogs limit exceeded
         during the interval."
    ::= { iShelfOntPPPoEInterval15Entry 7 }

-- %CLICOLLABEL Inactive
-- %CLISHOWGROUP i15table.1
iShelfOntPPPoEInterval15InactivityDrops OBJECT-TYPE
    SYNTAX      Counter32
    MAX-ACCESS  read-only
    STATUS      current
    DESCRIPTION
        "This counter is the number of dialogs that
         were dropped due to inactivity
         during the interval."
    ::= { iShelfOntPPPoEInterval15Entry 8 }

-- %CLICOLLABEL NoRes
-- %CLISHOWGROUP i15table.2
iShelfOntPPPoEInterval15ResourceErrors OBJECT-TYPE
    SYNTAX      Counter32
    MAX-ACCESS  read-only
    STATUS      current
    DESCRIPTION
        "This counter is the number of discoveries that
         were dropped due to lack of available PON bandwidth
         during the interval."
    ::= { iShelfOntPPPoEInterval15Entry 9 }

-- %CLICOLLABEL InPackets
-- %CLIWIDTH 8
-- %CLISHOWGROUP i15table.2
iShelfOntPPPoEInterval15InPackets OBJECT-TYPE
    SYNTAX      Counter32
    MAX-ACCESS  read-only
    STATUS      current
    DESCRIPTION
        "This counter is the total received packets
         during the interval."
    ::= { iShelfOntPPPoEInterval15Entry 10 }

-- %CLICOLLABEL InOctets
-- %CLISHOWGROUP i15table.2
iShelfOntPPPoEInterval15InOctets OBJECT-TYPE
    SYNTAX      Counter32
    MAX-ACCESS  read-only
    STATUS      current
    DESCRIPTION
        "This counter is the total received octets
         during the interval."
    ::= { iShelfOntPPPoEInterval15Entry 11 }

-- %CLICOLLABEL OutPackets
-- %CLISHOWGROUP i15table.2
iShelfOntPPPoEInterval15OutPackets OBJECT-TYPE
    SYNTAX      Counter32
    MAX-ACCESS  read-only
    STATUS      current
    DESCRIPTION
        "This counter is the total transmitted packets
         during the interval."
    ::= { iShelfOntPPPoEInterval15Entry 12 }

-- %CLICOLLABEL OutOctets
-- %CLISHOWGROUP i15table.2
iShelfOntPPPoEInterval15OutOctets OBJECT-TYPE
    SYNTAX      Counter32
    MAX-ACCESS  read-only
    STATUS      current
    DESCRIPTION
        "This counter is the total transmitted octets
         during the interval."
    ::= { iShelfOntPPPoEInterval15Entry 13 }


-- %CLISHOWGROUP i15table.1
-- %CLIWIDTH 5
iShelfOntPPPoEInterval15ValidData OBJECT-TYPE
    SYNTAX      IShelfPerfInvalidFlag
    MAX-ACCESS  read-only
    STATUS      current
    DESCRIPTION
        "This object indicates if the data for this interval
         is valid."
    ::= { iShelfOntPPPoEInterval15Entry 14 }


-- ++++++++++++++++++++++++++++++++++++++++++++++++++++++++++++++++++++++++
--
-- iShelfOntPPPoECurrent24Table - 
--
-- ++++++++++++++++++++++++++++++++++++++++++++++++++++++++++++++++++++++++

-- %CLICMDPREFIX ont:pm:pppoe
-- %CLICMDABBR c24table
-- %CLISHOWGROUP c24table
iShelfOntPPPoECurrent24Table OBJECT-TYPE
    SYNTAX      SEQUENCE OF IShelfOntPPPoECurrent24Entry
    MAX-ACCESS  not-accessible
    STATUS      current
    DESCRIPTION
        "This table contains performance history data pertaining
         to ONT PPPoE Services for the current 24 hour interval.
         Threshold crossing alerts may be applied to
         the counters in this table.
         Rows in this table are automatically created."
    ::= { iShelfOntPm 19 }

iShelfOntPPPoECurrent24Entry OBJECT-TYPE
    SYNTAX      IShelfOntPPPoECurrent24Entry
    MAX-ACCESS  not-accessible
    STATUS      current
    DESCRIPTION
        "Each entry contains performance history data for one
         instance of PPPoE Service."
    INDEX       { iShelfOntPPPoECurrent24LogicalId,
                  iShelfOntPPPoECurrent24SLCIndex,
                  iShelfOntPPPoECurrent24Port }
    ::= { iShelfOntPPPoECurrent24Table 1 }

IShelfOntPPPoECurrent24Entry ::=
    SEQUENCE {
        iShelfOntPPPoECurrent24LogicalId
            IShelfOntLogicalId,
        iShelfOntPPPoECurrent24SLCIndex
            IShelfOntSubscriberLineCardIndex,
        iShelfOntPPPoECurrent24Port
            INTEGER,
        iShelfOntPPPoECurrent24PeakDialogs
            Counter32,
        iShelfOntPPPoECurrent24Discovries
            Counter32,
        iShelfOntPPPoECurrent24DiscoveryDrops
            Counter32,
        iShelfOntPPPoECurrent24InactivityDrops
            Counter32,
        iShelfOntPPPoECurrent24ResourceErrors
            Counter32,
        iShelfOntPPPoECurrent24InPackets
            Counter32,
        iShelfOntPPPoECurrent24InOctets
            Counter32,
        iShelfOntPPPoECurrent24OutPackets
            Counter32,
        iShelfOntPPPoECurrent24OutOctets
            Counter32,
        iShelfOntPPPoECurrent24ValidData
            IShelfPerfInvalidFlag,
        iShelfOntPPPoECurrent24ThresholdCrossingPointer
            IShelfThresholdCrossingPointer
    }

-- %CLISHOWGROUP c24table.1
-- %CLISHOWGROUP c24table.2
-- %CLIWIDTH 3
iShelfOntPPPoECurrent24LogicalId OBJECT-TYPE
    SYNTAX      IShelfOntLogicalId
    MAX-ACCESS  read-only
    STATUS      current
    DESCRIPTION "This object identifies the logical ID of the ONT."
    ::= { iShelfOntPPPoECurrent24Entry 1 }

-- %CLISHOWGROUP c24table.1
-- %CLISHOWGROUP c24table.2
iShelfOntPPPoECurrent24SLCIndex OBJECT-TYPE
    SYNTAX      IShelfOntSubscriberLineCardIndex
    MAX-ACCESS  read-only
    STATUS      current
    DESCRIPTION
        "This object identifies the ONT subscriber line card
         index."
    ::= { iShelfOntPPPoECurrent24Entry 2 }

-- %CLISHOWGROUP c24table.1
-- %CLISHOWGROUP c24table.2
iShelfOntPPPoECurrent24Port OBJECT-TYPE
    SYNTAX      INTEGER (1..4)
    MAX-ACCESS  read-only
    STATUS      current
    DESCRIPTION "This object identifies the ethernet port number."
    ::= { iShelfOntPPPoECurrent24Entry 3 }


-- //PMPARAMTYPE PEAK
-- %CLICOLLABEL Peak-Dia
-- %CLISHOWGROUP c24table.1
iShelfOntPPPoECurrent24PeakDialogs OBJECT-TYPE
    SYNTAX      Counter32
    MAX-ACCESS  read-only
    STATUS      current
    DESCRIPTION
        "This counter is the maximum concurent dialogs
         active during the interval."
    ::= { iShelfOntPPPoECurrent24Entry 4 }

-- %CLICOLLABEL Discoveries
-- %CLISHOWGROUP c24table.1
iShelfOntPPPoECurrent24Discovries OBJECT-TYPE
    SYNTAX      Counter32
    MAX-ACCESS  read-only
    STATUS      current
    DESCRIPTION
        "This counter is the number of discovery packets
         received during the interval."
    ::= { iShelfOntPPPoECurrent24Entry 5 }

-- %CLICOLLABEL DialogLimit
-- %CLISHOWGROUP c24table.1
iShelfOntPPPoECurrent24DiscoveryDrops OBJECT-TYPE
    SYNTAX      Counter32
    MAX-ACCESS  read-only
    STATUS      current
    DESCRIPTION
        "This counter is the number of discoveries that
         were dropped due to active dialogs limit exceeded
         during the interval."
    ::= { iShelfOntPPPoECurrent24Entry 6 }

-- %CLICOLLABEL Inactive
-- %CLISHOWGROUP c24table.1
iShelfOntPPPoECurrent24InactivityDrops OBJECT-TYPE
    SYNTAX      Counter32
    MAX-ACCESS  read-only
    STATUS      current
    DESCRIPTION
        "This counter is the number of dialogs that
         were dropped due to inactivity
         during the interval."
    ::= { iShelfOntPPPoECurrent24Entry 7 }

-- %CLICOLLABEL NoRes
-- %CLISHOWGROUP c24table.2
iShelfOntPPPoECurrent24ResourceErrors OBJECT-TYPE
    SYNTAX      Counter32
    MAX-ACCESS  read-only
    STATUS      current
    DESCRIPTION
        "This counter is the number of discoveries that
         were dropped due to lack of available PON bandwidth
         during the interval."
    ::= { iShelfOntPPPoECurrent24Entry 8 }

-- %CLICOLLABEL InPackets
-- %CLIWIDTH 8
-- %CLISHOWGROUP c24table.2
iShelfOntPPPoECurrent24InPackets OBJECT-TYPE
    SYNTAX      Counter32
    MAX-ACCESS  read-only
    STATUS      current
    DESCRIPTION
        "This counter is the total received packets
         during the interval."
    ::= { iShelfOntPPPoECurrent24Entry 9 }

-- %CLICOLLABEL InOctets
-- %CLISHOWGROUP c24table.2
iShelfOntPPPoECurrent24InOctets OBJECT-TYPE
    SYNTAX      Counter32
    MAX-ACCESS  read-only
    STATUS      current
    DESCRIPTION
        "This counter is the total received octets
         during the interval."
    ::= { iShelfOntPPPoECurrent24Entry 10 }

-- %CLICOLLABEL OutPackets
-- %CLISHOWGROUP c24table.2
iShelfOntPPPoECurrent24OutPackets OBJECT-TYPE
    SYNTAX      Counter32
    MAX-ACCESS  read-only
    STATUS      current
    DESCRIPTION
        "This counter is the total transmitted packets
         during the interval."
    ::= { iShelfOntPPPoECurrent24Entry 11 }

-- %CLICOLLABEL OutOctets
-- %CLISHOWGROUP c24table.2
iShelfOntPPPoECurrent24OutOctets OBJECT-TYPE
    SYNTAX      Counter32
    MAX-ACCESS  read-only
    STATUS      current
    DESCRIPTION
        "This counter is the total transmitted octets
         during the interval."
    ::= { iShelfOntPPPoECurrent24Entry 12 }



-- %CLISHOWGROUP c24table.1
-- %CLIWIDTH 5
iShelfOntPPPoECurrent24ValidData OBJECT-TYPE
    SYNTAX      IShelfPerfInvalidFlag
    MAX-ACCESS  read-only
    STATUS      current
    DESCRIPTION
        "This object indicates if the data for this interval
         is valid."
    ::= { iShelfOntPPPoECurrent24Entry 13 }

-- %CLISHOWGROUP c24table.1
iShelfOntPPPoECurrent24ThresholdCrossingPointer OBJECT-TYPE
    SYNTAX      IShelfThresholdCrossingPointer
    MAX-ACCESS  read-write
    STATUS      current
    DESCRIPTION
        "This object points to the threshold crossing entry
         (in iShelfThresholdCrossingTable). A value of zero
         indicates threshold crossing are not being generated."
    DEFVAL      { 0 }
    ::= { iShelfOntPPPoECurrent24Entry 14 }

-- ++++++++++++++++++++++++++++++++++++++++++++++++++++++++++++++++++++++++
--
-- iShelfOntPPPoEInterval24Table - 
--
-- ++++++++++++++++++++++++++++++++++++++++++++++++++++++++++++++++++++++++

-- %CLICMDPREFIX ont:pm:pppoe
-- %CLICMDABBR i24table
-- %CLISHOWGROUP i24table
iShelfOntPPPoEInterval24Table OBJECT-TYPE
    SYNTAX      SEQUENCE OF IShelfOntPPPoEInterval24Entry
    MAX-ACCESS  not-accessible
    STATUS      current
    DESCRIPTION
        "This table contains performance history data pertaining
         to ONT PPPoE Services for the previous 24 hour intervals.
         Rows in this table are automatically created."
    ::= { iShelfOntPm 20 }

iShelfOntPPPoEInterval24Entry OBJECT-TYPE
    SYNTAX      IShelfOntPPPoEInterval24Entry
    MAX-ACCESS  not-accessible
    STATUS      current
    DESCRIPTION
        "Each entry contains performance history data for one
         instance of PPPoE Service."
    INDEX       { iShelfOntPPPoEInterval24LogicalId,
                  iShelfOntPPPoEInterval24SLCIndex,
                  iShelfOntPPPoEInterval24Port,
                  iShelfOntPPPoEInterval24Number }
    ::= { iShelfOntPPPoEInterval24Table 1 }

IShelfOntPPPoEInterval24Entry ::=
    SEQUENCE {
        iShelfOntPPPoEInterval24LogicalId
            IShelfOntLogicalId,
        iShelfOntPPPoEInterval24SLCIndex
            IShelfOntSubscriberLineCardIndex,
        iShelfOntPPPoEInterval24Port
            INTEGER,
        iShelfOntPPPoEInterval24Number
            INTEGER,
        iShelfOntPPPoEInterval24PeakDialogs
            Counter32,
        iShelfOntPPPoEInterval24Discovries
            Counter32,
        iShelfOntPPPoEInterval24DiscoveryDrops
            Counter32,
        iShelfOntPPPoEInterval24InactivityDrops
            Counter32,
        iShelfOntPPPoEInterval24ResourceErrors
            Counter32,
        iShelfOntPPPoEInterval24InPackets
            Counter32,
        iShelfOntPPPoEInterval24InOctets
            Counter32,
        iShelfOntPPPoEInterval24OutPackets
            Counter32,
        iShelfOntPPPoEInterval24OutOctets
            Counter32,
        iShelfOntPPPoEInterval24ValidData
            IShelfPerfInvalidFlag
    }

-- %CLISHOWGROUP i24table.1
-- %CLISHOWGROUP i24table.2
-- %CLIWIDTH 3
iShelfOntPPPoEInterval24LogicalId OBJECT-TYPE
    SYNTAX      IShelfOntLogicalId
    MAX-ACCESS  read-only
    STATUS      current
    DESCRIPTION "This object identifies the logical ID of the ONT."
    ::= { iShelfOntPPPoEInterval24Entry 1 }

-- %CLISHOWGROUP i24table.1
-- %CLISHOWGROUP i24table.2
iShelfOntPPPoEInterval24SLCIndex OBJECT-TYPE
    SYNTAX      IShelfOntSubscriberLineCardIndex
    MAX-ACCESS  read-only
    STATUS      current
    DESCRIPTION
        "This object identifies the ONT subscriber line card
         index."
    ::= { iShelfOntPPPoEInterval24Entry 2 }

-- %CLISHOWGROUP i24table.1
-- %CLISHOWGROUP i24table.2
iShelfOntPPPoEInterval24Port OBJECT-TYPE
    SYNTAX      INTEGER (1..4)
    MAX-ACCESS  read-only
    STATUS      current
    DESCRIPTION "This object identifies the ethernet port number."
    ::= { iShelfOntPPPoEInterval24Entry 3 }

-- %CLISHOWGROUP i24table.1
-- %CLISHOWGROUP i24table.2
-- %CLICOLLABEL Int
-- %CLIWIDTH 3
iShelfOntPPPoEInterval24Number OBJECT-TYPE
    SYNTAX      INTEGER(1..6)
    MAX-ACCESS  read-only
    STATUS      current
    DESCRIPTION
        "This object identifies the interval for which this set
         of statistics is available. The interval identified
         by 1 is the most recently completed 24 hour interval."
    ::= { iShelfOntPPPoEInterval24Entry 4 }



-- //PMPARAMTYPE PEAK
-- %CLICOLLABEL Peak-Dia
-- %CLISHOWGROUP i24table.1
iShelfOntPPPoEInterval24PeakDialogs OBJECT-TYPE
    SYNTAX      Counter32
    MAX-ACCESS  read-only
    STATUS      current
    DESCRIPTION
        "This counter is the maximum concurent dialogs
         active during the interval."
    ::= { iShelfOntPPPoEInterval24Entry 5 }

-- %CLICOLLABEL Discoveries
-- %CLISHOWGROUP i24table.1
iShelfOntPPPoEInterval24Discovries OBJECT-TYPE
    SYNTAX      Counter32
    MAX-ACCESS  read-only
    STATUS      current
    DESCRIPTION
        "This counter is the number of discovery packets
         received during the interval."
    ::= { iShelfOntPPPoEInterval24Entry 6 }

-- %CLICOLLABEL DialogLimit
-- %CLISHOWGROUP i24table.1
iShelfOntPPPoEInterval24DiscoveryDrops OBJECT-TYPE
    SYNTAX      Counter32
    MAX-ACCESS  read-only
    STATUS      current
    DESCRIPTION
        "This counter is the number of discoveries that
         were dropped due to active dialogs limit exceeded
         during the interval."
    ::= { iShelfOntPPPoEInterval24Entry 7 }

-- %CLICOLLABEL Inactive
-- %CLISHOWGROUP i24table.1
iShelfOntPPPoEInterval24InactivityDrops OBJECT-TYPE
    SYNTAX      Counter32
    MAX-ACCESS  read-only
    STATUS      current
    DESCRIPTION
        "This counter is the number of dialogs that
         were dropped due to inactivity
         during the interval."
    ::= { iShelfOntPPPoEInterval24Entry 8 }

-- %CLICOLLABEL NoRes
-- %CLISHOWGROUP i24table.2
iShelfOntPPPoEInterval24ResourceErrors OBJECT-TYPE
    SYNTAX      Counter32
    MAX-ACCESS  read-only
    STATUS      current
    DESCRIPTION
        "This counter is the number of discoveries that
         were dropped due to lack of available PON bandwidth
         during the interval."
    ::= { iShelfOntPPPoEInterval24Entry 9 }

-- %CLICOLLABEL InPackets
-- %CLIWIDTH 8
-- %CLISHOWGROUP i24table.2
iShelfOntPPPoEInterval24InPackets OBJECT-TYPE
    SYNTAX      Counter32
    MAX-ACCESS  read-only
    STATUS      current
    DESCRIPTION
        "This counter is the total received packets
         during the interval."
    ::= { iShelfOntPPPoEInterval24Entry 10 }

-- %CLICOLLABEL InOctets
-- %CLISHOWGROUP i24table.2
iShelfOntPPPoEInterval24InOctets OBJECT-TYPE
    SYNTAX      Counter32
    MAX-ACCESS  read-only
    STATUS      current
    DESCRIPTION
        "This counter is the total received octets
         during the interval."
    ::= { iShelfOntPPPoEInterval24Entry 11 }

-- %CLICOLLABEL OutPackets
-- %CLISHOWGROUP i24table.2
iShelfOntPPPoEInterval24OutPackets OBJECT-TYPE
    SYNTAX      Counter32
    MAX-ACCESS  read-only
    STATUS      current
    DESCRIPTION
        "This counter is the total transmitted packets
         during the interval."
    ::= { iShelfOntPPPoEInterval24Entry 12 }

-- %CLICOLLABEL OutOctets
-- %CLISHOWGROUP i24table.2
iShelfOntPPPoEInterval24OutOctets OBJECT-TYPE
    SYNTAX      Counter32
    MAX-ACCESS  read-only
    STATUS      current
    DESCRIPTION
        "This counter is the total transmitted octets
         during the interval."
    ::= { iShelfOntPPPoEInterval24Entry 13 }


-- %CLISHOWGROUP i24table.1
-- %CLIWIDTH 5
iShelfOntPPPoEInterval24ValidData OBJECT-TYPE
    SYNTAX      IShelfPerfInvalidFlag
    MAX-ACCESS  read-only
    STATUS      current
    DESCRIPTION
        "This object indicates if the data for this interval
         is valid."
    ::= { iShelfOntPPPoEInterval24Entry 14 }

-- ++++++++++++++++++++++++++++++++++++++++++++++++++++++++++++++++++++++++
--
-- iShelfT1NearCurrent15Table -
--
-- ++++++++++++++++++++++++++++++++++++++++++++++++++++++++++++++++++++++++

-- %CLICMDPREFIX ont:pm:t1
-- %CLICMDABBR c15neartable
iShelfT1NearCurrent15Table OBJECT-TYPE
    SYNTAX      SEQUENCE OF IShelfT1NearCurrent15Entry
    MAX-ACCESS  not-accessible
    STATUS      current
    DESCRIPTION ""
    ::= { iShelfT1Pm 1 }

iShelfT1NearCurrent15Entry OBJECT-TYPE
    SYNTAX      IShelfT1NearCurrent15Entry
    MAX-ACCESS  not-accessible
    STATUS      current
    DESCRIPTION ""
    INDEX       { iShelfT1NearCurrent15LocationType,
                  iShelfT1NearCurrent15Location,
                  iShelfT1NearCurrent15Circuit }
    ::= { iShelfT1NearCurrent15Table 1 }

IShelfT1NearCurrent15Entry ::=
    SEQUENCE {
        iShelfT1NearCurrent15LocationType
            IShelfLocationType,
        iShelfT1NearCurrent15Location
            IShelfLocation,
        iShelfT1NearCurrent15Circuit
            IShelfCircuit,
        iShelfT1NearCurrent15CVs
            Gauge32,
        iShelfT1NearCurrent15ESs
            Gauge32,
        iShelfT1NearCurrent15SESs
            Gauge32,
        iShelfT1NearCurrent15CSSs
            Gauge32,
        iShelfT1NearCurrent15SASs
            Gauge32,
        iShelfT1NearCurrent15UASs
            Gauge32,
        iShelfT1NearCurrent15FCs
            Gauge32,
        iShelfT1NearCurrent15ESLs
            Gauge32,
        iShelfT1NearCurrent15ValidData
            IShelfPerfInvalidFlag,
        iShelfT1NearCurrent15ThresholdCrossingPointer
            IShelfThresholdCrossingPointer
    }

-- %CLIWIDTH 2
iShelfT1NearCurrent15LocationType OBJECT-TYPE
    SYNTAX      IShelfLocationType
    MAX-ACCESS  read-only
    STATUS      current
    DESCRIPTION ""
    ::= { iShelfT1NearCurrent15Entry 1 }

iShelfT1NearCurrent15Location OBJECT-TYPE
    SYNTAX      IShelfLocation
    MAX-ACCESS  read-only
    STATUS      current
    DESCRIPTION ""
    ::= { iShelfT1NearCurrent15Entry 2 }

-- %CLICOLLABEL P
-- %CLIWIDTH 1
iShelfT1NearCurrent15Circuit OBJECT-TYPE
    SYNTAX      IShelfCircuit
    MAX-ACCESS  read-only
    STATUS      current
    DESCRIPTION "This object identifies the T1 port number."
    ::= { iShelfT1NearCurrent15Entry 3 }

-- %CLICOLLABEL CVs
-- %CLIWIDTH 9
iShelfT1NearCurrent15CVs OBJECT-TYPE
    SYNTAX      Gauge32
    MAX-ACCESS  read-only
    STATUS      current
    DESCRIPTION ""
    ::= { iShelfT1NearCurrent15Entry 4 }

-- %CLICOLLABEL ESs
-- %CLIWIDTH 5
iShelfT1NearCurrent15ESs OBJECT-TYPE
    SYNTAX      Gauge32
    MAX-ACCESS  read-only
    STATUS      current
    DESCRIPTION ""
    ::= { iShelfT1NearCurrent15Entry 5 }

-- %PMPARAMTYPE ES
-- %CLICOLLABEL SESs
-- %CLIWIDTH 5
iShelfT1NearCurrent15SESs OBJECT-TYPE
    SYNTAX      Gauge32
    MAX-ACCESS  read-only
    STATUS      current
    DESCRIPTION ""
    ::= { iShelfT1NearCurrent15Entry 6 }

-- %CLICOLLABEL CSSs
-- %CLIWIDTH 5
iShelfT1NearCurrent15CSSs OBJECT-TYPE
    SYNTAX      Gauge32
    MAX-ACCESS  read-only
    STATUS      current
    DESCRIPTION ""
    ::= { iShelfT1NearCurrent15Entry 7 }

-- %CLICOLLABEL SASs
-- %CLIWIDTH 5
iShelfT1NearCurrent15SASs OBJECT-TYPE
    SYNTAX      Gauge32
    MAX-ACCESS  read-only
    STATUS      current
    DESCRIPTION ""
    ::= { iShelfT1NearCurrent15Entry 8 }

-- %PMPARAMTYPE US
-- %CLICOLLABEL UASs
-- %CLIWIDTH 5
iShelfT1NearCurrent15UASs OBJECT-TYPE
    SYNTAX      Gauge32
    MAX-ACCESS  read-only
    STATUS      current
    DESCRIPTION ""
    ::= { iShelfT1NearCurrent15Entry 9 }

-- %CLICOLLABEL FCs
-- %CLIWIDTH 5
iShelfT1NearCurrent15FCs OBJECT-TYPE
    SYNTAX      Gauge32
    MAX-ACCESS  read-only
    STATUS      current
    DESCRIPTION ""
    ::= { iShelfT1NearCurrent15Entry 10 }

-- %CLICOLLABEL ESLs
-- %CLIWIDTH 5
iShelfT1NearCurrent15ESLs OBJECT-TYPE
    SYNTAX      Gauge32
    MAX-ACCESS  read-only
    STATUS      current
    DESCRIPTION ""
    ::= { iShelfT1NearCurrent15Entry 11 }

-- %CLIWIDTH 5
iShelfT1NearCurrent15ValidData OBJECT-TYPE
    SYNTAX      IShelfPerfInvalidFlag
    MAX-ACCESS  read-only
    STATUS      current
    DESCRIPTION
        "This object indicates if the data for this interval
         is valid."
    ::= { iShelfT1NearCurrent15Entry 12 }

-- %CLIWIDTH 2
iShelfT1NearCurrent15ThresholdCrossingPointer OBJECT-TYPE
    SYNTAX      IShelfThresholdCrossingPointer
    MAX-ACCESS  read-write
    STATUS      current
    DESCRIPTION
        "This object points to the threshold crossing entry
         (in iShelfThresholdCrossingTable). A value of zero
         indicates threshold crossing are not being generated."
    DEFVAL      { 0 }
    ::= { iShelfT1NearCurrent15Entry 13 }

-- ++++++++++++++++++++++++++++++++++++++++++++++++++++++++++++++++++++++++
--
-- iShelfT1NearInterval15Table -
--
-- ++++++++++++++++++++++++++++++++++++++++++++++++++++++++++++++++++++++++

-- %CLICMDPREFIX ont:pm:t1
-- %CLICMDABBR i15neartable
iShelfT1NearInterval15Table OBJECT-TYPE
    SYNTAX      SEQUENCE OF IShelfT1NearInterval15Entry
    MAX-ACCESS  not-accessible
    STATUS      current
    DESCRIPTION ""
    ::= { iShelfT1Pm 2 }

iShelfT1NearInterval15Entry OBJECT-TYPE
    SYNTAX      IShelfT1NearInterval15Entry
    MAX-ACCESS  not-accessible
    STATUS      current
    DESCRIPTION ""
    INDEX       { iShelfT1NearInterval15LocationType,
                  iShelfT1NearInterval15Location,
                  iShelfT1NearInterval15Circuit,
                  iShelfT1NearInterval15Number }
    ::= { iShelfT1NearInterval15Table 1 }

IShelfT1NearInterval15Entry ::=
    SEQUENCE {
        iShelfT1NearInterval15LocationType
            IShelfLocationType,
        iShelfT1NearInterval15Location
            IShelfLocation,
        iShelfT1NearInterval15Circuit
            IShelfCircuit,
        iShelfT1NearInterval15Number
            INTEGER,
        iShelfT1NearInterval15CVs
            Gauge32,
        iShelfT1NearInterval15ESs
            Gauge32,
        iShelfT1NearInterval15SESs
            Gauge32,
        iShelfT1NearInterval15CSSs
            Gauge32,
        iShelfT1NearInterval15SASs
            Gauge32,
        iShelfT1NearInterval15UASs
            Gauge32,
        iShelfT1NearInterval15FCs
            Gauge32,
        iShelfT1NearInterval15ESLs
            Gauge32,
        iShelfT1NearInterval15ValidData
            IShelfPerfInvalidFlag
    }

-- %CLIWIDTH 2
iShelfT1NearInterval15LocationType OBJECT-TYPE
    SYNTAX      IShelfLocationType
    MAX-ACCESS  read-only
    STATUS      current
    DESCRIPTION ""
    ::= { iShelfT1NearInterval15Entry 1 }

iShelfT1NearInterval15Location OBJECT-TYPE
    SYNTAX      IShelfLocation
    MAX-ACCESS  read-only
    STATUS      current
    DESCRIPTION ""
    ::= { iShelfT1NearInterval15Entry 2 }

-- %CLICOLLABEL P
-- %CLIWIDTH 1
iShelfT1NearInterval15Circuit OBJECT-TYPE
    SYNTAX      IShelfCircuit
    MAX-ACCESS  read-only
    STATUS      current
    DESCRIPTION "This object identifies the T1 port number."
    ::= { iShelfT1NearInterval15Entry 3 }

-- %CLICOLLABEL Int
-- %CLIWIDTH 2
iShelfT1NearInterval15Number OBJECT-TYPE
    SYNTAX      INTEGER(1..32)
    MAX-ACCESS  read-only
    STATUS      current
    DESCRIPTION
        "This object identifies the interval for which this set
         of statistics is available. The interval identified
         by 1 is the most recently completed 15 minute interval."
    ::= { iShelfT1NearInterval15Entry 4 }

-- %CLICOLLABEL CVs
-- %CLIWIDTH 9
iShelfT1NearInterval15CVs OBJECT-TYPE
    SYNTAX      Gauge32
    MAX-ACCESS  read-only
    STATUS      current
    DESCRIPTION ""
    ::= { iShelfT1NearInterval15Entry 5 }

-- %CLICOLLABEL ESs
-- %CLIWIDTH 5
iShelfT1NearInterval15ESs OBJECT-TYPE
    SYNTAX      Gauge32
    MAX-ACCESS  read-only
    STATUS      current
    DESCRIPTION ""
    ::= { iShelfT1NearInterval15Entry 6 }

-- %CLICOLLABEL SESs
-- %CLIWIDTH 5
iShelfT1NearInterval15SESs OBJECT-TYPE
    SYNTAX      Gauge32
    MAX-ACCESS  read-only
    STATUS      current
    DESCRIPTION ""
    ::= { iShelfT1NearInterval15Entry 7 }

-- %CLICOLLABEL CSSs
-- %CLIWIDTH 5
iShelfT1NearInterval15CSSs OBJECT-TYPE
    SYNTAX      Gauge32
    MAX-ACCESS  read-only
    STATUS      current
    DESCRIPTION ""
    ::= { iShelfT1NearInterval15Entry 8 }

-- %CLICOLLABEL SASs
-- %CLIWIDTH 5
iShelfT1NearInterval15SASs OBJECT-TYPE
    SYNTAX      Gauge32
    MAX-ACCESS  read-only
    STATUS      current
    DESCRIPTION ""
    ::= { iShelfT1NearInterval15Entry 9 }

-- %CLICOLLABEL UASs
-- %CLIWIDTH 5
iShelfT1NearInterval15UASs OBJECT-TYPE
    SYNTAX      Gauge32
    MAX-ACCESS  read-only
    STATUS      current
    DESCRIPTION ""
    ::= { iShelfT1NearInterval15Entry 10 }

-- %CLICOLLABEL FCs
-- %CLIWIDTH 5
iShelfT1NearInterval15FCs OBJECT-TYPE
    SYNTAX      Gauge32
    MAX-ACCESS  read-only
    STATUS      current
    DESCRIPTION ""
    ::= { iShelfT1NearInterval15Entry 11 }

-- %CLICOLLABEL ESLs
-- %CLIWIDTH 5
iShelfT1NearInterval15ESLs OBJECT-TYPE
    SYNTAX      Gauge32
    MAX-ACCESS  read-only
    STATUS      current
    DESCRIPTION ""
    ::= { iShelfT1NearInterval15Entry 12 }

-- %CLIWIDTH 5
iShelfT1NearInterval15ValidData OBJECT-TYPE
    SYNTAX      IShelfPerfInvalidFlag
    MAX-ACCESS  read-only
    STATUS      current
    DESCRIPTION
        "This object indicates if the data for this interval
         is valid."
    ::= { iShelfT1NearInterval15Entry 13 }

-- ++++++++++++++++++++++++++++++++++++++++++++++++++++++++++++++++++++++++
--
-- iShelfT1NearCurrent24Table -
--
-- ++++++++++++++++++++++++++++++++++++++++++++++++++++++++++++++++++++++++

-- %CLICMDPREFIX ont:pm:t1
-- %CLICMDABBR c24neartable
iShelfT1NearCurrent24Table OBJECT-TYPE
    SYNTAX      SEQUENCE OF IShelfT1NearCurrent24Entry
    MAX-ACCESS  not-accessible
    STATUS      current
    DESCRIPTION ""
    ::= { iShelfT1Pm 3 }

iShelfT1NearCurrent24Entry OBJECT-TYPE
    SYNTAX      IShelfT1NearCurrent24Entry
    MAX-ACCESS  not-accessible
    STATUS      current
    DESCRIPTION ""
    INDEX       { iShelfT1NearCurrent24LocationType,
                  iShelfT1NearCurrent24Location,
                  iShelfT1NearCurrent24Circuit }
    ::= { iShelfT1NearCurrent24Table 1 }

IShelfT1NearCurrent24Entry ::=
    SEQUENCE {
        iShelfT1NearCurrent24LocationType
            IShelfLocationType,
        iShelfT1NearCurrent24Location
            IShelfLocation,
        iShelfT1NearCurrent24Circuit
            IShelfCircuit,
        iShelfT1NearCurrent24CVs
            Gauge32,
        iShelfT1NearCurrent24ESs
            Gauge32,
        iShelfT1NearCurrent24SESs
            Gauge32,
        iShelfT1NearCurrent24CSSs
            Gauge32,
        iShelfT1NearCurrent24SASs
            Gauge32,
        iShelfT1NearCurrent24UASs
            Gauge32,
        iShelfT1NearCurrent24FCs
            Gauge32,
        iShelfT1NearCurrent24ESLs
            Gauge32,
        iShelfT1NearCurrent24ValidData
            IShelfPerfInvalidFlag,
        iShelfT1NearCurrent24ThresholdCrossingPointer
            IShelfThresholdCrossingPointer
    }

-- %CLIWIDTH 2
iShelfT1NearCurrent24LocationType OBJECT-TYPE
    SYNTAX      IShelfLocationType
    MAX-ACCESS  read-only
    STATUS      current
    DESCRIPTION ""
    ::= { iShelfT1NearCurrent24Entry 1 }

iShelfT1NearCurrent24Location OBJECT-TYPE
    SYNTAX      IShelfLocation
    MAX-ACCESS  read-only
    STATUS      current
    DESCRIPTION ""
    ::= { iShelfT1NearCurrent24Entry 2 }

-- %CLICOLLABEL P
-- %CLIWIDTH 1
iShelfT1NearCurrent24Circuit OBJECT-TYPE
    SYNTAX      IShelfCircuit
    MAX-ACCESS  read-only
    STATUS      current
    DESCRIPTION "This object identifies the T1 port number."
    ::= { iShelfT1NearCurrent24Entry 3 }

-- %CLICOLLABEL CVs
-- %CLIWIDTH 9
iShelfT1NearCurrent24CVs OBJECT-TYPE
    SYNTAX      Gauge32
    MAX-ACCESS  read-only
    STATUS      current
    DESCRIPTION ""
    ::= { iShelfT1NearCurrent24Entry 4 }

-- %CLICOLLABEL ESs
-- %CLIWIDTH 5
iShelfT1NearCurrent24ESs OBJECT-TYPE
    SYNTAX      Gauge32
    MAX-ACCESS  read-only
    STATUS      current
    DESCRIPTION ""
    ::= { iShelfT1NearCurrent24Entry 5 }

-- %CLICOLLABEL SESs
-- %CLIWIDTH 5
iShelfT1NearCurrent24SESs OBJECT-TYPE
    SYNTAX      Gauge32
    MAX-ACCESS  read-only
    STATUS      current
    DESCRIPTION ""
    ::= { iShelfT1NearCurrent24Entry 6 }

-- %CLICOLLABEL CSSs
-- %CLIWIDTH 5
iShelfT1NearCurrent24CSSs OBJECT-TYPE
    SYNTAX      Gauge32
    MAX-ACCESS  read-only
    STATUS      current
    DESCRIPTION ""
    ::= { iShelfT1NearCurrent24Entry 7 }

-- %CLICOLLABEL SASs
-- %CLIWIDTH 5
iShelfT1NearCurrent24SASs OBJECT-TYPE
    SYNTAX      Gauge32
    MAX-ACCESS  read-only
    STATUS      current
    DESCRIPTION ""
    ::= { iShelfT1NearCurrent24Entry 8 }

-- %CLICOLLABEL UASs
-- %CLIWIDTH 5
iShelfT1NearCurrent24UASs OBJECT-TYPE
    SYNTAX      Gauge32
    MAX-ACCESS  read-only
    STATUS      current
    DESCRIPTION ""
    ::= { iShelfT1NearCurrent24Entry 9 }

-- %CLICOLLABEL FCs
-- %CLIWIDTH 5
iShelfT1NearCurrent24FCs OBJECT-TYPE
    SYNTAX      Gauge32
    MAX-ACCESS  read-only
    STATUS      current
    DESCRIPTION ""
    ::= { iShelfT1NearCurrent24Entry 10 }

-- %CLICOLLABEL ESLs
-- %CLIWIDTH 5
iShelfT1NearCurrent24ESLs OBJECT-TYPE
    SYNTAX      Gauge32
    MAX-ACCESS  read-only
    STATUS      current
    DESCRIPTION ""
    ::= { iShelfT1NearCurrent24Entry 11 }

-- %CLIWIDTH 5
iShelfT1NearCurrent24ValidData OBJECT-TYPE
    SYNTAX      IShelfPerfInvalidFlag
    MAX-ACCESS  read-only
    STATUS      current
    DESCRIPTION
        "This object indicates if the data for this interval
         is valid."
    ::= { iShelfT1NearCurrent24Entry 12 }

-- %CLIWIDTH 2
iShelfT1NearCurrent24ThresholdCrossingPointer OBJECT-TYPE
    SYNTAX      IShelfThresholdCrossingPointer
    MAX-ACCESS  read-write
    STATUS      current
    DESCRIPTION
        "This object points to the threshold crossing entry
         (in iShelfThresholdCrossingTable). A value of zero
         indicates threshold crossing are not being generated."
    DEFVAL      { 0 }
    ::= { iShelfT1NearCurrent24Entry 13 }

-- ++++++++++++++++++++++++++++++++++++++++++++++++++++++++++++++++++++++++
--
-- iShelfT1NearInterval24Table -
--
-- ++++++++++++++++++++++++++++++++++++++++++++++++++++++++++++++++++++++++

-- %CLICMDPREFIX ont:pm:t1
-- %CLICMDABBR i24neartable
iShelfT1NearInterval24Table OBJECT-TYPE
    SYNTAX      SEQUENCE OF IShelfT1NearInterval24Entry
    MAX-ACCESS  not-accessible
    STATUS      current
    DESCRIPTION ""
    ::= { iShelfT1Pm 4 }

iShelfT1NearInterval24Entry OBJECT-TYPE
    SYNTAX      IShelfT1NearInterval24Entry
    MAX-ACCESS  not-accessible
    STATUS      current
    DESCRIPTION ""
    INDEX       { iShelfT1NearInterval24LocationType,
                  iShelfT1NearInterval24Location,
                  iShelfT1NearInterval24Circuit,
                  iShelfT1NearInterval24Number }
    ::= { iShelfT1NearInterval24Table 1 }

IShelfT1NearInterval24Entry ::=
    SEQUENCE {
        iShelfT1NearInterval24LocationType
            IShelfLocationType,
        iShelfT1NearInterval24Location
            IShelfLocation,
        iShelfT1NearInterval24Circuit
            IShelfCircuit,
        iShelfT1NearInterval24Number
            INTEGER,
        iShelfT1NearInterval24CVs
            Gauge32,
        iShelfT1NearInterval24ESs
            Gauge32,
        iShelfT1NearInterval24SESs
            Gauge32,
        iShelfT1NearInterval24CSSs
            Gauge32,
        iShelfT1NearInterval24SASs
            Gauge32,
        iShelfT1NearInterval24UASs
            Gauge32,
        iShelfT1NearInterval24FCs
            Gauge32,
        iShelfT1NearInterval24ESLs
            Gauge32,
        iShelfT1NearInterval24ValidData
            IShelfPerfInvalidFlag
    }

-- %CLIWIDTH 2
iShelfT1NearInterval24LocationType OBJECT-TYPE
    SYNTAX      IShelfLocationType
    MAX-ACCESS  read-only
    STATUS      current
    DESCRIPTION ""
    ::= { iShelfT1NearInterval24Entry 1 }

iShelfT1NearInterval24Location OBJECT-TYPE
    SYNTAX      IShelfLocation
    MAX-ACCESS  read-only
    STATUS      current
    DESCRIPTION ""
    ::= { iShelfT1NearInterval24Entry 2 }

-- %CLICOLLABEL P
-- %CLIWIDTH 1
iShelfT1NearInterval24Circuit OBJECT-TYPE
    SYNTAX      IShelfCircuit
    MAX-ACCESS  read-only
    STATUS      current
    DESCRIPTION "This object identifies the T1 port number."
    ::= { iShelfT1NearInterval24Entry 3 }

-- %CLICOLLABEL Int
-- %CLIWIDTH 2
iShelfT1NearInterval24Number OBJECT-TYPE
    SYNTAX      INTEGER(1..6)
    MAX-ACCESS  read-only
    STATUS      current
    DESCRIPTION
        "This object identifies the interval for which this set
         of statistics is available. The interval identified
         by 1 is the most recently completed 15 minute interval."
    ::= { iShelfT1NearInterval24Entry 4 }

-- %CLICOLLABEL CVs
-- %CLIWIDTH 9
iShelfT1NearInterval24CVs OBJECT-TYPE
    SYNTAX      Gauge32
    MAX-ACCESS  read-only
    STATUS      current
    DESCRIPTION ""
    ::= { iShelfT1NearInterval24Entry 5 }

-- %CLICOLLABEL ESs
-- %CLIWIDTH 5
iShelfT1NearInterval24ESs OBJECT-TYPE
    SYNTAX      Gauge32
    MAX-ACCESS  read-only
    STATUS      current
    DESCRIPTION ""
    ::= { iShelfT1NearInterval24Entry 6 }

-- %CLICOLLABEL SESs
-- %CLIWIDTH 5
iShelfT1NearInterval24SESs OBJECT-TYPE
    SYNTAX      Gauge32
    MAX-ACCESS  read-only
    STATUS      current
    DESCRIPTION ""
    ::= { iShelfT1NearInterval24Entry 7 }

-- %CLICOLLABEL CSSs
-- %CLIWIDTH 5
iShelfT1NearInterval24CSSs OBJECT-TYPE
    SYNTAX      Gauge32
    MAX-ACCESS  read-only
    STATUS      current
    DESCRIPTION ""
    ::= { iShelfT1NearInterval24Entry 8 }

-- %CLICOLLABEL SASs
-- %CLIWIDTH 5
iShelfT1NearInterval24SASs OBJECT-TYPE
    SYNTAX      Gauge32
    MAX-ACCESS  read-only
    STATUS      current
    DESCRIPTION ""
    ::= { iShelfT1NearInterval24Entry 9 }

-- %CLICOLLABEL UASs
-- %CLIWIDTH 5
iShelfT1NearInterval24UASs OBJECT-TYPE
    SYNTAX      Gauge32
    MAX-ACCESS  read-only
    STATUS      current
    DESCRIPTION ""
    ::= { iShelfT1NearInterval24Entry 10 }

-- %CLICOLLABEL FCs
-- %CLIWIDTH 5
iShelfT1NearInterval24FCs OBJECT-TYPE
    SYNTAX      Gauge32
    MAX-ACCESS  read-only
    STATUS      current
    DESCRIPTION ""
    ::= { iShelfT1NearInterval24Entry 11 }

-- %CLICOLLABEL ESLs
-- %CLIWIDTH 5
iShelfT1NearInterval24ESLs OBJECT-TYPE
    SYNTAX      Gauge32
    MAX-ACCESS  read-only
    STATUS      current
    DESCRIPTION ""
    ::= { iShelfT1NearInterval24Entry 12 }

-- %CLIWIDTH 5
iShelfT1NearInterval24ValidData OBJECT-TYPE
    SYNTAX      IShelfPerfInvalidFlag
    MAX-ACCESS  read-only
    STATUS      current
    DESCRIPTION
        "This object indicates if the data for this interval
         is valid."
    ::= { iShelfT1NearInterval24Entry 13 }

-- ++++++++++++++++++++++++++++++++++++++++++++++++++++++++++++++++++++++++
--
-- iShelfT1FarCurrent15Table -
--
-- ++++++++++++++++++++++++++++++++++++++++++++++++++++++++++++++++++++++++

-- %CLICMDPREFIX ont:pm:t1
-- %CLICMDABBR c15fartable
iShelfT1FarCurrent15Table OBJECT-TYPE
    SYNTAX      SEQUENCE OF IShelfT1FarCurrent15Entry
    MAX-ACCESS  not-accessible
    STATUS      current
    DESCRIPTION ""
    ::= { iShelfT1Pm 5 }

iShelfT1FarCurrent15Entry OBJECT-TYPE
    SYNTAX      IShelfT1FarCurrent15Entry
    MAX-ACCESS  not-accessible
    STATUS      current
    DESCRIPTION ""
    INDEX       { iShelfT1FarCurrent15LocationType,
                  iShelfT1FarCurrent15Location,
                  iShelfT1FarCurrent15Circuit }
    ::= { iShelfT1FarCurrent15Table 1 }

IShelfT1FarCurrent15Entry ::=
    SEQUENCE {
        iShelfT1FarCurrent15LocationType
            IShelfLocationType,
        iShelfT1FarCurrent15Location
            IShelfLocation,
        iShelfT1FarCurrent15Circuit
            IShelfCircuit,
        iShelfT1FarCurrent15CVs
            Gauge32,
        iShelfT1FarCurrent15ESs
            Gauge32,
        iShelfT1FarCurrent15SESs
            Gauge32,
        iShelfT1FarCurrent15CSSs
            Gauge32,
        iShelfT1FarCurrent15SASs
            Gauge32,
        iShelfT1FarCurrent15UASs
            Gauge32,
        iShelfT1FarCurrent15FCs
            Gauge32,
        iShelfT1FarCurrent15ESLs
            Gauge32,
        iShelfT1FarCurrent15ValidData
            IShelfPerfInvalidFlag,
        iShelfT1FarCurrent15ThresholdCrossingPointer
            IShelfThresholdCrossingPointer
    }

-- %CLIWIDTH 2
iShelfT1FarCurrent15LocationType OBJECT-TYPE
    SYNTAX      IShelfLocationType
    MAX-ACCESS  read-only
    STATUS      current
    DESCRIPTION ""
    ::= { iShelfT1FarCurrent15Entry 1 }

iShelfT1FarCurrent15Location OBJECT-TYPE
    SYNTAX      IShelfLocation
    MAX-ACCESS  read-only
    STATUS      current
    DESCRIPTION ""
    ::= { iShelfT1FarCurrent15Entry 2 }

-- %CLICOLLABEL P
-- %CLIWIDTH 1
iShelfT1FarCurrent15Circuit OBJECT-TYPE
    SYNTAX      IShelfCircuit
    MAX-ACCESS  read-only
    STATUS      current
    DESCRIPTION "This object identifies the T1 port number."
    ::= { iShelfT1FarCurrent15Entry 3 }

-- %CLICOLLABEL CVs
-- %CLIWIDTH 9
iShelfT1FarCurrent15CVs OBJECT-TYPE
    SYNTAX      Gauge32
    MAX-ACCESS  read-only
    STATUS      current
    DESCRIPTION ""
    ::= { iShelfT1FarCurrent15Entry 4 }

-- %CLICOLLABEL ESs
-- %CLIWIDTH 5
iShelfT1FarCurrent15ESs OBJECT-TYPE
    SYNTAX      Gauge32
    MAX-ACCESS  read-only
    STATUS      current
    DESCRIPTION ""
    ::= { iShelfT1FarCurrent15Entry 5 }

-- %PMPARAMTYPE ES
-- %CLICOLLABEL SESs
-- %CLIWIDTH 5
iShelfT1FarCurrent15SESs OBJECT-TYPE
    SYNTAX      Gauge32
    MAX-ACCESS  read-only
    STATUS      current
    DESCRIPTION ""
    ::= { iShelfT1FarCurrent15Entry 6 }

-- %CLICOLLABEL CSSs
-- %CLIWIDTH 5
iShelfT1FarCurrent15CSSs OBJECT-TYPE
    SYNTAX      Gauge32
    MAX-ACCESS  read-only
    STATUS      current
    DESCRIPTION ""
    ::= { iShelfT1FarCurrent15Entry 7 }

-- %CLICOLLABEL SASs
-- %CLIWIDTH 5
iShelfT1FarCurrent15SASs OBJECT-TYPE
    SYNTAX      Gauge32
    MAX-ACCESS  read-only
    STATUS      current
    DESCRIPTION ""
    ::= { iShelfT1FarCurrent15Entry 8 }

-- %PMPARAMTYPE US
-- %CLICOLLABEL UASs
-- %CLIWIDTH 5
iShelfT1FarCurrent15UASs OBJECT-TYPE
    SYNTAX      Gauge32
    MAX-ACCESS  read-only
    STATUS      current
    DESCRIPTION ""
    ::= { iShelfT1FarCurrent15Entry 9 }

-- %CLICOLLABEL FCs
-- %CLIWIDTH 5
iShelfT1FarCurrent15FCs OBJECT-TYPE
    SYNTAX      Gauge32
    MAX-ACCESS  read-only
    STATUS      current
    DESCRIPTION ""
    ::= { iShelfT1FarCurrent15Entry 10 }

-- %CLICOLLABEL ESLs
-- %CLIWIDTH 5
iShelfT1FarCurrent15ESLs OBJECT-TYPE
    SYNTAX      Gauge32
    MAX-ACCESS  read-only
    STATUS      current
    DESCRIPTION ""
    ::= { iShelfT1FarCurrent15Entry 11 }

-- %CLIWIDTH 5
iShelfT1FarCurrent15ValidData OBJECT-TYPE
    SYNTAX      IShelfPerfInvalidFlag
    MAX-ACCESS  read-only
    STATUS      current
    DESCRIPTION
        "This object indicates if the data for this interval
         is valid."
    ::= { iShelfT1FarCurrent15Entry 12 }

-- %CLIWIDTH 2
iShelfT1FarCurrent15ThresholdCrossingPointer OBJECT-TYPE
    SYNTAX      IShelfThresholdCrossingPointer
    MAX-ACCESS  read-write
    STATUS      current
    DESCRIPTION
        "This object points to the threshold crossing entry
         (in iShelfThresholdCrossingTable). A value of zero
         indicates threshold crossing are not being generated."
    DEFVAL      { 0 }
    ::= { iShelfT1FarCurrent15Entry 13 }

-- ++++++++++++++++++++++++++++++++++++++++++++++++++++++++++++++++++++++++
--
-- iShelfT1FarInterval15Table -
--
-- ++++++++++++++++++++++++++++++++++++++++++++++++++++++++++++++++++++++++

-- %CLICMDPREFIX ont:pm:t1
-- %CLICMDABBR i15fartable
iShelfT1FarInterval15Table OBJECT-TYPE
    SYNTAX      SEQUENCE OF IShelfT1FarInterval15Entry
    MAX-ACCESS  not-accessible
    STATUS      current
    DESCRIPTION ""
    ::= { iShelfT1Pm 6 }

iShelfT1FarInterval15Entry OBJECT-TYPE
    SYNTAX      IShelfT1FarInterval15Entry
    MAX-ACCESS  not-accessible
    STATUS      current
    DESCRIPTION ""
    INDEX       { iShelfT1FarInterval15LocationType,
                  iShelfT1FarInterval15Location,
                  iShelfT1FarInterval15Circuit,
                  iShelfT1FarInterval15Number }
    ::= { iShelfT1FarInterval15Table 1 }

IShelfT1FarInterval15Entry ::=
    SEQUENCE {
        iShelfT1FarInterval15LocationType
            IShelfLocationType,
        iShelfT1FarInterval15Location
            IShelfLocation,
        iShelfT1FarInterval15Circuit
            IShelfCircuit,
        iShelfT1FarInterval15Number
            INTEGER,
        iShelfT1FarInterval15CVs
            Gauge32,
        iShelfT1FarInterval15ESs
            Gauge32,
        iShelfT1FarInterval15SESs
            Gauge32,
        iShelfT1FarInterval15CSSs
            Gauge32,
        iShelfT1FarInterval15SASs
            Gauge32,
        iShelfT1FarInterval15UASs
            Gauge32,
        iShelfT1FarInterval15FCs
            Gauge32,
        iShelfT1FarInterval15ESLs
            Gauge32,
        iShelfT1FarInterval15ValidData
            IShelfPerfInvalidFlag
    }

-- %CLIWIDTH 2
iShelfT1FarInterval15LocationType OBJECT-TYPE
    SYNTAX      IShelfLocationType
    MAX-ACCESS  read-only
    STATUS      current
    DESCRIPTION ""
    ::= { iShelfT1FarInterval15Entry 1 }

iShelfT1FarInterval15Location OBJECT-TYPE
    SYNTAX      IShelfLocation
    MAX-ACCESS  read-only
    STATUS      current
    DESCRIPTION ""
    ::= { iShelfT1FarInterval15Entry 2 }

-- %CLICOLLABEL P
-- %CLIWIDTH 1
iShelfT1FarInterval15Circuit OBJECT-TYPE
    SYNTAX      IShelfCircuit
    MAX-ACCESS  read-only
    STATUS      current
    DESCRIPTION "This object identifies the T1 port number."
    ::= { iShelfT1FarInterval15Entry 3 }

-- %CLICOLLABEL Int
-- %CLIWIDTH 2
iShelfT1FarInterval15Number OBJECT-TYPE
    SYNTAX      INTEGER(1..32)
    MAX-ACCESS  read-only
    STATUS      current
    DESCRIPTION
        "This object identifies the interval for which this set
         of statistics is available. The interval identified
         by 1 is the most recently completed 15 minute interval."
    ::= { iShelfT1FarInterval15Entry 4 }

-- %CLICOLLABEL CVs
-- %CLIWIDTH 9
iShelfT1FarInterval15CVs OBJECT-TYPE
    SYNTAX      Gauge32
    MAX-ACCESS  read-only
    STATUS      current
    DESCRIPTION ""
    ::= { iShelfT1FarInterval15Entry 5 }

-- %CLICOLLABEL ESs
-- %CLIWIDTH 5
iShelfT1FarInterval15ESs OBJECT-TYPE
    SYNTAX      Gauge32
    MAX-ACCESS  read-only
    STATUS      current
    DESCRIPTION ""
    ::= { iShelfT1FarInterval15Entry 6 }

-- %CLICOLLABEL SESs
-- %CLIWIDTH 5
iShelfT1FarInterval15SESs OBJECT-TYPE
    SYNTAX      Gauge32
    MAX-ACCESS  read-only
    STATUS      current
    DESCRIPTION ""
    ::= { iShelfT1FarInterval15Entry 7 }

-- %CLICOLLABEL CSSs
-- %CLIWIDTH 5
iShelfT1FarInterval15CSSs OBJECT-TYPE
    SYNTAX      Gauge32
    MAX-ACCESS  read-only
    STATUS      current
    DESCRIPTION ""
    ::= { iShelfT1FarInterval15Entry 8 }

-- %CLICOLLABEL SASs
-- %CLIWIDTH 5
iShelfT1FarInterval15SASs OBJECT-TYPE
    SYNTAX      Gauge32
    MAX-ACCESS  read-only
    STATUS      current
    DESCRIPTION ""
    ::= { iShelfT1FarInterval15Entry 9 }

-- %CLICOLLABEL UASs
-- %CLIWIDTH 5
iShelfT1FarInterval15UASs OBJECT-TYPE
    SYNTAX      Gauge32
    MAX-ACCESS  read-only
    STATUS      current
    DESCRIPTION ""
    ::= { iShelfT1FarInterval15Entry 10 }

-- %CLICOLLABEL FCs
-- %CLIWIDTH 5
iShelfT1FarInterval15FCs OBJECT-TYPE
    SYNTAX      Gauge32
    MAX-ACCESS  read-only
    STATUS      current
    DESCRIPTION ""
    ::= { iShelfT1FarInterval15Entry 11 }

-- %CLICOLLABEL ESLs
-- %CLIWIDTH 5
iShelfT1FarInterval15ESLs OBJECT-TYPE
    SYNTAX      Gauge32
    MAX-ACCESS  read-only
    STATUS      current
    DESCRIPTION ""
    ::= { iShelfT1FarInterval15Entry 12 }

-- %CLIWIDTH 5
iShelfT1FarInterval15ValidData OBJECT-TYPE
    SYNTAX      IShelfPerfInvalidFlag
    MAX-ACCESS  read-only
    STATUS      current
    DESCRIPTION
        "This object indicates if the data for this interval
         is valid."
    ::= { iShelfT1FarInterval15Entry 13 }

-- ++++++++++++++++++++++++++++++++++++++++++++++++++++++++++++++++++++++++
--
-- iShelfT1FarCurrent24Table -
--
-- ++++++++++++++++++++++++++++++++++++++++++++++++++++++++++++++++++++++++

-- %CLICMDPREFIX ont:pm:t1
-- %CLICMDABBR c24fartable
iShelfT1FarCurrent24Table OBJECT-TYPE
    SYNTAX      SEQUENCE OF IShelfT1FarCurrent24Entry
    MAX-ACCESS  not-accessible
    STATUS      current
    DESCRIPTION ""
    ::= { iShelfT1Pm 7 }

iShelfT1FarCurrent24Entry OBJECT-TYPE
    SYNTAX      IShelfT1FarCurrent24Entry
    MAX-ACCESS  not-accessible
    STATUS      current
    DESCRIPTION ""
    INDEX       { iShelfT1FarCurrent24LocationType,
                  iShelfT1FarCurrent24Location,
                  iShelfT1FarCurrent24Circuit }
    ::= { iShelfT1FarCurrent24Table 1 }

IShelfT1FarCurrent24Entry ::=
    SEQUENCE {
        iShelfT1FarCurrent24LocationType
            IShelfLocationType,
        iShelfT1FarCurrent24Location
            IShelfLocation,
        iShelfT1FarCurrent24Circuit
            IShelfCircuit,
        iShelfT1FarCurrent24CVs
            Gauge32,
        iShelfT1FarCurrent24ESs
            Gauge32,
        iShelfT1FarCurrent24SESs
            Gauge32,
        iShelfT1FarCurrent24CSSs
            Gauge32,
        iShelfT1FarCurrent24SASs
            Gauge32,
        iShelfT1FarCurrent24UASs
            Gauge32,
        iShelfT1FarCurrent24FCs
            Gauge32,
        iShelfT1FarCurrent24ESLs
            Gauge32,
        iShelfT1FarCurrent24ValidData
            IShelfPerfInvalidFlag,
        iShelfT1FarCurrent24ThresholdCrossingPointer
            IShelfThresholdCrossingPointer
    }

-- %CLIWIDTH 2
iShelfT1FarCurrent24LocationType OBJECT-TYPE
    SYNTAX      IShelfLocationType
    MAX-ACCESS  read-only
    STATUS      current
    DESCRIPTION ""
    ::= { iShelfT1FarCurrent24Entry 1 }

iShelfT1FarCurrent24Location OBJECT-TYPE
    SYNTAX      IShelfLocation
    MAX-ACCESS  read-only
    STATUS      current
    DESCRIPTION ""
    ::= { iShelfT1FarCurrent24Entry 2 }

-- %CLICOLLABEL P
-- %CLIWIDTH 1
iShelfT1FarCurrent24Circuit OBJECT-TYPE
    SYNTAX      IShelfCircuit
    MAX-ACCESS  read-only
    STATUS      current
    DESCRIPTION "This object identifies the T1 port number."
    ::= { iShelfT1FarCurrent24Entry 3 }

-- %CLICOLLABEL CVs
-- %CLIWIDTH 9
iShelfT1FarCurrent24CVs OBJECT-TYPE
    SYNTAX      Gauge32
    MAX-ACCESS  read-only
    STATUS      current
    DESCRIPTION ""
    ::= { iShelfT1FarCurrent24Entry 4 }

-- %CLICOLLABEL ESs
-- %CLIWIDTH 5
iShelfT1FarCurrent24ESs OBJECT-TYPE
    SYNTAX      Gauge32
    MAX-ACCESS  read-only
    STATUS      current
    DESCRIPTION ""
    ::= { iShelfT1FarCurrent24Entry 5 }

-- %CLICOLLABEL SESs
-- %CLIWIDTH 5
iShelfT1FarCurrent24SESs OBJECT-TYPE
    SYNTAX      Gauge32
    MAX-ACCESS  read-only
    STATUS      current
    DESCRIPTION ""
    ::= { iShelfT1FarCurrent24Entry 6 }

-- %CLICOLLABEL CSSs
-- %CLIWIDTH 5
iShelfT1FarCurrent24CSSs OBJECT-TYPE
    SYNTAX      Gauge32
    MAX-ACCESS  read-only
    STATUS      current
    DESCRIPTION ""
    ::= { iShelfT1FarCurrent24Entry 7 }

-- %CLICOLLABEL SASs
-- %CLIWIDTH 5
iShelfT1FarCurrent24SASs OBJECT-TYPE
    SYNTAX      Gauge32
    MAX-ACCESS  read-only
    STATUS      current
    DESCRIPTION ""
    ::= { iShelfT1FarCurrent24Entry 8 }

-- %CLICOLLABEL UASs
-- %CLIWIDTH 5
iShelfT1FarCurrent24UASs OBJECT-TYPE
    SYNTAX      Gauge32
    MAX-ACCESS  read-only
    STATUS      current
    DESCRIPTION ""
    ::= { iShelfT1FarCurrent24Entry 9 }

-- %CLICOLLABEL FCs
-- %CLIWIDTH 5
iShelfT1FarCurrent24FCs OBJECT-TYPE
    SYNTAX      Gauge32
    MAX-ACCESS  read-only
    STATUS      current
    DESCRIPTION ""
    ::= { iShelfT1FarCurrent24Entry 10 }

-- %CLICOLLABEL ESLs
-- %CLIWIDTH 5
iShelfT1FarCurrent24ESLs OBJECT-TYPE
    SYNTAX      Gauge32
    MAX-ACCESS  read-only
    STATUS      current
    DESCRIPTION ""
    ::= { iShelfT1FarCurrent24Entry 11 }

-- %CLIWIDTH 5
iShelfT1FarCurrent24ValidData OBJECT-TYPE
    SYNTAX      IShelfPerfInvalidFlag
    MAX-ACCESS  read-only
    STATUS      current
    DESCRIPTION
        "This object indicates if the data for this interval
         is valid."
    ::= { iShelfT1FarCurrent24Entry 12 }

-- %CLIWIDTH 2
iShelfT1FarCurrent24ThresholdCrossingPointer OBJECT-TYPE
    SYNTAX      IShelfThresholdCrossingPointer
    MAX-ACCESS  read-write
    STATUS      current
    DESCRIPTION
        "This object points to the threshold crossing entry
         (in iShelfThresholdCrossingTable). A value of zero
         indicates threshold crossing are not being generated."
    DEFVAL      { 0 }
    ::= { iShelfT1FarCurrent24Entry 13 }

-- ++++++++++++++++++++++++++++++++++++++++++++++++++++++++++++++++++++++++
--
-- iShelfT1FarInterval24Table -
--
-- ++++++++++++++++++++++++++++++++++++++++++++++++++++++++++++++++++++++++

-- %CLICMDPREFIX ont:pm:t1
-- %CLICMDABBR i24fartable
iShelfT1FarInterval24Table OBJECT-TYPE
    SYNTAX      SEQUENCE OF IShelfT1FarInterval24Entry
    MAX-ACCESS  not-accessible
    STATUS      current
    DESCRIPTION ""
    ::= { iShelfT1Pm 8 }

iShelfT1FarInterval24Entry OBJECT-TYPE
    SYNTAX      IShelfT1FarInterval24Entry
    MAX-ACCESS  not-accessible
    STATUS      current
    DESCRIPTION ""
    INDEX       { iShelfT1FarInterval24LocationType,
                  iShelfT1FarInterval24Location,
                  iShelfT1FarInterval24Circuit,
                  iShelfT1FarInterval24Number }
    ::= { iShelfT1FarInterval24Table 1 }

IShelfT1FarInterval24Entry ::=
    SEQUENCE {
        iShelfT1FarInterval24LocationType
            IShelfLocationType,
        iShelfT1FarInterval24Location
            IShelfLocation,
        iShelfT1FarInterval24Circuit
            IShelfCircuit,
        iShelfT1FarInterval24Number
            INTEGER,
        iShelfT1FarInterval24CVs
            Gauge32,
        iShelfT1FarInterval24ESs
            Gauge32,
        iShelfT1FarInterval24SESs
            Gauge32,
        iShelfT1FarInterval24CSSs
            Gauge32,
        iShelfT1FarInterval24SASs
            Gauge32,
        iShelfT1FarInterval24UASs
            Gauge32,
        iShelfT1FarInterval24FCs
            Gauge32,
        iShelfT1FarInterval24ESLs
            Gauge32,
        iShelfT1FarInterval24ValidData
            IShelfPerfInvalidFlag
    }

-- %CLIWIDTH 2
iShelfT1FarInterval24LocationType OBJECT-TYPE
    SYNTAX      IShelfLocationType
    MAX-ACCESS  read-only
    STATUS      current
    DESCRIPTION ""
    ::= { iShelfT1FarInterval24Entry 1 }

iShelfT1FarInterval24Location OBJECT-TYPE
    SYNTAX      IShelfLocation
    MAX-ACCESS  read-only
    STATUS      current
    DESCRIPTION ""
    ::= { iShelfT1FarInterval24Entry 2 }

-- %CLICOLLABEL P
-- %CLIWIDTH 1
iShelfT1FarInterval24Circuit OBJECT-TYPE
    SYNTAX      IShelfCircuit
    MAX-ACCESS  read-only
    STATUS      current
    DESCRIPTION "This object identifies the T1 port number."
    ::= { iShelfT1FarInterval24Entry 3 }

-- %CLICOLLABEL Int
-- %CLIWIDTH 2
iShelfT1FarInterval24Number OBJECT-TYPE
    SYNTAX      INTEGER(1..6)
    MAX-ACCESS  read-only
    STATUS      current
    DESCRIPTION
        "This object identifies the interval for which this set
         of statistics is available. The interval identified
         by 1 is the most recently completed 15 minute interval."
    ::= { iShelfT1FarInterval24Entry 4 }

-- %CLICOLLABEL CVs
-- %CLIWIDTH 9
iShelfT1FarInterval24CVs OBJECT-TYPE
    SYNTAX      Gauge32
    MAX-ACCESS  read-only
    STATUS      current
    DESCRIPTION ""
    ::= { iShelfT1FarInterval24Entry 5 }

-- %CLICOLLABEL ESs
-- %CLIWIDTH 5
iShelfT1FarInterval24ESs OBJECT-TYPE
    SYNTAX      Gauge32
    MAX-ACCESS  read-only
    STATUS      current
    DESCRIPTION ""
    ::= { iShelfT1FarInterval24Entry 6 }

-- %CLICOLLABEL SESs
-- %CLIWIDTH 5
iShelfT1FarInterval24SESs OBJECT-TYPE
    SYNTAX      Gauge32
    MAX-ACCESS  read-only
    STATUS      current
    DESCRIPTION ""
    ::= { iShelfT1FarInterval24Entry 7 }

-- %CLICOLLABEL CSSs
-- %CLIWIDTH 5
iShelfT1FarInterval24CSSs OBJECT-TYPE
    SYNTAX      Gauge32
    MAX-ACCESS  read-only
    STATUS      current
    DESCRIPTION ""
    ::= { iShelfT1FarInterval24Entry 8 }

-- %CLICOLLABEL SASs
-- %CLIWIDTH 5
iShelfT1FarInterval24SASs OBJECT-TYPE
    SYNTAX      Gauge32
    MAX-ACCESS  read-only
    STATUS      current
    DESCRIPTION ""
    ::= { iShelfT1FarInterval24Entry 9 }

-- %CLICOLLABEL UASs
-- %CLIWIDTH 5
iShelfT1FarInterval24UASs OBJECT-TYPE
    SYNTAX      Gauge32
    MAX-ACCESS  read-only
    STATUS      current
    DESCRIPTION ""
    ::= { iShelfT1FarInterval24Entry 10 }

-- %CLICOLLABEL FCs
-- %CLIWIDTH 5
iShelfT1FarInterval24FCs OBJECT-TYPE
    SYNTAX      Gauge32
    MAX-ACCESS  read-only
    STATUS      current
    DESCRIPTION ""
    ::= { iShelfT1FarInterval24Entry 11 }

-- %CLICOLLABEL ESLs
-- %CLIWIDTH 5
iShelfT1FarInterval24ESLs OBJECT-TYPE
    SYNTAX      Gauge32
    MAX-ACCESS  read-only
    STATUS      current
    DESCRIPTION ""
    ::= { iShelfT1FarInterval24Entry 12 }

-- %CLIWIDTH 5
iShelfT1FarInterval24ValidData OBJECT-TYPE
    SYNTAX      IShelfPerfInvalidFlag
    MAX-ACCESS  read-only
    STATUS      current
    DESCRIPTION
        "This object indicates if the data for this interval
         is valid."
    ::= { iShelfT1FarInterval24Entry 13 }

-- ++++++++++++++++++++++++++++++++++++++++++++++++++++++++++++++++++++++++
--
-- iShelfOltPonSdvCurrent15Table -
--
-- ++++++++++++++++++++++++++++++++++++++++++++++++++++++++++++++++++++++++

-- %CLICMDPREFIX pm:sdv
-- %CLICMDABBR c15table
-- %CLISHOWGROUP c15table
iShelfOltPonSdvCurrent15Table OBJECT-TYPE
    SYNTAX      SEQUENCE OF IShelfOltPonSdvCurrent15Entry
    MAX-ACCESS  not-accessible
    STATUS      current
    DESCRIPTION
        "This table contains performance history data pertaining
         to OLT SDV Services for the current 15 minute interval.
         Threshold crossing alerts may be applied to
         the counters in this table.
         Rows in this table are automatically created."
    ::= { iShelfSdvPm 1 }

iShelfOltPonSdvCurrent15Entry OBJECT-TYPE
    SYNTAX      IShelfOltPonSdvCurrent15Entry
    MAX-ACCESS  not-accessible
    STATUS      current
    DESCRIPTION
        "Each entry contains performance history data for one
         instance of SDV Service, one upstream SDV interface
         and each of the PON interfaces."
    INDEX       { iShelfOltPonSdvCurrent15Location,
                  iShelfOltPonSdvCurrent15Index }
    ::= { iShelfOltPonSdvCurrent15Table 1 }

IShelfOltPonSdvCurrent15Entry ::=
    SEQUENCE {
        iShelfOltPonSdvCurrent15Location
            IShelfLocation,
        iShelfOltPonSdvCurrent15Index
            INTEGER,
        iShelfOltPonSdvCurrent15PeakStreams
            Counter32,
        iShelfOltPonSdvCurrent15PeakBandwidth
            Counter32,
        iShelfOltPonSdvCurrent15Packets
            Counter32,
        iShelfOltPonSdvCurrent15Bytes
            Counter32,
        iShelfOltPonSdvCurrent15Drops
            Counter32,
        iShelfOltPonSdvCurrent15Joins
            Counter32,
        iShelfOltPonSdvCurrent15Leaves
            Counter32,
        iShelfOltPonSdvCurrent15Queries
            Counter32,
        iShelfOltPonSdvCurrent15StreamsAlerts
            Counter32,
        iShelfOltPonSdvCurrent15BandwidthAlerts
            Counter32,
        iShelfOltPonSdvCurrent15ValidData
            IShelfPerfInvalidFlag,
        iShelfOltPonSdvCurrent15ThresholdCrossingPointer
            IShelfThresholdCrossingPointer
    }

-- %CLISHOWGROUP c15table.1
-- %CLISHOWGROUP c15table.2
iShelfOltPonSdvCurrent15Location OBJECT-TYPE
    SYNTAX      IShelfLocation
    MAX-ACCESS  read-only
    STATUS      current
    DESCRIPTION
        "This object identifies the location of the OLT card
         supporting the PON interface.  This will be the Node/Shelf/Slot."
    ::= { iShelfOltPonSdvCurrent15Entry 1 }

-- %CLISHOWGROUP c15table.1
-- %CLISHOWGROUP c15table.2
iShelfOltPonSdvCurrent15Index OBJECT-TYPE
    SYNTAX      INTEGER (1..4)
    MAX-ACCESS  read-only
    STATUS      current
    DESCRIPTION
        "This object identifies one of the SDV OLT interface,
         one upstream SDV interface and each of the PON interfaces."
    ::= { iShelfOltPonSdvCurrent15Entry 2 }

-- %CLISHOWGROUP c15table.1
-- //PMPARAMTYPE PEAK
-- %CLICOLLABEL Peak-Strms
iShelfOltPonSdvCurrent15PeakStreams OBJECT-TYPE
    SYNTAX      Counter32
    MAX-ACCESS  read-only
    STATUS      current
    DESCRIPTION
        "This counter is the peak number of simultaneous
         streams during the interval."
    ::= { iShelfOltPonSdvCurrent15Entry 3 }

-- %CLISHOWGROUP c15table.1
-- //PMPARAMTYPE PEAK
-- %CLICOLLABEL Peak-BW
iShelfOltPonSdvCurrent15PeakBandwidth OBJECT-TYPE
    SYNTAX      Counter32
    MAX-ACCESS  read-only
    STATUS      current
    DESCRIPTION
        "This counter is the peak bandwidth usage
         during the interval."
    ::= { iShelfOltPonSdvCurrent15Entry 4 }

-- %CLISHOWGROUP c15table.2
-- %CLICOLLABEL Packets
iShelfOltPonSdvCurrent15Packets OBJECT-TYPE
    SYNTAX      Counter32
    MAX-ACCESS  read-only
    STATUS      current
    DESCRIPTION
        "This counter is the total multicast packets forwarded
         during the interval."
    ::= { iShelfOltPonSdvCurrent15Entry 5 }

-- %CLISHOWGROUP c15table.2
-- %CLICOLLABEL Bytes
iShelfOltPonSdvCurrent15Bytes OBJECT-TYPE
    SYNTAX      Counter32
    MAX-ACCESS  read-only
    STATUS      current
    DESCRIPTION
        "This counter is the total multicast bytes forwarded
         during the interval."
    ::= { iShelfOltPonSdvCurrent15Entry 6 }

-- %CLISHOWGROUP c15table.2
-- %CLICOLLABEL Drops
iShelfOltPonSdvCurrent15Drops OBJECT-TYPE
    SYNTAX      Counter32
    MAX-ACCESS  read-only
    STATUS      current
    DESCRIPTION
        "This counter is the total multicast packets dropped
         during the interval."
    ::= { iShelfOltPonSdvCurrent15Entry 7 }

-- %CLISHOWGROUP c15table.2
-- %CLICOLLABEL Joins
iShelfOltPonSdvCurrent15Joins OBJECT-TYPE
    SYNTAX      Counter32
    MAX-ACCESS  read-only
    STATUS      current
    DESCRIPTION
        "This counter is the total join messages (IGMP
         membership reports) received from set-top-boxes
         during the interval."
    ::= { iShelfOltPonSdvCurrent15Entry 8 }

-- %CLISHOWGROUP c15table.2
-- %CLICOLLABEL Leaves
iShelfOltPonSdvCurrent15Leaves OBJECT-TYPE
    SYNTAX      Counter32
    MAX-ACCESS  read-only
    STATUS      current
    DESCRIPTION
        "This counter is the total stream leaves executed
         during the interval."
    ::= { iShelfOltPonSdvCurrent15Entry 9 }

-- %CLISHOWGROUP c15table.2
-- %CLICOLLABEL Queries
iShelfOltPonSdvCurrent15Queries OBJECT-TYPE
    SYNTAX      Counter32
    MAX-ACCESS  read-only
    STATUS      current
    DESCRIPTION
        "This counter is the total queries received
         during the interval."
    ::= { iShelfOltPonSdvCurrent15Entry 10 }

-- %CLISHOWGROUP c15table.1
-- %CLICOLLABEL Limit-St
iShelfOltPonSdvCurrent15StreamsAlerts OBJECT-TYPE
    SYNTAX      Counter32
    MAX-ACCESS  read-only
    STATUS      current
    DESCRIPTION
        "This counter is the total times the Stream Limit
         threshold was exceeded during the interval."
    ::= { iShelfOltPonSdvCurrent15Entry 11 }

-- %CLISHOWGROUP c15table.1
-- %CLICOLLABEL Limit-BW
iShelfOltPonSdvCurrent15BandwidthAlerts OBJECT-TYPE
    SYNTAX      Counter32
    MAX-ACCESS  read-only
    STATUS      current
    DESCRIPTION
        "This counter is the total times the bandwidth Limit
         threshold was exceeded during the interval."
    ::= { iShelfOltPonSdvCurrent15Entry 12 }


-- %CLISHOWGROUP c15table.1
iShelfOltPonSdvCurrent15ValidData OBJECT-TYPE
    SYNTAX      IShelfPerfInvalidFlag
    MAX-ACCESS  read-only
    STATUS      current
    DESCRIPTION
        "This object indicates if the data for this interval
         is valid."
    ::= { iShelfOltPonSdvCurrent15Entry 13 }

-- %CLISHOWGROUP c15table.1
iShelfOltPonSdvCurrent15ThresholdCrossingPointer OBJECT-TYPE
    SYNTAX      IShelfThresholdCrossingPointer
    MAX-ACCESS  read-write
    STATUS      current
    DESCRIPTION
        "This object points to the threshold crossing entry
         (in iShelfOltPonThresholdCrossingTable). A value of zero
         indicates threshold crossing are not being generated."
    DEFVAL      { 0 }
    ::= { iShelfOltPonSdvCurrent15Entry 14 }

-- ++++++++++++++++++++++++++++++++++++++++++++++++++++++++++++++++++++++++
--
-- iShelfOltPonSdvInterval15Table -
--
-- ++++++++++++++++++++++++++++++++++++++++++++++++++++++++++++++++++++++++

-- %CLICMDPREFIX pm:sdv
-- %CLICMDABBR i15table
-- %CLISHOWGROUP i15table
iShelfOltPonSdvInterval15Table OBJECT-TYPE
    SYNTAX      SEQUENCE OF IShelfOltPonSdvInterval15Entry
    MAX-ACCESS  not-accessible
    STATUS      current
    DESCRIPTION
        "This table contains performance history data pertaining
         to OLT SDV Services for the previous 15 minute intervals.
         Rows in this table are automatically created."
    ::= { iShelfSdvPm 2 }

iShelfOltPonSdvInterval15Entry OBJECT-TYPE
    SYNTAX      IShelfOltPonSdvInterval15Entry
    MAX-ACCESS  not-accessible
    STATUS      current
    DESCRIPTION
        "Each entry contains performance history data for one
         instance of SDV Service, one upstream SDV interface
         and each of the PON interfaces."
    INDEX       { iShelfOltPonSdvInterval15Location,
                  iShelfOltPonSdvInterval15Index,
                  iShelfOltPonSdvInterval15Number }
    ::= { iShelfOltPonSdvInterval15Table 1 }

IShelfOltPonSdvInterval15Entry ::=
    SEQUENCE {
        iShelfOltPonSdvInterval15Location
            IShelfLocation,
        iShelfOltPonSdvInterval15Index
            INTEGER,
        iShelfOltPonSdvInterval15Number
            INTEGER,
        iShelfOltPonSdvInterval15PeakStreams
            Counter32,
        iShelfOltPonSdvInterval15PeakBandwidth
            Counter32,
        iShelfOltPonSdvInterval15Packets
            Counter32,
        iShelfOltPonSdvInterval15Bytes
            Counter32,
        iShelfOltPonSdvInterval15Drops
            Counter32,
        iShelfOltPonSdvInterval15Joins
            Counter32,
        iShelfOltPonSdvInterval15Leaves
            Counter32,
        iShelfOltPonSdvInterval15Queries
            Counter32,
        iShelfOltPonSdvInterval15StreamsAlerts
            Counter32,
        iShelfOltPonSdvInterval15BandwidthAlerts
            Counter32,
        iShelfOltPonSdvInterval15ValidData
            IShelfPerfInvalidFlag
    }

-- %CLISHOWGROUP i15table.1
-- %CLISHOWGROUP i15table.2
iShelfOltPonSdvInterval15Location OBJECT-TYPE
    SYNTAX      IShelfLocation
    MAX-ACCESS  read-only
    STATUS      current
    DESCRIPTION
        "This object identifies the location of the OLT card
         (Node/Shelf/Slot)"
    ::= { iShelfOltPonSdvInterval15Entry 1 }

-- %CLISHOWGROUP i15table.1
-- %CLISHOWGROUP i15table.2
iShelfOltPonSdvInterval15Index OBJECT-TYPE
    SYNTAX      INTEGER (1..4)
    MAX-ACCESS  read-only
    STATUS      current
    DESCRIPTION
        "This object identifies one of the SDV OLT interface,
         one upstream SDV interface and each of the PON interfaces."
    ::= { iShelfOltPonSdvInterval15Entry 2 }

-- %CLISHOWGROUP i15table.1
-- %CLISHOWGROUP i15table.2
-- %CLICOLLABEL Int
-- %CLIWIDTH 3
iShelfOltPonSdvInterval15Number OBJECT-TYPE
    SYNTAX      INTEGER(1..32)
    MAX-ACCESS  read-only
    STATUS      current
    DESCRIPTION
        "This object identifies the interval for which this set
         of statistics is available. The interval identified
         by 1 is the most recently completed 15 minute interval."
    ::= { iShelfOltPonSdvInterval15Entry 3 }



-- %CLISHOWGROUP i15table.1
-- //PMPARAMTYPE PEAK
-- %CLICOLLABEL Peak-Strms
iShelfOltPonSdvInterval15PeakStreams OBJECT-TYPE
    SYNTAX      Counter32
    MAX-ACCESS  read-only
    STATUS      current
    DESCRIPTION
        "This counter is the peak number of simultaneous
         streams during the interval."
    ::= { iShelfOltPonSdvInterval15Entry 4 }

-- %CLISHOWGROUP i15table.1
-- //PMPARAMTYPE PEAK
-- %CLICOLLABEL Peak-BW
iShelfOltPonSdvInterval15PeakBandwidth OBJECT-TYPE
    SYNTAX      Counter32
    MAX-ACCESS  read-only
    STATUS      current
    DESCRIPTION
        "This counter is the peak bandwidth usage
         during the interval."
    ::= { iShelfOltPonSdvInterval15Entry 5 }

-- %CLISHOWGROUP i15table.2
-- %CLICOLLABEL Packets
iShelfOltPonSdvInterval15Packets OBJECT-TYPE
    SYNTAX      Counter32
    MAX-ACCESS  read-only
    STATUS      current
    DESCRIPTION
        "This counter is the total multicast packets forwarded
         during the interval."
    ::= { iShelfOltPonSdvInterval15Entry 6 }

-- %CLISHOWGROUP i15table.2
-- %CLICOLLABEL Bytes
iShelfOltPonSdvInterval15Bytes OBJECT-TYPE
    SYNTAX      Counter32
    MAX-ACCESS  read-only
    STATUS      current
    DESCRIPTION
        "This counter is the total multicast bytes forwarded
         during the interval."
    ::= { iShelfOltPonSdvInterval15Entry 7 }

-- %CLISHOWGROUP i15table.2
-- %CLICOLLABEL Drops
iShelfOltPonSdvInterval15Drops OBJECT-TYPE
    SYNTAX      Counter32
    MAX-ACCESS  read-only
    STATUS      current
    DESCRIPTION
        "This counter is the total multicast packets dropped
         during the interval."
    ::= { iShelfOltPonSdvInterval15Entry 8 }

-- %CLISHOWGROUP i15table.2
-- %CLICOLLABEL Joins
iShelfOltPonSdvInterval15Joins OBJECT-TYPE
    SYNTAX      Counter32
    MAX-ACCESS  read-only
    STATUS      current
    DESCRIPTION
        "This counter is the total join messages (IGMP
         membership reports) received from set-top-boxes
         during the interval."
    ::= { iShelfOltPonSdvInterval15Entry 9 }

-- %CLISHOWGROUP i15table.2
-- %CLICOLLABEL Leaves
iShelfOltPonSdvInterval15Leaves OBJECT-TYPE
    SYNTAX      Counter32
    MAX-ACCESS  read-only
    STATUS      current
    DESCRIPTION
        "This counter is the total stream leaves executed
         during the interval."
    ::= { iShelfOltPonSdvInterval15Entry 10 }

-- %CLISHOWGROUP i15table.2
-- %CLICOLLABEL Queries
iShelfOltPonSdvInterval15Queries OBJECT-TYPE
    SYNTAX      Counter32
    MAX-ACCESS  read-only
    STATUS      current
    DESCRIPTION
        "This counter is the total queries received
         during the interval."
    ::= { iShelfOltPonSdvInterval15Entry 11 }

-- %CLISHOWGROUP i15table.1
-- %CLICOLLABEL Limit-Strms
iShelfOltPonSdvInterval15StreamsAlerts OBJECT-TYPE
    SYNTAX      Counter32
    MAX-ACCESS  read-only
    STATUS      current
    DESCRIPTION
        "This counter is the total times the Stream Limit
         threshold was exceeded during the interval."
    ::= { iShelfOltPonSdvInterval15Entry 12 }

-- %CLISHOWGROUP i15table.1
-- %CLICOLLABEL Limit-BW
iShelfOltPonSdvInterval15BandwidthAlerts OBJECT-TYPE
    SYNTAX      Counter32
    MAX-ACCESS  read-only
    STATUS      current
    DESCRIPTION
        "This counter is the total times the bandwidth Limit
         threshold was exceeded during the interval."
    ::= { iShelfOltPonSdvInterval15Entry 13 }


-- %CLISHOWGROUP i15table.1
-- %CLIWIDTH 5
iShelfOltPonSdvInterval15ValidData OBJECT-TYPE
    SYNTAX      IShelfPerfInvalidFlag
    MAX-ACCESS  read-only
    STATUS      current
    DESCRIPTION
        "This object indicates if the data for this interval
         is valid."
    ::= { iShelfOltPonSdvInterval15Entry 14 }

-- ++++++++++++++++++++++++++++++++++++++++++++++++++++++++++++++++++++++++
--
-- iShelfOltPonSdvCurrent24Table -
--
-- ++++++++++++++++++++++++++++++++++++++++++++++++++++++++++++++++++++++++

-- %CLICMDPREFIX pm:sdv
-- %CLICMDABBR c24table
-- %CLISHOWGROUP c24table
iShelfOltPonSdvCurrent24Table OBJECT-TYPE
    SYNTAX      SEQUENCE OF IShelfOltPonSdvCurrent24Entry
    MAX-ACCESS  not-accessible
    STATUS      current
    DESCRIPTION
        "This table contains performance history data pertaining
         to OLT SDV Services for the current 24 hour interval.
         Threshold crossing alerts may be applied to
         the counters in this table.
         Rows in this table are automatically created."
    ::= { iShelfSdvPm 3 }

iShelfOltPonSdvCurrent24Entry OBJECT-TYPE
    SYNTAX      IShelfOltPonSdvCurrent24Entry
    MAX-ACCESS  not-accessible
    STATUS      current
    DESCRIPTION
        "Each entry contains performance history data for one
         instance of SDV Service, one upstream SDV interface
         and each of the PON interfaces."
    INDEX       { iShelfOltPonSdvCurrent24Location,
                  iShelfOltPonSdvCurrent24Index }
    ::= { iShelfOltPonSdvCurrent24Table 1 }

IShelfOltPonSdvCurrent24Entry ::=
    SEQUENCE {
        iShelfOltPonSdvCurrent24Location
            IShelfLocation,
        iShelfOltPonSdvCurrent24Index
            INTEGER,
        iShelfOltPonSdvCurrent24PeakStreams
            Counter32,
        iShelfOltPonSdvCurrent24PeakBandwidth
            Counter32,
        iShelfOltPonSdvCurrent24Packets
            Counter32,
        iShelfOltPonSdvCurrent24Bytes
            Counter32,
        iShelfOltPonSdvCurrent24Drops
            Counter32,
        iShelfOltPonSdvCurrent24Joins
            Counter32,
        iShelfOltPonSdvCurrent24Leaves
            Counter32,
        iShelfOltPonSdvCurrent24Queries
            Counter32,
        iShelfOltPonSdvCurrent24StreamsAlerts
            Counter32,
        iShelfOltPonSdvCurrent24BandwidthAlerts
            Counter32,
        iShelfOltPonSdvCurrent24ValidData
            IShelfPerfInvalidFlag,
        iShelfOltPonSdvCurrent24ThresholdCrossingPointer
            IShelfThresholdCrossingPointer
    }

-- %CLISHOWGROUP c24table.1
-- %CLISHOWGROUP c24table.2
iShelfOltPonSdvCurrent24Location OBJECT-TYPE
    SYNTAX      IShelfLocation
    MAX-ACCESS  read-only
    STATUS      current
    DESCRIPTION
        "This object identifies the location of the OLT card
         (Node/Shelf/Slot)."
    ::= { iShelfOltPonSdvCurrent24Entry 1 }

-- %CLISHOWGROUP c24table.1
-- %CLISHOWGROUP c24table.2
iShelfOltPonSdvCurrent24Index OBJECT-TYPE
    SYNTAX      INTEGER (1..4)
    MAX-ACCESS  read-only
    STATUS      current
    DESCRIPTION
        "This object identifies one of the SDV OLT interface,
         one upstream SDV interface and each of the PON interfaces."
    ::= { iShelfOltPonSdvCurrent24Entry 2 }



-- %CLISHOWGROUP c24table.1
-- //PMPARAMTYPE PEAK
-- %CLICOLLABEL Peak-Strms
iShelfOltPonSdvCurrent24PeakStreams OBJECT-TYPE
    SYNTAX      Counter32
    MAX-ACCESS  read-only
    STATUS      current
    DESCRIPTION
        "This counter is the peak number of simultaneous
         streams during the interval."
    ::= { iShelfOltPonSdvCurrent24Entry 3 }

-- %CLISHOWGROUP c24table.1
-- //PMPARAMTYPE PEAK
-- %CLICOLLABEL Peak-BW
iShelfOltPonSdvCurrent24PeakBandwidth OBJECT-TYPE
    SYNTAX      Counter32
    MAX-ACCESS  read-only
    STATUS      current
    DESCRIPTION
        "This counter is the peak bandwidth usage
         during the interval."
    ::= { iShelfOltPonSdvCurrent24Entry 4 }

-- %CLISHOWGROUP c24table.1
-- %CLICOLLABEL Packets
iShelfOltPonSdvCurrent24Packets OBJECT-TYPE
    SYNTAX      Counter32
    MAX-ACCESS  read-only
    STATUS      current
    DESCRIPTION
        "This counter is the total multicast packets forwarded
         during the interval."
    ::= { iShelfOltPonSdvCurrent24Entry 5 }

-- %CLISHOWGROUP c24table.2
-- %CLICOLLABEL Bytes
iShelfOltPonSdvCurrent24Bytes OBJECT-TYPE
    SYNTAX      Counter32
    MAX-ACCESS  read-only
    STATUS      current
    DESCRIPTION
        "This counter is the total multicast bytes forwarded
         during the interval."
    ::= { iShelfOltPonSdvCurrent24Entry 6 }

-- %CLISHOWGROUP c24table.2
-- %CLICOLLABEL Drops
iShelfOltPonSdvCurrent24Drops OBJECT-TYPE
    SYNTAX      Counter32
    MAX-ACCESS  read-only
    STATUS      current
    DESCRIPTION
        "This counter is the total multicast packets dropped
         during the interval."
    ::= { iShelfOltPonSdvCurrent24Entry 7 }

-- %CLISHOWGROUP c24table.2
-- %CLICOLLABEL Joins
iShelfOltPonSdvCurrent24Joins OBJECT-TYPE
    SYNTAX      Counter32
    MAX-ACCESS  read-only
    STATUS      current
    DESCRIPTION
        "This counter is the total join messages (IGMP
         membership reports) received from set-top-boxes
         during the interval."
    ::= { iShelfOltPonSdvCurrent24Entry 8 }

-- %CLISHOWGROUP c24table.2
-- %CLICOLLABEL Leaves
iShelfOltPonSdvCurrent24Leaves OBJECT-TYPE
    SYNTAX      Counter32
    MAX-ACCESS  read-only
    STATUS      current
    DESCRIPTION
        "This counter is the total stream leaves executed
         during the interval."
    ::= { iShelfOltPonSdvCurrent24Entry 9 }

-- %CLISHOWGROUP c24table.2
-- %CLICOLLABEL Queries
iShelfOltPonSdvCurrent24Queries OBJECT-TYPE
    SYNTAX      Counter32
    MAX-ACCESS  read-only
    STATUS      current
    DESCRIPTION
        "This counter is the total queries received
         during the interval."
    ::= { iShelfOltPonSdvCurrent24Entry 10 }

-- %CLISHOWGROUP c24table.1
-- %CLICOLLABEL Limit-Strms
iShelfOltPonSdvCurrent24StreamsAlerts OBJECT-TYPE
    SYNTAX      Counter32
    MAX-ACCESS  read-only
    STATUS      current
    DESCRIPTION
        "This counter is the total times the Stream Limit
         threshold was exceeded during the interval."
    ::= { iShelfOltPonSdvCurrent24Entry 11 }

-- %CLISHOWGROUP c24table.1
-- %CLICOLLABEL Limit-BW
iShelfOltPonSdvCurrent24BandwidthAlerts OBJECT-TYPE
    SYNTAX      Counter32
    MAX-ACCESS  read-only
    STATUS      current
    DESCRIPTION
        "This counter is the total times the bandwidth Limit
         threshold was exceeded during the interval."
    ::= { iShelfOltPonSdvCurrent24Entry 12 }


-- %CLISHOWGROUP c24table.1
iShelfOltPonSdvCurrent24ValidData OBJECT-TYPE
    SYNTAX      IShelfPerfInvalidFlag
    MAX-ACCESS  read-only
    STATUS      current
    DESCRIPTION
        "This object indicates if the data for this interval
         is valid."
    ::= { iShelfOltPonSdvCurrent24Entry 13 }

-- %CLISHOWGROUP c24table.1
iShelfOltPonSdvCurrent24ThresholdCrossingPointer OBJECT-TYPE
    SYNTAX      IShelfThresholdCrossingPointer
    MAX-ACCESS  read-write
    STATUS      current
    DESCRIPTION
        "This object points to the threshold crossing entry
         (in iShelfOltPonThresholdCrossingTable). A value of zero
         indicates threshold crossing are not being generated."
    DEFVAL      { 0 }
    ::= { iShelfOltPonSdvCurrent24Entry 14 }

-- ++++++++++++++++++++++++++++++++++++++++++++++++++++++++++++++++++++++++
--
-- iShelfOltPonSdvInterval24Table -
--
-- ++++++++++++++++++++++++++++++++++++++++++++++++++++++++++++++++++++++++

-- %CLICMDPREFIX pm:sdv
-- %CLICMDABBR i24table
-- %CLISHOWGROUP i24table
iShelfOltPonSdvInterval24Table OBJECT-TYPE
    SYNTAX      SEQUENCE OF IShelfOltPonSdvInterval24Entry
    MAX-ACCESS  not-accessible
    STATUS      current
    DESCRIPTION
        "This table contains performance history data pertaining
         to OLT SDV Services for the previous 24 hour intervals.
         Rows in this table are automatically created."
    ::= { iShelfSdvPm 4 }

iShelfOltPonSdvInterval24Entry OBJECT-TYPE
    SYNTAX      IShelfOltPonSdvInterval24Entry
    MAX-ACCESS  not-accessible
    STATUS      current
    DESCRIPTION
        "Each entry contains performance history data for one
         instance of SDV Service, one upstream SDV interface
         and each of the PON interfaces."
    INDEX       { iShelfOltPonSdvInterval24Location,
                  iShelfOltPonSdvInterval24Index,
                  iShelfOltPonSdvInterval24Number }
    ::= { iShelfOltPonSdvInterval24Table 1 }

IShelfOltPonSdvInterval24Entry ::=
    SEQUENCE {
        iShelfOltPonSdvInterval24Location
            IShelfLocation,
        iShelfOltPonSdvInterval24Index
            INTEGER,
        iShelfOltPonSdvInterval24Number
            INTEGER,
        iShelfOltPonSdvInterval24PeakStreams
            Counter32,
        iShelfOltPonSdvInterval24PeakBandwidth
            Counter32,
        iShelfOltPonSdvInterval24Packets
            Counter32,
        iShelfOltPonSdvInterval24Bytes
            Counter32,
        iShelfOltPonSdvInterval24Drops
            Counter32,
        iShelfOltPonSdvInterval24Joins
            Counter32,
        iShelfOltPonSdvInterval24Leaves
            Counter32,
        iShelfOltPonSdvInterval24Queries
            Counter32,
        iShelfOltPonSdvInterval24StreamsAlerts
            Counter32,
        iShelfOltPonSdvInterval24BandwidthAlerts
            Counter32,
        iShelfOltPonSdvInterval24ValidData
            IShelfPerfInvalidFlag
    }

-- %CLISHOWGROUP i24table.1
-- %CLISHOWGROUP i24table.2
iShelfOltPonSdvInterval24Location OBJECT-TYPE
    SYNTAX      IShelfLocation
    MAX-ACCESS  read-only
    STATUS      current
    DESCRIPTION
        "This object identifies the location of OLT
         (Node/Shelf/Slot)."
    ::= { iShelfOltPonSdvInterval24Entry 1 }

-- %CLISHOWGROUP i24table.1
-- %CLISHOWGROUP i24table.2
iShelfOltPonSdvInterval24Index OBJECT-TYPE
    SYNTAX      INTEGER (1..4)
    MAX-ACCESS  read-only
    STATUS      current
    DESCRIPTION
        "This object identifies one of the SDV OLT interface,
         one upstream SDV interface and each of the PON interfaces."
    ::= { iShelfOltPonSdvInterval24Entry 2 }

-- %CLISHOWGROUP i24table.1
-- %CLISHOWGROUP i24table.2
-- %CLICOLLABEL Int
-- %CLIWIDTH 3
iShelfOltPonSdvInterval24Number OBJECT-TYPE
    SYNTAX      INTEGER(1..6)
    MAX-ACCESS  read-only
    STATUS      current
    DESCRIPTION
        "This object identifies the interval for which this set
         of statistics is available. The interval identified
         by 1 is the most recently completed 24 hour interval."
    ::= { iShelfOltPonSdvInterval24Entry 3 }



-- %CLISHOWGROUP i24table.1
-- //PMPARAMTYPE PEAK
-- %CLICOLLABEL Peak-Strms
iShelfOltPonSdvInterval24PeakStreams OBJECT-TYPE
    SYNTAX      Counter32
    MAX-ACCESS  read-only
    STATUS      current
    DESCRIPTION
        "This counter is the peak number of simultaneous
         streams during the interval."
    ::= { iShelfOltPonSdvInterval24Entry 4 }

-- %CLISHOWGROUP i24table.1
-- //PMPARAMTYPE PEAK
-- %CLICOLLABEL Peak-BW
iShelfOltPonSdvInterval24PeakBandwidth OBJECT-TYPE
    SYNTAX      Counter32
    MAX-ACCESS  read-only
    STATUS      current
    DESCRIPTION
        "This counter is the peak bandwidth usage
         during the interval."
    ::= { iShelfOltPonSdvInterval24Entry 5 }

-- %CLISHOWGROUP i24table.2
-- %CLICOLLABEL Packets
iShelfOltPonSdvInterval24Packets OBJECT-TYPE
    SYNTAX      Counter32
    MAX-ACCESS  read-only
    STATUS      current
    DESCRIPTION
        "This counter is the total multicast packets forwarded
         during the interval."
    ::= { iShelfOltPonSdvInterval24Entry 6 }

-- %CLISHOWGROUP i24table.2
-- %CLICOLLABEL Bytes
iShelfOltPonSdvInterval24Bytes OBJECT-TYPE
    SYNTAX      Counter32
    MAX-ACCESS  read-only
    STATUS      current
    DESCRIPTION
        "This counter is the total multicast bytes forwarded
         during the interval."
    ::= { iShelfOltPonSdvInterval24Entry 7 }

-- %CLISHOWGROUP i24table.2
-- %CLICOLLABEL Drops
iShelfOltPonSdvInterval24Drops OBJECT-TYPE
    SYNTAX      Counter32
    MAX-ACCESS  read-only
    STATUS      current
    DESCRIPTION
        "This counter is the total multicast packets dropped
         during the interval."
    ::= { iShelfOltPonSdvInterval24Entry 8 }

-- %CLISHOWGROUP i24table.2
-- %CLICOLLABEL Joins
iShelfOltPonSdvInterval24Joins OBJECT-TYPE
    SYNTAX      Counter32
    MAX-ACCESS  read-only
    STATUS      current
    DESCRIPTION
        "This counter is the total join messages (IGMP
         membership reports) received from set-top-boxes
         during the interval."
    ::= { iShelfOltPonSdvInterval24Entry 9 }

-- %CLISHOWGROUP i24table.2
-- %CLICOLLABEL Leaves
iShelfOltPonSdvInterval24Leaves OBJECT-TYPE
    SYNTAX      Counter32
    MAX-ACCESS  read-only
    STATUS      current
    DESCRIPTION
        "This counter is the total stream leaves executed
         during the interval."
    ::= { iShelfOltPonSdvInterval24Entry 10 }

-- %CLISHOWGROUP i24table.2
-- %CLICOLLABEL Queries
iShelfOltPonSdvInterval24Queries OBJECT-TYPE
    SYNTAX      Counter32
    MAX-ACCESS  read-only
    STATUS      current
    DESCRIPTION
        "This counter is the total queries received
         during the interval."
    ::= { iShelfOltPonSdvInterval24Entry 11 }

-- %CLISHOWGROUP i24table.1
-- %CLICOLLABEL Limit-Strms
iShelfOltPonSdvInterval24StreamsAlerts OBJECT-TYPE
    SYNTAX      Counter32
    MAX-ACCESS  read-only
    STATUS      current
    DESCRIPTION
        "This counter is the total times the Stream Limit
         threshold was exceeded during the interval."
    ::= { iShelfOltPonSdvInterval24Entry 12 }

-- %CLISHOWGROUP i24table.1
-- %CLICOLLABEL Limit-BW
iShelfOltPonSdvInterval24BandwidthAlerts OBJECT-TYPE
    SYNTAX      Counter32
    MAX-ACCESS  read-only
    STATUS      current
    DESCRIPTION
        "This counter is the total times the bandwidth Limit
         threshold was exceeded during the interval."
    ::= { iShelfOltPonSdvInterval24Entry 13 }


-- %CLISHOWGROUP i24table.1
iShelfOltPonSdvInterval24ValidData OBJECT-TYPE
    SYNTAX      IShelfPerfInvalidFlag
    MAX-ACCESS  read-only
    STATUS      current
    DESCRIPTION
        "This object indicates if the data for this interval
         is valid."
    ::= { iShelfOltPonSdvInterval24Entry 14 }

-- ++++++++++++++++++++++++++++++++++++++++++++++++++++++++++++++++++++++++
--
-- iShelfOltGigEthernetCurrent15Table -
--
-- ++++++++++++++++++++++++++++++++++++++++++++++++++++++++++++++++++++++++

-- %CLICMDPREFIX pm:olt:geth
-- %CLICMDABBR c15table
iShelfOltGigEthernetCurrent15Table OBJECT-TYPE
    SYNTAX      SEQUENCE OF IShelfOltGigEthernetCurrent15Entry
    MAX-ACCESS  not-accessible
    STATUS      current
    DESCRIPTION
        "This table contains performance history data pertaining
         to the OLT gig ethernet interface for the current 15 minute
         interval. Error counters are maintained in this table
         and threshold crossing alerts may be generated if any
         of the error counters cross the threshold.

         Rows in this table are automatically created."
    ::= { iShelfOltPm 1 }

iShelfOltGigEthernetCurrent15Entry OBJECT-TYPE
    SYNTAX      IShelfOltGigEthernetCurrent15Entry
    MAX-ACCESS  not-accessible
    STATUS      current
    DESCRIPTION
        "Each entry contains performance history data for one
         OLT gig ethernet interface."
    INDEX       { iShelfOltGigEthernetCurrent15Location }
    ::= { iShelfOltGigEthernetCurrent15Table 1 }

IShelfOltGigEthernetCurrent15Entry ::=
    SEQUENCE {
        iShelfOltGigEthernetCurrent15Location
            IShelfLocation,
        iShelfOltGigEthernetCurrent15Crc
            Counter32,
        iShelfOltGigEthernetCurrent15LongPkts
            Counter32,
        iShelfOltGigEthernetCurrent15ShortPkts
            Counter32,
        iShelfOltGigEthernetCurrent15Collisions
            Counter32,
        iShelfOltGigEthernetCurrent15CollisionDrops
            Counter32,
        iShelfOltGigEthernetCurrent15ValidData
            IShelfPerfInvalidFlag,
        iShelfOltGigEthernetCurrent15ThresholdCrossingPointer
            IShelfThresholdCrossingPointer
    }

iShelfOltGigEthernetCurrent15Location OBJECT-TYPE
    SYNTAX      IShelfLocation
    MAX-ACCESS  read-only
    STATUS      current
    DESCRIPTION "This object identifies the gig ethernet interface."
    ::= { iShelfOltGigEthernetCurrent15Entry 1 }

-- %CLICOLLABEL CRCErrs
iShelfOltGigEthernetCurrent15Crc OBJECT-TYPE
    SYNTAX      Counter32
    MAX-ACCESS  read-only
    STATUS      current
    DESCRIPTION
        "This counter is the number of received frames with
         CRC errors."
    ::= { iShelfOltGigEthernetCurrent15Entry 2 }

-- %CLICOLLABEL LongPkts
iShelfOltGigEthernetCurrent15LongPkts OBJECT-TYPE
    SYNTAX      Counter32
    MAX-ACCESS  read-only
    STATUS      current
    DESCRIPTION
        "This counter is the number of received frames that
         were too long (i.e., more than 1500 bytes)."
    ::= { iShelfOltGigEthernetCurrent15Entry 3 }

-- %CLICOLLABEL ShortPkts
iShelfOltGigEthernetCurrent15ShortPkts OBJECT-TYPE
    SYNTAX      Counter32
    MAX-ACCESS  read-only
    STATUS      current
    DESCRIPTION
        "This counter is the number of received frames that
         were too short (i.e., less than 64 bytes)."
    ::= { iShelfOltGigEthernetCurrent15Entry 4 }

-- %CLICOLLABEL Colls
iShelfOltGigEthernetCurrent15Collisions OBJECT-TYPE
    SYNTAX      Counter32
    MAX-ACCESS  read-only
    STATUS      current
    DESCRIPTION
        "This counter is the number of collision
         conditions detected."
    ::= { iShelfOltGigEthernetCurrent15Entry 5 }

-- %CLICOLLABEL Coll-Drops
iShelfOltGigEthernetCurrent15CollisionDrops OBJECT-TYPE
    SYNTAX      Counter32
    MAX-ACCESS  read-only
    STATUS      current
    DESCRIPTION
        "This counter is the number of collision drop
         conditions detected."
    ::= { iShelfOltGigEthernetCurrent15Entry 6 }

iShelfOltGigEthernetCurrent15ValidData OBJECT-TYPE
    SYNTAX      IShelfPerfInvalidFlag
    MAX-ACCESS  read-only
    STATUS      current
    DESCRIPTION
        "This object indicates if the data for this interval
         is valid."
    ::= { iShelfOltGigEthernetCurrent15Entry 7 }

iShelfOltGigEthernetCurrent15ThresholdCrossingPointer OBJECT-TYPE
    SYNTAX      IShelfThresholdCrossingPointer
    MAX-ACCESS  read-write
    STATUS      current
    DESCRIPTION
        "This object points to the threshold crossing entry
         (in iShelfOltThresholdCrossingTable). A value of zero
         indicates threshold crossing are not being generated."
    DEFVAL      { 0 }
    ::= { iShelfOltGigEthernetCurrent15Entry 8 }

-- ++++++++++++++++++++++++++++++++++++++++++++++++++++++++++++++++++++++++
--
-- iShelfOltGigEthernetInterval15Table -
--
-- ++++++++++++++++++++++++++++++++++++++++++++++++++++++++++++++++++++++++

-- %CLICMDPREFIX pm:olt:geth
-- %CLICMDABBR i15table
iShelfOltGigEthernetInterval15Table OBJECT-TYPE
    SYNTAX      SEQUENCE OF IShelfOltGigEthernetInterval15Entry
    MAX-ACCESS  not-accessible
    STATUS      current
    DESCRIPTION
        "This table contains performance history data pertaining
         the the OLT gig ethernet interface for previous 15 minute
         intervals.

         Rows in this table are automatically created."
    ::= { iShelfOltPm 2 }

iShelfOltGigEthernetInterval15Entry OBJECT-TYPE
    SYNTAX      IShelfOltGigEthernetInterval15Entry
    MAX-ACCESS  not-accessible
    STATUS      current
    DESCRIPTION
        "Each entry contains performance history data for one
         OLT gig ethernet interface."
    INDEX       { iShelfOltGigEthernetInterval15Location,
                  iShelfOltGigEthernetInterval15Number }
    ::= { iShelfOltGigEthernetInterval15Table 1 }

IShelfOltGigEthernetInterval15Entry ::=
    SEQUENCE {
        iShelfOltGigEthernetInterval15Location
            IShelfLocation,
        iShelfOltGigEthernetInterval15Number
            INTEGER,
        iShelfOltGigEthernetInterval15Crc
            Counter32,
        iShelfOltGigEthernetInterval15LongPkts
            Counter32,
        iShelfOltGigEthernetInterval15ShortPkts
            Counter32,
        iShelfOltGigEthernetInterval15Collisions
            Counter32,
        iShelfOltGigEthernetInterval15CollisionDrops
            Counter32,
        iShelfOltGigEthernetInterval15ValidData
            IShelfPerfInvalidFlag
    }

iShelfOltGigEthernetInterval15Location OBJECT-TYPE
    SYNTAX      IShelfLocation
    MAX-ACCESS  read-only
    STATUS      current
    DESCRIPTION "This object identifies the gig ethernet interface."
    ::= { iShelfOltGigEthernetInterval15Entry 1 }

-- %CLICOLLABEL Int
-- %CLIWIDTH 3
iShelfOltGigEthernetInterval15Number OBJECT-TYPE
    SYNTAX      INTEGER(1..32)
    MAX-ACCESS  read-only
    STATUS      current
    DESCRIPTION
        "This object identifies the interval for which this set
         of statistics is available. The interval identified
         by 1 is the most recently completed 15 minute interval."
    ::= { iShelfOltGigEthernetInterval15Entry 2 }

-- %CLICOLLABEL CRCErrs
iShelfOltGigEthernetInterval15Crc OBJECT-TYPE
    SYNTAX      Counter32
    MAX-ACCESS  read-only
    STATUS      current
    DESCRIPTION
        "This counter is the number of received frames with
         CRC errors."
    ::= { iShelfOltGigEthernetInterval15Entry 3 }

-- %CLICOLLABEL LongPkts
iShelfOltGigEthernetInterval15LongPkts OBJECT-TYPE
    SYNTAX      Counter32
    MAX-ACCESS  read-only
    STATUS      current
    DESCRIPTION
        "This counter is the number of received frames that
         were too long (i.e., more than 1500 bytes)."
    ::= { iShelfOltGigEthernetInterval15Entry 4 }

-- %CLICOLLABEL ShortPkts
iShelfOltGigEthernetInterval15ShortPkts OBJECT-TYPE
    SYNTAX      Counter32
    MAX-ACCESS  read-only
    STATUS      current
    DESCRIPTION
        "This counter is the number of received frames that
         were too short (i.e., less than 64 bytes)."
    ::= { iShelfOltGigEthernetInterval15Entry 5 }

-- %CLICOLLABEL Colls
iShelfOltGigEthernetInterval15Collisions OBJECT-TYPE
    SYNTAX      Counter32
    MAX-ACCESS  read-only
    STATUS      current
    DESCRIPTION
        "This counter is the number of collisions
         conditions detected."
    ::= { iShelfOltGigEthernetInterval15Entry 6 }

-- %CLICOLLABEL Coll-Drops
iShelfOltGigEthernetInterval15CollisionDrops OBJECT-TYPE
    SYNTAX      Counter32
    MAX-ACCESS  read-only
    STATUS      current
    DESCRIPTION
        "This counter is the number of collision drop
         conditions detected."
    ::= { iShelfOltGigEthernetInterval15Entry 7 }

iShelfOltGigEthernetInterval15ValidData OBJECT-TYPE
    SYNTAX      IShelfPerfInvalidFlag
    MAX-ACCESS  read-only
    STATUS      current
    DESCRIPTION
        "This object indicates if the data for this interval
         is valid."
    ::= { iShelfOltGigEthernetInterval15Entry 8 }

-- ++++++++++++++++++++++++++++++++++++++++++++++++++++++++++++++++++++++++
--
-- iShelfOltGigEthernetCurrent24Table -
--
-- ++++++++++++++++++++++++++++++++++++++++++++++++++++++++++++++++++++++++

-- %CLICMDPREFIX pm:olt:geth
-- %CLICMDABBR c24table
iShelfOltGigEthernetCurrent24Table OBJECT-TYPE
    SYNTAX      SEQUENCE OF IShelfOltGigEthernetCurrent24Entry
    MAX-ACCESS  not-accessible
    STATUS      current
    DESCRIPTION
        "This table contains performance history data pertaining
         to the OLT gig ethernet interface for the current 24 hour
         interval. Threshold crossing alerts may be applied to
         the error counters in this table."
    ::= { iShelfOltPm 3 }

iShelfOltGigEthernetCurrent24Entry OBJECT-TYPE
    SYNTAX      IShelfOltGigEthernetCurrent24Entry
    MAX-ACCESS  not-accessible
    STATUS      current
    DESCRIPTION
        "Each entry contains performance history data for one
         OLT gig ethernet interface."
    INDEX       { iShelfOltGigEthernetCurrent24Location }
    ::= { iShelfOltGigEthernetCurrent24Table 1 }

IShelfOltGigEthernetCurrent24Entry ::=
    SEQUENCE {
        iShelfOltGigEthernetCurrent24Location
            IShelfLocation,
        iShelfOltGigEthernetCurrent24Crc
            Counter32,
        iShelfOltGigEthernetCurrent24LongPkts
            Counter32,
        iShelfOltGigEthernetCurrent24ShortPkts
            Counter32,
        iShelfOltGigEthernetCurrent24Collisions
            Counter32,
        iShelfOltGigEthernetCurrent24CollisionDrops
            Counter32,
        iShelfOltGigEthernetCurrent24ValidData
            IShelfPerfInvalidFlag,
        iShelfOltGigEthernetCurrent24ThresholdCrossingPointer
            IShelfThresholdCrossingPointer
    }

iShelfOltGigEthernetCurrent24Location OBJECT-TYPE
    SYNTAX      IShelfLocation
    MAX-ACCESS  read-only
    STATUS      current
    DESCRIPTION "This object identifies the gig ethernet interface."
    ::= { iShelfOltGigEthernetCurrent24Entry 1 }

-- %CLICOLLABEL CRCErrs
iShelfOltGigEthernetCurrent24Crc OBJECT-TYPE
    SYNTAX      Counter32
    MAX-ACCESS  read-only
    STATUS      current
    DESCRIPTION
        "This counter is the number of received frames with
         CRC errors."
    ::= { iShelfOltGigEthernetCurrent24Entry 2 }

-- %CLICOLLABEL LongPkts
iShelfOltGigEthernetCurrent24LongPkts OBJECT-TYPE
    SYNTAX      Counter32
    MAX-ACCESS  read-only
    STATUS      current
    DESCRIPTION
        "This counter is the number of received frames that
         were too long (i.e., more than 1500 bytes)."
    ::= { iShelfOltGigEthernetCurrent24Entry 3 }

-- %CLICOLLABEL ShortPkts
iShelfOltGigEthernetCurrent24ShortPkts OBJECT-TYPE
    SYNTAX      Counter32
    MAX-ACCESS  read-only
    STATUS      current
    DESCRIPTION
        "This counter is the number of received frames that
         were too short (i.e., less than 64 bytes)."
    ::= { iShelfOltGigEthernetCurrent24Entry 4 }

-- %CLICOLLABEL Colls
iShelfOltGigEthernetCurrent24Collisions OBJECT-TYPE
    SYNTAX      Counter32
    MAX-ACCESS  read-only
    STATUS      current
    DESCRIPTION
        "This counter is the number of collision
         conditions detected."
    ::= { iShelfOltGigEthernetCurrent24Entry 5 }

-- %CLICOLLABEL Coll-Drops
iShelfOltGigEthernetCurrent24CollisionDrops OBJECT-TYPE
    SYNTAX      Counter32
    MAX-ACCESS  read-only
    STATUS      current
    DESCRIPTION
        "This counter is the number of collision drop
         conditions detected."
    ::= { iShelfOltGigEthernetCurrent24Entry 6 }

iShelfOltGigEthernetCurrent24ValidData OBJECT-TYPE
    SYNTAX      IShelfPerfInvalidFlag
    MAX-ACCESS  read-only
    STATUS      current
    DESCRIPTION
        "This object indicates if the data for this interval
         is valid."
    ::= { iShelfOltGigEthernetCurrent24Entry 7 }

iShelfOltGigEthernetCurrent24ThresholdCrossingPointer OBJECT-TYPE
    SYNTAX      IShelfThresholdCrossingPointer
    MAX-ACCESS  read-write
    STATUS      current
    DESCRIPTION
        "This object points to the threshold crossing entry
         (in iShelfOltThresholdCrossingTable). A value of zero
         indicates threshold crossing are not being generated."
    DEFVAL      { 0 }
    ::= { iShelfOltGigEthernetCurrent24Entry 8 }

-- ++++++++++++++++++++++++++++++++++++++++++++++++++++++++++++++++++++++++
--
-- iShelfOltGigEthernetInterval24Table -
--
-- ++++++++++++++++++++++++++++++++++++++++++++++++++++++++++++++++++++++++

-- %CLICMDPREFIX pm:olt:geth
-- %CLICMDABBR i24table
iShelfOltGigEthernetInterval24Table OBJECT-TYPE
    SYNTAX      SEQUENCE OF IShelfOltGigEthernetInterval24Entry
    MAX-ACCESS  not-accessible
    STATUS      current
    DESCRIPTION
        "The table contains performance history data pertaining
         the OLT gig ethernet interface for previous 24 hour intervals.

         Rows in this table are automatically created."
    ::= { iShelfOltPm 4 }

iShelfOltGigEthernetInterval24Entry OBJECT-TYPE
    SYNTAX      IShelfOltGigEthernetInterval24Entry
    MAX-ACCESS  not-accessible
    STATUS      current
    DESCRIPTION
        "Each entry contains performance history data for one
         OLT gig ethernet interface."
    INDEX       { iShelfOltGigEthernetInterval24Location,
                  iShelfOltGigEthernetInterval24Number }
    ::= { iShelfOltGigEthernetInterval24Table 1 }

IShelfOltGigEthernetInterval24Entry ::=
    SEQUENCE {
        iShelfOltGigEthernetInterval24Location
            IShelfLocation,
        iShelfOltGigEthernetInterval24Number
            INTEGER,
        iShelfOltGigEthernetInterval24Crc
            Counter32,
        iShelfOltGigEthernetInterval24LongPkts
            Counter32,
        iShelfOltGigEthernetInterval24ShortPkts
            Counter32,
        iShelfOltGigEthernetInterval24Collisions
            Counter32,
        iShelfOltGigEthernetInterval24CollisionDrops
            Counter32,
        iShelfOltGigEthernetInterval24ValidData
            IShelfPerfInvalidFlag
    }

iShelfOltGigEthernetInterval24Location OBJECT-TYPE
    SYNTAX      IShelfLocation
    MAX-ACCESS  read-only
    STATUS      current
    DESCRIPTION "This object identifies the gig ethernet interface."
    ::= { iShelfOltGigEthernetInterval24Entry 1 }

-- %CLICOLLABEL Int
-- %CLIWIDTH 3
iShelfOltGigEthernetInterval24Number OBJECT-TYPE
    SYNTAX      INTEGER(1..6)
    MAX-ACCESS  read-only
    STATUS      current
    DESCRIPTION
        "This object identifies the interval for which this set
         of statistics is available. The interval identified
         by 1 is the most recently completed 24 hour interval."
    ::= { iShelfOltGigEthernetInterval24Entry 2 }

-- %CLICOLLABEL CRCErrs
iShelfOltGigEthernetInterval24Crc OBJECT-TYPE
    SYNTAX      Counter32
    MAX-ACCESS  read-only
    STATUS      current
    DESCRIPTION
        "This counter is the number of received frames with
         CRC errors."
    ::= { iShelfOltGigEthernetInterval24Entry 3 }

-- %CLICOLLABEL LongPkts
iShelfOltGigEthernetInterval24LongPkts OBJECT-TYPE
    SYNTAX      Counter32
    MAX-ACCESS  read-only
    STATUS      current
    DESCRIPTION
        "This counter is the number of received frames that
         were too long (i.e., more than 1500 bytes)."
    ::= { iShelfOltGigEthernetInterval24Entry 4 }

-- %CLICOLLABEL ShortPkts
iShelfOltGigEthernetInterval24ShortPkts OBJECT-TYPE
    SYNTAX      Counter32
    MAX-ACCESS  read-only
    STATUS      current
    DESCRIPTION
        "This counter is the number of received frames that
         were too short (i.e., less than 64 bytes)."
    ::= { iShelfOltGigEthernetInterval24Entry 5 }

-- %CLICOLLABEL Colls
iShelfOltGigEthernetInterval24Collisions OBJECT-TYPE
    SYNTAX      Counter32
    MAX-ACCESS  read-only
    STATUS      current
    DESCRIPTION
        "This counter is the number of collisions
         conditions detected."
    ::= { iShelfOltGigEthernetInterval24Entry 6 }

-- %CLICOLLABEL Coll-Drops
iShelfOltGigEthernetInterval24CollisionDrops OBJECT-TYPE
    SYNTAX      Counter32
    MAX-ACCESS  read-only
    STATUS      current
    DESCRIPTION
        "This counter is the number of collision drop
         conditions detected."
    ::= { iShelfOltGigEthernetInterval24Entry 7 }

iShelfOltGigEthernetInterval24ValidData OBJECT-TYPE
    SYNTAX      IShelfPerfInvalidFlag
    MAX-ACCESS  read-only
    STATUS      current
    DESCRIPTION
        "This object indicates if the data for this interval
         is valid."
    ::= { iShelfOltGigEthernetInterval24Entry 8 }

-- ++++++++++++++++++++++++++++++++++++++++++++++++++++++++++++++++++++++++
--
-- iShelfOltTrafficShaperStatsTable -
--
-- ++++++++++++++++++++++++++++++++++++++++++++++++++++++++++++++++++++++++

-- %CLICMDPREFIX pm:olt:shaper
-- %CLICMDABBR stats
iShelfOltTrafficShaperStatsTable OBJECT-TYPE
    SYNTAX      SEQUENCE OF IShelfOltTrafficShaperStatsEntry
    MAX-ACCESS  not-accessible
    STATUS      current
    DESCRIPTION ""
    ::= { iShelfOltPm 5 }

iShelfOltTrafficShaperStatsEntry OBJECT-TYPE
    SYNTAX      IShelfOltTrafficShaperStatsEntry
    MAX-ACCESS  not-accessible
    STATUS      current
    DESCRIPTION ""
    INDEX       { iShelfOltTrafficShaperStatsLocation,
                  iShelfOltTrafficShaperStatsIndex }
    ::= { iShelfOltTrafficShaperStatsTable 1 }

IShelfOltTrafficShaperStatsEntry ::=
    SEQUENCE {
        iShelfOltTrafficShaperStatsLocation
            IShelfLocation,
        iShelfOltTrafficShaperStatsIndex
            IShelfOltTrafficShaperIndex,
        iShelfOltTrafficShaperStatsOutPkts
            Counter32,
        iShelfOltTrafficShaperStatsOutOctets
            Counter32,
        iShelfOltTrafficShaperStatsDiscards
            Counter32
    }

iShelfOltTrafficShaperStatsLocation OBJECT-TYPE
    SYNTAX      IShelfLocation
    MAX-ACCESS  read-only
    STATUS      current
    DESCRIPTION "Node/Shelf/Slot of OLT"
    ::= { iShelfOltTrafficShaperStatsEntry 1 }

iShelfOltTrafficShaperStatsIndex OBJECT-TYPE
    SYNTAX      IShelfOltTrafficShaperIndex
    MAX-ACCESS  read-only
    STATUS      current
    DESCRIPTION "The traffic shaper profile instance."
    ::= { iShelfOltTrafficShaperStatsEntry 2 }
    
iShelfOltTrafficShaperStatsOutPkts OBJECT-TYPE
    SYNTAX      Counter32
    MAX-ACCESS  read-only
    STATUS      current
    DESCRIPTION "Number of packets transmitted via the shaper."
    ::= { iShelfOltTrafficShaperStatsEntry 3 }
    
iShelfOltTrafficShaperStatsOutOctets OBJECT-TYPE
    SYNTAX      Counter32
    MAX-ACCESS  read-only
    STATUS      current
    DESCRIPTION "Number of octets transmitted via the shaper."
    ::= { iShelfOltTrafficShaperStatsEntry 4 }
    
iShelfOltTrafficShaperStatsDiscards OBJECT-TYPE
    SYNTAX      Counter32
    MAX-ACCESS  read-only
    STATUS      current
    DESCRIPTION
        "Number of packets discarded due to rate limiting of
         the shaper."
    ::= { iShelfOltTrafficShaperStatsEntry 5 }
    
-- ++++++++++++++++++++++++++++++++++++++++++++++++++++++++++++++++++++++++
--
-- iShelfOltVlanStatsTable -
--
-- ++++++++++++++++++++++++++++++++++++++++++++++++++++++++++++++++++++++++

-- %CLICMDPREFIX pm:olt:vlan
-- %CLICMDABBR stats
iShelfOltVlanStatsTable OBJECT-TYPE
    SYNTAX      SEQUENCE OF IShelfOltVlanStatsEntry
    MAX-ACCESS  not-accessible
    STATUS      current
    DESCRIPTION ""
    ::= { iShelfOltPm 6 }

iShelfOltVlanStatsEntry OBJECT-TYPE
    SYNTAX      IShelfOltVlanStatsEntry
    MAX-ACCESS  not-accessible
    STATUS      current
    DESCRIPTION ""
    INDEX       { iShelfOltVlanStatsLocation,
                  iShelfOltVlanStatsIfType }
    ::= { iShelfOltVlanStatsTable 1 }

IShelfOltVlanStatsEntry ::=
    SEQUENCE {
        iShelfOltVlanStatsLocation
            IShelfLocation,
        iShelfOltVlanStatsIfType
            INTEGER,
        iShelfOltVlanStatsLearnedMacs
            Counter32,
        iShelfOltVlanStatsFixedMacs
            Counter32,
        iShelfOltVlanStatsMcastInForwPkts
            Counter32,
        iShelfOltVlanStatsInDropPkts
            Counter32,
        iShelfOltVlanStatsUcastInForwPkts
            Counter32,
        iShelfOltVlanStatsUcastHairpinPkts
            Counter32,
        iShelfOltVlanStatsMcastInForwOctets
            Counter32,
        iShelfOltVlanStatsInDropOctets
            Counter32,
        iShelfOltVlanStatsUcastInForwOctets
            Counter32,
        iShelfOltVlanStatsUcastHairpinOctets
            Counter32
    }

iShelfOltVlanStatsLocation OBJECT-TYPE
    SYNTAX      IShelfLocation
    MAX-ACCESS  read-only
    STATUS      current
    DESCRIPTION "Node/Shelf/Slot of OLT"
    ::= { iShelfOltVlanStatsEntry 1 }

iShelfOltVlanStatsIfType OBJECT-TYPE
    SYNTAX      INTEGER {
                    pon(1),       -- All OLT PON interfaces
                    gige(2),      -- OLT Gigabit Ethernet interface
                    remote(3)     -- All Remote interfaces via backplane
            }
    MAX-ACCESS  read-only
    STATUS      current
    DESCRIPTION "Indicates the type of interface to which the counts apply."
    ::= { iShelfOltVlanStatsEntry 2 }

    
iShelfOltVlanStatsLearnedMacs OBJECT-TYPE
    SYNTAX      Counter32
    MAX-ACCESS  read-only
    STATUS      current
    DESCRIPTION "Number of remote MacAddresses learned for the interface type."
    ::= { iShelfOltVlanStatsEntry 3 }
    
iShelfOltVlanStatsFixedMacs OBJECT-TYPE
    SYNTAX      Counter32
    MAX-ACCESS  read-only
    STATUS      current
    DESCRIPTION "Number of MacAddresses updated for the interface type."
    ::= { iShelfOltVlanStatsEntry 4 }
    
iShelfOltVlanStatsMcastInForwPkts OBJECT-TYPE
    SYNTAX      Counter32
    MAX-ACCESS  read-only
    STATUS      current
    DESCRIPTION
        "Number of multi-cast packets forwarded by the interface type.
         In the case of a PON type interface this would be the number forwarded
         to the GigE or remote interface.  For the GigE or remote types it
         would be the number forwarded to the PON interfaces."
    ::= { iShelfOltVlanStatsEntry 5 }

iShelfOltVlanStatsInDropPkts OBJECT-TYPE
    SYNTAX      Counter32
    MAX-ACCESS  read-only
    STATUS      current
    DESCRIPTION "Number of dropped packets for the interface type."
    ::= { iShelfOltVlanStatsEntry 6 }

iShelfOltVlanStatsUcastInForwPkts OBJECT-TYPE
    SYNTAX      Counter32
    MAX-ACCESS  read-only
    STATUS      current
    DESCRIPTION
        "Number of unicast forwarded packets for the interface type.
         In the case of a PON type interface this would be the number forwarded
         to the GigE or remote interface.  For the GigE or remote types it
         would be the number forwarded to the PON interfaces."
    ::= { iShelfOltVlanStatsEntry 7 }

iShelfOltVlanStatsUcastHairpinPkts OBJECT-TYPE
    SYNTAX      Counter32
    MAX-ACCESS  read-only
    STATUS      current
    DESCRIPTION
        "Number of unicast hairpined packets for the interface type.
         This count is only applicable for pon type interfaces."
    ::= { iShelfOltVlanStatsEntry 8 }

iShelfOltVlanStatsMcastInForwOctets OBJECT-TYPE
    SYNTAX      Counter32
    MAX-ACCESS  read-only
    STATUS      current
    DESCRIPTION
        "Number of multi-cast octets forwarded by the interface type.
         In the case of a PON type interface this would be the number forwarded
         to the GigE or remote interface.  For the GigE or remote types it
         would be the number forwarded to the PON interfaces."
    ::= { iShelfOltVlanStatsEntry 9 }

iShelfOltVlanStatsInDropOctets OBJECT-TYPE
    SYNTAX      Counter32
    MAX-ACCESS  read-only
    STATUS      current
    DESCRIPTION "Number of dropped octets for the interface type."
    ::= { iShelfOltVlanStatsEntry 10 }

iShelfOltVlanStatsUcastInForwOctets OBJECT-TYPE
    SYNTAX      Counter32
    MAX-ACCESS  read-only
    STATUS      current
    DESCRIPTION
        "Number of unicast forwarded octets for the interface type.
         In the case of a PON type interface this would be the number forwarded
         to the GigE or remote interface.  For the GigE or remote types it
         would be the number forwarded to the PON interfaces."
    ::= { iShelfOltVlanStatsEntry 11 }

iShelfOltVlanStatsUcastHairpinOctets OBJECT-TYPE
    SYNTAX      Counter32
    MAX-ACCESS  read-only
    STATUS      current
    DESCRIPTION
        "Number of unicast hairpined octets for the interface type.
         This count is only applicable for pon type interfaces."
    ::= { iShelfOltVlanStatsEntry 12 }

-- ++++++++++++++++++++++++++++++++++++++++++++++++++++++++++++++++++++++++
--
-- iShelfTrapStatsTable - 
--
-- ++++++++++++++++++++++++++++++++++++++++++++++++++++++++++++++++++++++++

iShelfTrapStatsNumTraps OBJECT-TYPE
    SYNTAX      Counter32
    MAX-ACCESS  read-only
    STATUS      current
    DESCRIPTION "Count of number of traps processed at the EGW."
    ::= { iShelfEgwPmTrap 1 }

iShelfTrapStatsNumQueued OBJECT-TYPE
    SYNTAX      Counter32
    MAX-ACCESS  read-only
    STATUS      current
    DESCRIPTION
        "Count of number of traps queued by the EGW due to
         throttling at the EGW."
    ::= { iShelfEgwPmTrap 2 }

iShelfTrapStatsPeakQueueSize OBJECT-TYPE
    SYNTAX      Counter32
    MAX-ACCESS  read-only
    STATUS      current
    DESCRIPTION "Maximum size the trap queue reached due to throttling"
    ::= { iShelfEgwPmTrap 3 }

iShelfTrapStatsNumDiscarded OBJECT-TYPE
    SYNTAX      Counter32
    MAX-ACCESS  read-only
    STATUS      current
    DESCRIPTION "Number of traps discarded due to resource limitations"
    ::= { iShelfEgwPmTrap 4 }

iShelfTrapStatsNumFiltered OBJECT-TYPE
    SYNTAX      Counter32
    MAX-ACCESS  read-only
    STATUS      current
    DESCRIPTION "Number of traps ignored due to filtering"
    ::= { iShelfEgwPmTrap 5 }

END
