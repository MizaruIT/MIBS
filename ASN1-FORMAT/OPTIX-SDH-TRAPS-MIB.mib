--
-- OPTIX-SDH-TRAPS-MIB.mib
-- MIB generated by MG-SOFT Visual MIB Builder Version 3.0 Build 253
-- Wednesday, October 25, 2006 at 15:59:00
--


	OPTIX-SDH-TRAPS-MIB DEFINITIONS ::= BEGIN
 
		IMPORTS
			optixCommonSdh			
				FROM OPTIX-OID-MIB			
			almCurAlarmDataNID, almCurAlarmDataBid, almCurAlarmDataEid, almCurAlarmDataSeverity, almCurAlarmDataState, 
			almCurAlarmDataStartTime, almCurAlarmDataEndTime, almCurAlarmDataPara, almCurAlarmDataTableStatus			
				FROM OPTIX-SDH-ALM-MIB			
			SdhPerformanceEventType, SdhAlarmEventType			
				FROM OPTIX-SDH-TC-MIB			
			OBJECT-GROUP, MODULE-COMPLIANCE, NOTIFICATION-GROUP			
				FROM SNMPv2-CONF			
			mgmt, Gauge32, OBJECT-TYPE, MODULE-IDENTITY, NOTIFICATION-TYPE			
				FROM SNMPv2-SMI			
			DateAndTime			
				FROM SNMPv2-TC;
	
	
		optixSdhTraps MODULE-IDENTITY 
			LAST-UPDATED "200604141801Z"		-- April 14, 2006 at 18:01 GMT
			ORGANIZATION 
				"Huawei Technologies co.,Ltd."
			CONTACT-INFO 
				"R&D Building
				Huawei Technologies Co., Ltd.
				Bantian, Longgang District 
				Shenzhen, P. R. China
				http://www.huawei.com
				Zip:518129
				E-mail:support@huawei.com"
			DESCRIPTION 
				"This module describes rules of Huawei transmit 
				platform self-defined types."
			REVISION "200604151247Z"		-- April 15, 2006 at 12:47 GMT
			DESCRIPTION
				"he initial revision of this MIB module."
			::= { optixCommonSdh 40 }
	
--
-- Type definitions
--
		RowStatus ::= INTEGER
			{
			active(1),
			notInService(2),
			notReady(3),
			createAndGo(4),
			createAndWait(5),
			destroy(6)
			}
		
	
	
--
-- Node definitions
--
		-- 1.3.6.1.4.1.2011.2.25.3.10.40.10
		optixTrapsCommon OBJECT IDENTIFIER ::= { optixSdhTraps 10 }
		
--     -------------------------------------------------------------------------
-- Event(REP) common object nodes
-- -------------------------------------------------------------------------
		-- 1.3.6.1.4.1.2011.2.25.3.10.40.10.10
		evtBoardNo OBJECT-TYPE
			SYNTAX Gauge32
			MAX-ACCESS read-only
			STATUS current
			DESCRIPTION
				"Card No.:between 1 and 20"
			::= { optixTrapsCommon 10 }
		
		-- 1.3.6.1.4.1.2011.2.25.3.10.40.10.20
		evtOpticalPort OBJECT-TYPE
			SYNTAX Gauge32
			MAX-ACCESS read-only
			STATUS current
			DESCRIPTION
				"Optical port No.:values depend on type of card"
			::= { optixTrapsCommon 20 }
		
		-- 1.3.6.1.4.1.2011.2.25.3.10.40.10.30
		evtPathNumber OBJECT-TYPE
			SYNTAX Gauge32
			MAX-ACCESS read-only
			STATUS current
			DESCRIPTION
				"Path No.:values depend on type of card"
			::= { optixTrapsCommon 30 }
		
		-- 1.3.6.1.4.1.2011.2.25.3.10.40.10.40
		evtPerEventID OBJECT-TYPE
			SYNTAX SdhPerformanceEventType
			MAX-ACCESS read-only
			STATUS current
			DESCRIPTION
				"Event ID:values depend on type of card"
			::= { optixTrapsCommon 40 }
		
		-- 1.3.6.1.4.1.2011.2.25.3.10.40.10.50
		evtDataValue OBJECT-TYPE
			SYNTAX Gauge32
			MAX-ACCESS read-only
			STATUS current
			DESCRIPTION
				"PM parameter value."
			::= { optixTrapsCommon 50 }
		
		-- 1.3.6.1.4.1.2011.2.25.3.10.40.10.60
		evtAlmEventID OBJECT-TYPE
			SYNTAX SdhAlarmEventType
			MAX-ACCESS read-only
			STATUS current
			DESCRIPTION
				"Event ID:values depend on type of card"
			::= { optixTrapsCommon 60 }
		
		-- 1.3.6.1.4.1.2011.2.25.3.10.40.10.70
		evtStartTime OBJECT-TYPE
			SYNTAX DateAndTime
			MAX-ACCESS read-only
			STATUS current
			DESCRIPTION
				"start date and time."
			::= { optixTrapsCommon 70 }
		
		-- 1.3.6.1.4.1.2011.2.25.3.10.40.10.80
		evtEndTime OBJECT-TYPE
			SYNTAX DateAndTime
			MAX-ACCESS read-only
			STATUS current
			DESCRIPTION
				"end date and time."
			::= { optixTrapsCommon 80 }
		
		-- 1.3.6.1.4.1.2011.2.25.3.10.40.10.90
		evtKeepTime OBJECT-TYPE
			SYNTAX Gauge32
			MAX-ACCESS read-only
			STATUS current
			DESCRIPTION
				"Event Keep Time, Unit: Second"
			::= { optixTrapsCommon 90 }
		
		-- 1.3.6.1.4.1.2011.2.25.3.10.40.10.100
		evtEventStatus OBJECT-TYPE
			SYNTAX INTEGER
				{
				start(1),
				continued(2),
				end(3)
				}
			MAX-ACCESS read-only
			STATUS current
			DESCRIPTION
				"Event Status: Start/End"
			::= { optixTrapsCommon 100 }
		
		-- 1.3.6.1.4.1.2011.2.25.3.10.40.10.110
		evtAlmSeverity OBJECT-TYPE
			SYNTAX INTEGER
				{
				cr(1),
				mj(2),
				mn(3)
				}
			MAX-ACCESS read-only
			STATUS current
			DESCRIPTION
				"Alarm severity."
			::= { optixTrapsCommon 110 }
		
		-- 1.3.6.1.4.1.2011.2.25.3.10.40.10.120
		evtPerPeriod OBJECT-TYPE
			SYNTAX INTEGER
				{
				period15m(1),
				period24h(2)
				}
			MAX-ACCESS read-only
			STATUS current
			DESCRIPTION
				"PM period type: 15 minutes period or one day period."
			::= { optixTrapsCommon 120 }
		
--   Alarm data
		-- 1.3.6.1.4.1.2011.2.25.3.10.40.20
		optixTraps OBJECT IDENTIFIER ::= { optixSdhTraps 20 }
		
		-- 1.3.6.1.4.1.2011.2.25.3.10.40.20.10
		optixTrapsHisDataEvent OBJECT IDENTIFIER ::= { optixTraps 10 }
		
--     -------------------------------------------------------------------------
-- Event(REP) of Performance Monitor
-- 
-- -------------------------------------------------------------------------
		-- 1.3.6.1.4.1.2011.2.25.3.10.40.20.10.1
		evt15mHistoryDataEvents NOTIFICATION-TYPE
			OBJECTS { evtBoardNo, evtOpticalPort, evtPathNumber, evtPerEventID, evtStartTime, 
				evtDataValue }
			STATUS current
			DESCRIPTION 
				"Automatic report evt15mHistoryDataEvents"
			::= { optixTrapsHisDataEvent 1 }
		
		-- 1.3.6.1.4.1.2011.2.25.3.10.40.20.10.2
		evt24hHistoryDataEvents NOTIFICATION-TYPE
			OBJECTS { evtBoardNo, evtOpticalPort, evtPathNumber, evtPerEventID, evtStartTime, 
				evtDataValue }
			STATUS current
			DESCRIPTION 
				"Automatic report evt24hHistoryDataEvents"
			::= { optixTrapsHisDataEvent 2 }
		
		-- 1.3.6.1.4.1.2011.2.25.3.10.40.20.20
		optixTrapsThresholdCrossingEvent OBJECT IDENTIFIER ::= { optixTraps 20 }
		
		-- 1.3.6.1.4.1.2011.2.25.3.10.40.20.20.1
		evt15mThresholdCrossingEvents NOTIFICATION-TYPE
			OBJECTS { evtBoardNo, evtOpticalPort, evtPathNumber, evtPerEventID, evtDataValue, 
				evtStartTime, evtEventStatus }
			STATUS current
			DESCRIPTION 
				"Automatic report 15 minutes threshold crossing"
			::= { optixTrapsThresholdCrossingEvent 1 }
		
		-- 1.3.6.1.4.1.2011.2.25.3.10.40.20.20.2
		evt24hThresholdCrossingEvents NOTIFICATION-TYPE
			OBJECTS { evtBoardNo, evtOpticalPort, evtPathNumber, evtPerEventID, evtDataValue, 
				evtStartTime, evtEventStatus }
			STATUS current
			DESCRIPTION 
				"Automatic report one day threshold crossing"
			::= { optixTrapsThresholdCrossingEvent 2 }
		
		-- 1.3.6.1.4.1.2011.2.25.3.10.40.20.30
		optixTrapsUATEvent OBJECT IDENTIFIER ::= { optixTraps 30 }
		
		-- 1.3.6.1.4.1.2011.2.25.3.10.40.20.30.6
		rsUnavailableTime NOTIFICATION-TYPE
			OBJECTS { evtBoardNo, evtOpticalPort, evtPathNumber, evtStartTime, evtEndTime, 
				evtEventStatus }
			STATUS current
			DESCRIPTION 
				"Automatic report RS UAT event."
			::= { optixTrapsUATEvent 6 }
		
		-- 1.3.6.1.4.1.2011.2.25.3.10.40.20.30.22
		msUnavailableTime NOTIFICATION-TYPE
			OBJECTS { evtBoardNo, evtOpticalPort, evtPathNumber, evtStartTime, evtEndTime, 
				evtEventStatus }
			STATUS current
			DESCRIPTION 
				"Automatic report MS UAT event."
			::= { optixTrapsUATEvent 22 }
		
		-- 1.3.6.1.4.1.2011.2.25.3.10.40.20.30.33
		msFarEndUnavailableTime NOTIFICATION-TYPE
			OBJECTS { evtBoardNo, evtOpticalPort, evtPathNumber, evtStartTime, evtEndTime, 
				evtEventStatus }
			STATUS current
			DESCRIPTION 
				"Automatic report MS FEUAT event."
			::= { optixTrapsUATEvent 33 }
		
		-- 1.3.6.1.4.1.2011.2.25.3.10.40.20.30.54
		hpUnavailableTime NOTIFICATION-TYPE
			OBJECTS { evtBoardNo, evtOpticalPort, evtPathNumber, evtStartTime, evtEndTime, 
				evtEventStatus }
			STATUS current
			DESCRIPTION 
				"Automatic report HP UAT event."
			::= { optixTrapsUATEvent 54 }
		
		-- 1.3.6.1.4.1.2011.2.25.3.10.40.20.30.76
		hpFarEndUnavailableTime NOTIFICATION-TYPE
			OBJECTS { evtBoardNo, evtOpticalPort, evtPathNumber, evtStartTime, evtEndTime, 
				evtEventStatus }
			STATUS current
			DESCRIPTION 
				"Automatic report HP FEUAT event."
			::= { optixTrapsUATEvent 76 }
		
		-- 1.3.6.1.4.1.2011.2.25.3.10.40.20.30.142
		lpFarEndUnavailableTime NOTIFICATION-TYPE
			OBJECTS { evtBoardNo, evtOpticalPort, evtPathNumber, evtStartTime, evtEndTime, 
				evtEventStatus }
			STATUS current
			DESCRIPTION 
				"Automatic report LP FEUAT event."
			::= { optixTrapsUATEvent 142 }
		
		-- 1.3.6.1.4.1.2011.2.25.3.10.40.20.30.150
		lpUnavailableTime NOTIFICATION-TYPE
			OBJECTS { evtBoardNo, evtOpticalPort, evtPathNumber, evtAlmEventID, evtStartTime, 
				evtEventStatus }
			STATUS current
			DESCRIPTION 
				"Automatic report LP UAT event."
			::= { optixTrapsUATEvent 150 }
		
		-- 1.3.6.1.4.1.2011.2.25.3.10.40.20.40
		optixTrapsCSESEvent OBJECT IDENTIFIER ::= { optixTraps 40 }
		
		-- 1.3.6.1.4.1.2011.2.25.3.10.40.20.40.7
		rsConsecutiveSeverelyErroredSecond NOTIFICATION-TYPE
			OBJECTS { evtBoardNo, evtOpticalPort, evtPathNumber, evtStartTime, evtKeepTime
				 }
			STATUS current
			DESCRIPTION 
				"Automatic report RS CSES event."
			::= { optixTrapsCSESEvent 7 }
		
		-- 1.3.6.1.4.1.2011.2.25.3.10.40.20.40.23
		msConsecutiveSeverelyErroredSecond NOTIFICATION-TYPE
			OBJECTS { evtBoardNo, evtOpticalPort, evtPathNumber, evtStartTime, evtKeepTime
				 }
			STATUS current
			DESCRIPTION 
				"Automatic report MS CSES event."
			::= { optixTrapsCSESEvent 23 }
		
		-- 1.3.6.1.4.1.2011.2.25.3.10.40.20.40.24
		msFarEndConsecutiveSeverelyErroredSecond NOTIFICATION-TYPE
			OBJECTS { evtBoardNo, evtOpticalPort, evtPathNumber, evtStartTime, evtKeepTime
				 }
			STATUS current
			DESCRIPTION 
				"Automatic report MS FECSES event."
			::= { optixTrapsCSESEvent 24 }
		
		-- 1.3.6.1.4.1.2011.2.25.3.10.40.20.40.55
		hpConsecutiveSeverelyErroredSecond NOTIFICATION-TYPE
			OBJECTS { evtBoardNo, evtOpticalPort, evtPathNumber, evtStartTime, evtKeepTime
				 }
			STATUS current
			DESCRIPTION 
				"Automatic report HP CSES event."
			::= { optixTrapsCSESEvent 55 }
		
		-- 1.3.6.1.4.1.2011.2.25.3.10.40.20.40.56
		hpFarEndConsecutiveSeverelyErroredSecond NOTIFICATION-TYPE
			OBJECTS { evtBoardNo, evtOpticalPort, evtPathNumber, evtStartTime, evtKeepTime
				 }
			STATUS current
			DESCRIPTION 
				"Automatic report HP FECSES event."
			::= { optixTrapsCSESEvent 56 }
		
		-- 1.3.6.1.4.1.2011.2.25.3.10.40.20.40.151
		lpConsecutiveSeverelyErroredSecond NOTIFICATION-TYPE
			OBJECTS { evtBoardNo, evtOpticalPort, evtPathNumber, evtStartTime, evtKeepTime
				 }
			STATUS current
			DESCRIPTION 
				"Automatic report LP CSES event."
			::= { optixTrapsCSESEvent 151 }
		
		-- 1.3.6.1.4.1.2011.2.25.3.10.40.20.40.152
		lpFarEndConsecutiveSeverelyErroredSecond NOTIFICATION-TYPE
			OBJECTS { evtBoardNo, evtOpticalPort, evtPathNumber, evtStartTime, evtKeepTime
				 }
			STATUS current
			DESCRIPTION 
				"Automatic report LP FECSES event."
			::= { optixTrapsCSESEvent 152 }
		
		-- 1.3.6.1.4.1.2011.2.25.3.10.40.20.50
		optixTrapsAlarm OBJECT IDENTIFIER ::= { optixTraps 50 }
		
		-- 1.3.6.1.4.1.2011.2.25.3.10.40.20.50.1
		criticalAlarm NOTIFICATION-TYPE
			OBJECTS { almCurAlarmDataNID, almCurAlarmDataBid, almCurAlarmDataEid, almCurAlarmDataState, almCurAlarmDataStartTime, 
				almCurAlarmDataPara }
			STATUS current
			DESCRIPTION 
				"Critical Alarm"
			::= { optixTrapsAlarm 1 }
		
		-- 1.3.6.1.4.1.2011.2.25.3.10.40.20.50.2
		majorAlarm NOTIFICATION-TYPE
			OBJECTS { almCurAlarmDataNID, almCurAlarmDataBid, almCurAlarmDataEid, almCurAlarmDataState, almCurAlarmDataStartTime, 
				almCurAlarmDataPara }
			STATUS current
			DESCRIPTION 
				"Major Alarm"
			::= { optixTrapsAlarm 2 }
		
		-- 1.3.6.1.4.1.2011.2.25.3.10.40.20.50.3
		minorAlarm NOTIFICATION-TYPE
			OBJECTS { almCurAlarmDataNID, almCurAlarmDataBid, almCurAlarmDataEid, almCurAlarmDataState, almCurAlarmDataStartTime, 
				almCurAlarmDataPara }
			STATUS current
			DESCRIPTION 
				"Minor Alarm"
			::= { optixTrapsAlarm 3 }
		
		-- 1.3.6.1.4.1.2011.2.25.3.10.40.20.50.4
		warningAlarm NOTIFICATION-TYPE
			OBJECTS { almCurAlarmDataNID, almCurAlarmDataBid, almCurAlarmDataEid, almCurAlarmDataState, almCurAlarmDataStartTime, 
				almCurAlarmDataPara }
			STATUS current
			DESCRIPTION 
				"Warning Alarm"
			::= { optixTrapsAlarm 4 }
		
		-- 1.3.6.1.4.1.2011.2.25.3.10.40.99
		optixSdhTrapsConformance OBJECT IDENTIFIER ::= { optixSdhTraps 99 }
		
		-- 1.3.6.1.4.1.2011.2.25.3.10.40.99.1
		optixSdhTrapsGroups OBJECT IDENTIFIER ::= { optixSdhTrapsConformance 1 }
		
		-- 1.3.6.1.4.1.2011.2.25.3.10.40.99.1.1
		currentObjectGroup OBJECT-GROUP
			OBJECTS { evtPerPeriod, evtAlmSeverity, evtEventStatus, evtKeepTime, evtEndTime, 
				evtStartTime, evtAlmEventID, evtDataValue, evtPerEventID, evtPathNumber, 
				evtOpticalPort, evtBoardNo }
			STATUS current
			DESCRIPTION 
				"Enter the description of the created OBJECT-GROUP."
			::= { optixSdhTrapsGroups 1 }
		
		-- 1.3.6.1.4.1.2011.2.25.3.10.40.99.1.2
		currentNotificationGroup NOTIFICATION-GROUP
			NOTIFICATIONS { evt15mHistoryDataEvents, evt24hHistoryDataEvents, evt15mThresholdCrossingEvents, evt24hThresholdCrossingEvents, rsUnavailableTime, 
				msUnavailableTime, msFarEndUnavailableTime, hpUnavailableTime, hpFarEndUnavailableTime, lpFarEndUnavailableTime, 
				lpUnavailableTime, rsConsecutiveSeverelyErroredSecond, msConsecutiveSeverelyErroredSecond, msFarEndConsecutiveSeverelyErroredSecond, hpConsecutiveSeverelyErroredSecond, 
				hpFarEndConsecutiveSeverelyErroredSecond, lpConsecutiveSeverelyErroredSecond, lpFarEndConsecutiveSeverelyErroredSecond, criticalAlarm, majorAlarm, 
				minorAlarm, warningAlarm }
			STATUS current
			DESCRIPTION 
				"Enter the description of the created NOTIFICATION-GROUP."
			::= { optixSdhTrapsGroups 2 }
		
		-- 1.3.6.1.4.1.2011.2.25.3.10.40.99.2
		optixSdhTrapsCompliances OBJECT IDENTIFIER ::= { optixSdhTrapsConformance 2 }
		
-- this module
		-- 1.3.6.1.4.1.2011.2.25.3.10.40.99.2.1
		optixSdhTrapsbasicCompliance MODULE-COMPLIANCE
			STATUS current
			DESCRIPTION 
				"Enter the description of the created MODULE-COMPLIANCE."
			MODULE -- this module
				MANDATORY-GROUPS { currentObjectGroup, currentNotificationGroup }
			::= { optixSdhTrapsCompliances 1 }
		
	
	END

--
-- OPTIX-SDH-TRAPS-MIB.mib
--
