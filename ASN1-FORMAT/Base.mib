-- Ericsson Television Limited Standard MIB disclaimer
-- ###################################################
-- SNMP MIBs for Ericsson Television Limited products are developed 
-- primarily for use by Ericsson Television Limited control solutions.
-- Where MIBs are provided to a third party or other non-Ericsson 
-- Television Limited person, for the purposes of their development 
-- of a non-Ericsson Television Limited control or monitoring solution, 
-- they are provided free of charge, and without obligation on the
-- part of Ericsson Television Limited to offer priority support, or
-- changes to suit the third party.
--
-- $Date: 2010-02-17 17:09:20 +0000 (Wed, 17 Feb 2010) $
-- $Revision: 192 $

ETV-Base-MIB DEFINITIONS ::= BEGIN

IMPORTS
   enterprises
      FROM SNMPv2-SMI;

-- Base MIB module.

mibEricssonTelevision OBJECT IDENTIFIER ::= { enterprises 1773 }
elementManagementMIB OBJECT IDENTIFIER ::= { mibEricssonTelevision 1 }

general     OBJECT IDENTIFIER ::= { elementManagementMIB 1 }
content     OBJECT IDENTIFIER ::= { elementManagementMIB 2 }
modules     OBJECT IDENTIFIER ::= { elementManagementMIB 3 }

END
