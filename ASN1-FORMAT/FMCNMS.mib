FNCNMS DEFINITIONS ::= BEGIN

IMPORTS

        MODULE-IDENTITY,
        NOTIFICATION-TYPE,
        OBJECT-TYPE,
        enterprises                      FROM SNMPv2-SMI
        TEXTUAL-CONVENTION,
        DisplayString,
        DateAndTime                      FROM SNMPv2-TC
        system                           FROM SNMPv2-MIB
        netsmart                     FROM FNC-COMMON-SMI
        MODULE-COMPLIANCE,                
        NOTIFICATION-GROUP,               
        OBJECT-GROUP                     FROM SNMPv2-CONF;



        
netsmart1500  MODULE-IDENTITY
        LAST-UPDATED "200308021600Z"
        ORGANIZATION "Fujitsu Network Communications Inc."
        CONTACT-INFO "Fujitsu Network Communications

                      Tel: I-800-USE-FTAC i.e (800) 873 3822"
        DESCRIPTION
                   " This MIB represents the interface definition
        between a third party SNMP Manager and FNC's NETSMART
        Management System. The functions provided in this MIB are:

        - Network Element (NE) Target IDentifier (TID) Discovery
        - Dynamic Alarm reporting
        - Alarm Discovery and Reconciliation
        "
        ::= {netsmart  1500}  --NETSMART 1500



nmsNEMgmtMIB OBJECT IDENTIFIER ::= { netsmart1500 1 }

nmsNEMgmt  OBJECT IDENTIFIER ::= {nmsNEMgmtMIB 1}
nmsNEAlarm OBJECT IDENTIFIER ::= {nmsNEMgmtMIB 2}                    

nmsNotificationTrapBase OBJECT IDENTIFIER ::= { nmsNEAlarm 0 }

NMSSeverity  ::=        TEXTUAL-CONVENTION
        STATUS          current
        DESCRIPTION 
                        " Severity represents the severity of the Notification.
        It is assigned by the NE. Cleared indicates that this notification 
        clears a  previously sent trap with a severity of critical,major,minor
        or info.
        "
        SYNTAX INTEGER {
                cleared(1),
                info(2),
                minor(3),
                major(4),
                critical(5)
        }
        


NMSCondDirection ::=    TEXTUAL-CONVENTION
        STATUS          current
        DESCRIPTION 
                        "Whether the fault is on the transmit side or on the 
        receive side.
        "
        SYNTAX INTEGER {
                na(1),
                transmit(2),
                receive(3)
        }       



NMSCondLocation ::=     TEXTUAL-CONVENTION
        STATUS          current
        DESCRIPTION 
                        " Location indicates whether the failure occurred on 
        the nearEnd of this NE or on the farEnd.
        "
        SYNTAX INTEGER  {
                na(1),
                nearEnd(2),
                farEnd(3)
        }




NMSServiceEffect ::=    TEXTUAL-CONVENTION
        STATUS          current
        DESCRIPTION 
                        "Service Affecting indicates whether the alarm affects 
        traffic or not.
        "
        SYNTAX INTEGER {        
                        na(1),
                        serviceAffecting(2),
                        nonServiceAffecting(3)
       }


NMSTrapSeqNumber ::=    TEXTUAL-CONVENTION
        STATUS          current

        DESCRIPTION 
                        " A value in the range 1-99999 is reported. The value 
        0 is never reported but can only be obtained through a GET.A value of 
        0 indicates that agent has not forwarded any notifications  since it
	booted up.  When the value of this field reaches 99999, the number
	resets and the subsequent notification is sent with a number 1. This 
        value is  not  unique per NE.It is a global number used across all NEs.
        "
        SYNTAX INTEGER(0..99999)


NMSMgdNE ::=            DisplayString (SIZE (1..20))
--        STATUS          current
--        DESCRIPTION 
--                        " Represents the TID (Target Identifier)  of the NE.
--        "
--        SYNTAX          OCTET STRING (SIZE (1..20))

NMSNEConnState ::=      TEXTUAL-CONVENTION
        STATUS          current
	DESCRIPTION 
                        " Describes the state of connection between
        an NE and agent.Connected indicates that the agent is connected to the
        NE. NotConnected indicates that there is no communication between NE 
        and agent. 
        "

        SYNTAX          INTEGER {
           	                connected(1),
                                notConnected(2)
                        }        


nmsNETable              OBJECT-TYPE
        SYNTAX          SEQUENCE OF NMSNEEntry
        MAX-ACCESS      not-accessible
        STATUS          current
        DESCRIPTION
                        " This Table contains a row for each  managed NE in
	NETSMART. The row contains:
	- the TID (20 characters max) of each NE.
	- the NE Type ( A string representing the FNC Product Name) .
	- the NE Connection State. @see NMSNEConnState
       " 
        ::= {nmsNEMgmt 1}

nmsNEEntry              OBJECT-TYPE
        SYNTAX          NMSNEEntry
        MAX-ACCESS      not-accessible
        STATUS          current
        DESCRIPTION 
                        " Provides information about a managed NE in NETSMART.
        "
        INDEX    { IMPLIED neTID }
        ::= { nmsNETable 1 }

NMSNEEntry ::= SEQUENCE {
        neTID NMSMgdNE,
        neType OCTET STRING,
        neConnState NMSNEConnState
}

neTID                   OBJECT-TYPE
        SYNTAX          NMSMgdNE 
        MAX-ACCESS      read-only
        STATUS          current
        DESCRIPTION 
                        "TID of the NE. @see NMSMgdNE.
        "
        ::= { nmsNEEntry 1}

neType                  OBJECT-TYPE
       SYNTAX           OCTET STRING
       MAX-ACCESS       read-only
       STATUS           current
       DESCRIPTION  
                        " Describes the type of Fujitsu NETWORK Element
       Current Types are
       FLM6,
       FACTR,
       FLM150,
       FLM600,
       FLM2400,
       FLX 600A,
       FLX 2500A,
       FLASH 192,
       FLASH 10G, 
       FLASHWAVE 4010,
       FLASHWAVE 4020,
       FLASHWAVE 4100,
       FLASHWAVE 4300,
       FLASHWAVE 4500,
       FLASHWAVE 4560, 
       FLASHWAVE 7200,
       FLASHWAVE 7300,
       FLASHWAVE 7500,
       FLASHWAVE 7700, 
       Fujitsu NE,
       Generic NE,
       Unknown.
       
       -Unknown NEType represents NEs whose type is not determined yet.
       -Fujitsu NE NEType represents the NEs which are minimally (only fault
        management) supported by the agent.
       -Generic NE NEType represents non Fujitsu NEs whose fault management
        functionality is supported by the agent.   
       "
       ::= { nmsNEEntry 2}

neConnState             OBJECT-TYPE
        SYNTAX          NMSNEConnState
        MAX-ACCESS      read-only
        STATUS          current
        DESCRIPTION
                        " Describes connection state between agent and NE.
        @see NMSNEConnState.
        A nmsNEStateChangeEvent NOTIFICATION generated whenever there is a 
        change in neConnState.
        Also see neOperation and nmsNEOperationEvent for the default state when
        an NE is added. 
        "
        ::= {nmsNEEntry 3}

        
nmsNEAlarmTable         OBJECT-TYPE
        SYNTAX          SEQUENCE OF NMSNEAlarmListEntry
        MAX-ACCESS      not-accessible
        STATUS          current
        DESCRIPTION 
                        " This table contains a NE TID and a List of 
        nmsNEAlarmList for this TID.
        "
        ::= {nmsNEAlarm 1}


nmsNEAlarmListEntry     OBJECT-TYPE
        SYNTAX          NMSNEAlarmListEntry
        MAX-ACCESS      not-accessible
        STATUS          current
        DESCRIPTION 
                        " A row in the table indicating the specific Alarm for
	the given TID.
        "
        INDEX { alarmTID,alarmIndex }
        ::= { nmsNEAlarmTable 1}        

NMSNEAlarmListEntry ::=  SEQUENCE {
        alarmTID                NMSMgdNE,
        alarmIndex              INTEGER,
        alarmEntityId           OCTET STRING,
        alarmEntityType         OCTET STRING,        
        alarmSeverity           NMSSeverity,
        alarmCondType           OCTET STRING,
        alarmServEffect         NMSServiceEffect,
        alarmLocation           NMSCondLocation,
        alarmDirection          NMSCondDirection,
        alarmDescription        OCTET STRING,
        neAlarmTimeStamp        DateAndTime,    
        nmsAlarmTimeStamp       DateAndTime 
} 

alarmTID                OBJECT-TYPE
        SYNTAX          NMSMgdNE
        MAX-ACCESS      read-only
        STATUS          current
        DESCRIPTION 
                        " NE TID against which this Alarm is being raised.
        @see NMSMgdNE.
        "
        ::= {nmsNEAlarmListEntry 1}

alarmIndex              OBJECT-TYPE
        SYNTAX          INTEGER(0..99999)
        MAX-ACCESS      read-only
        STATUS          current

        DESCRIPTION  
                        "The instance of the alarm for this NE.
        This variable is used to identify a unique row for each alarm.
	In the nmsNEAlarmTable a sequence of alarms  will look like:
                
                TID      alarmIndex             Other Alarm Data
                ========================================================
                TID1      1                  	1-1 oc3 CR LOS SA RCV  Loss Of Signal neTimeStamp1 nmsTimeStamp2
                TID1      2                  	2-1 oc3 CR LOS SA RCV  Loss Of Signal neTimeStamp1 nmsTimeStamp2
                TID1      3                  	3-1 oc3 CR LOS SA RCV  Loss Of Signal neTimeStamp1 nmsTimeStamp2
                TID2      1                   	1-1 oc3 CR LOS SA RCV  Loss Of Signal neTimeStamp1 nmsTimeStamp2
                TID2      2                    	1-1 oc3 CR LOS SA RCV  Loss Of Signal neTimeStamp1 nmsTimeStamp2

                TID3      1                  	2-1 oc3 CR LOS SA RCV  Loss Of Signal neTimeStamp1 nmsTimeStamp2
                TID3      2                   	3-1 oc3 CR LOS SA RCV  Loss Of Signal neTimeStamp1 nmsTimeStamp2
                TID3      3                   	4-1 oc3 CR LOS SA RCV  Loss Of Signal neTimeStamp1 nmsTimeStamp2
                TID3      4                   	5-1 oc3 CR LOS SA RCV  Loss Of Signal neTimeStamp1 nmsTimeStamp2
                TID3      5                   	6-1 oc3 CR LOS SA RCV  Loss Of Signal neTimeStamp1 nmsTimeStamp2
                TID4      1                   	1-1 oc3 CR LOS SA RCV  Loss Of Signal neTimeStamp1 nmsTimeStamp2
                

        i.e. For each TID alarmIndex starts with 1 and is incremented by 1.
        This is to help retrieve alarms on an NE basis. 
       "
       ::= {nmsNEAlarmListEntry 2}                         

alarmEntityId           OBJECT-TYPE
        SYNTAX          OCTET STRING
        MAX-ACCESS      read-only
        STATUS          current
        DESCRIPTION 
                        "Describes the AID of the entity against  which this 
        notification is being sent.
        "
        ::= {nmsNEAlarmListEntry 3}

alarmEntityType         OBJECT-TYPE
        SYNTAX          OCTET STRING
        MAX-ACCESS      read-only
        STATUS          current
        DESCRIPTION 
                        " Describes the  kind  the entity against which this 
        notification is being sent . The combination of (alarmEntity,
        alarmEntityType) represents a addressable entity on the NE.
        Examples of kind of entities are EQPT,OC3,STS1,COM,ENV etc.
        "
        ::= {nmsNEAlarmListEntry 4}

alarmSeverity           OBJECT-TYPE
        SYNTAX          NMSSeverity
        MAX-ACCESS      read-only
        STATUS          current
        DESCRIPTION  
                        "Describes the severity of the notification being sent.
        @see NMSSeverity
        "
        ::= { nmsNEAlarmListEntry 5}

alarmCondType           OBJECT-TYPE
        SYNTAX          OCTET STRING
        MAX-ACCESS      read-only
        STATUS          current
        DESCRIPTION  
                        " Describes the condition type i.e RMVD or LOS etc. 
        "
        ::= {nmsNEAlarmListEntry 6}

alarmServEffect         OBJECT-TYPE 
        SYNTAX          NMSServiceEffect
        MAX-ACCESS      read-only
        STATUS          current
        DESCRIPTION     
                        " Describes whether the notification is serviceAffecting 
        or not.
        @see NMSServiceEffect.
        "
        ::= {nmsNEAlarmListEntry 7}

alarmLocation           OBJECT-TYPE
        SYNTAX          NMSCondLocation
        MAX-ACCESS      read-only
        STATUS          current
        DESCRIPTION 
                        " Describes if the location is applicable and if
        applicable the appropriate location.
        @see NMSCondLocation.
        "
        ::= { nmsNEAlarmListEntry 8}

alarmDirection          OBJECT-TYPE
        SYNTAX          NMSCondDirection
        MAX-ACCESS      read-only
        STATUS          current
        DESCRIPTION  
                        " Describes if the direction is a applicable and if 
        applicable the appropriate direction.
        @see NMSCondLocation.
        "
        ::= {nmsNEAlarmListEntry 9}


alarmDescription        OBJECT-TYPE
        SYNTAX          OCTET STRING
        MAX-ACCESS      read-only
        STATUS          current
        DESCRIPTION 
                        " Gives a textual description of the condition.
        "
        ::= {nmsNEAlarmListEntry 10}

neAlarmTimeStamp        OBJECT-TYPE
        SYNTAX          DateAndTime
        MAX-ACCESS      read-only
        STATUS          current
        DESCRIPTION  
                        "Time stamp at which the NE generated the fault. The 
        correctness of the value depends whether this fault is reported to the
        agent or agent retrieved this information from NE. For faults reported
        from the NE this value is correct where as for faults retrieved the 
        timestamp indicates the time on NE at which this fault was retrieved.
        "
        ::= {nmsNEAlarmListEntry 11}
      
nmsAlarmTimeStamp       OBJECT-TYPE
        SYNTAX          DateAndTime
        MAX-ACCESS      read-only
        STATUS          current
        DESCRIPTION 
                        " Time at which the NMS received the fault.
        "
        ::= {nmsNEAlarmListEntry 12}


nmsLastMsgNumber        OBJECT-TYPE
        SYNTAX          NMSTrapSeqNumber
        MAX-ACCESS      read-only
        STATUS          current
        DESCRIPTION
                        " This variable describes the value of the last
        NMSTrapIndex reported by the agent in the notifications.
        @see NMSTrapSeqNumber.
        "
        ::= {nmsNEAlarm 2}

nmsTrapHistoryTable     OBJECT-TYPE
        SYNTAX          SEQUENCE OF NMSTrapHistoryTableEntry
        MAX-ACCESS      not-accessible
        STATUS          current
        DESCRIPTION     
                        " Thus table contains a sequence of trap seq number and
        the corresponding neTID.A Management system upon detecting that it has 
        not received a particular sequence number, can  determine the NE
        against which the sequence number was used and do a alarm 
        resynchornization for that NE.
        "
        ::= {nmsNEAlarm 3}
        
nmsTrapHistoryTableEntry  OBJECT-TYPE
        SYNTAX            NMSTrapHistoryTableEntry
        MAX-ACCESS        not-accessible
        STATUS            current
        DESCRIPTION  
                          " A row indicating the trap sequence number and 
        NE TID  which caused this  event to be sent.
        "
        INDEX           {nmsTrapHistoryIndex }
        ::=  { nmsTrapHistoryTable 1}


NMSTrapHistoryTableEntry ::= SEQUENCE {
        nmsTrapHistoryIndex     NMSTrapSeqNumber,
        nmsTrapHistoryTID       NMSMgdNE
}

nmsTrapHistoryIndex     OBJECT-TYPE
        SYNTAX          NMSTrapSeqNumber
        MAX-ACCESS      read-only
        STATUS          current
        DESCRIPTION     
                        " A Sequence Number that was previously sent.
        @see NMSTrapSeqNumber.
        "
        ::=  {nmsTrapHistoryTableEntry 1}

nmsTrapHistoryTID        OBJECT-TYPE
        SYNTAX           NMSMgdNE
        MAX-ACCESS       read-only
        STATUS           current
        DESCRIPTION      
                        " The tid for which  the sequence entry was sent.
        @see NMSMGgNE.
        "
        ::=  {nmsTrapHistoryTableEntry 2}



nmsNotificationBase OBJECT IDENTIFIER ::= { nmsNEAlarm 4 }

notifTID                OBJECT-TYPE
        SYNTAX          NMSMgdNE
        MAX-ACCESS      read-only
        STATUS          current
        DESCRIPTION 
                        " NE TID against which this notification is being sent.
        @see NMSMgdNE.
        "
        ::= { nmsNotificationBase 1}

neEntityID              OBJECT-TYPE
        SYNTAX          OCTET STRING
        MAX-ACCESS      read-only
        STATUS          current
        DESCRIPTION 
                        " Describes the AID of the entity against  which this 
        notification is being sent.
        "
        ::= { nmsNotificationBase 2}

neEntityType            OBJECT-TYPE
        SYNTAX          OCTET STRING
        MAX-ACCESS      read-only
        STATUS          current
        DESCRIPTION 
                    " Describes the  type the entity against  which this 
        notification is being sent . The combination (neEntityID,neEntityType)
        represents a addressable entity on the network element.
        Examples of neEntityType would be EQPT,OC3,COM,STS1,ENV etc.
        "
        ::= { nmsNotificationBase 3}

neSeverity              OBJECT-TYPE
        SYNTAX          NMSSeverity
        MAX-ACCESS      read-only
        STATUS          current
        DESCRIPTION     
                        " Describes the severity of the notification being sent.
        @see NMSSeverity.
        "
        ::= { nmsNotificationBase 4}

neCondType              OBJECT-TYPE
        SYNTAX          OCTET STRING
        MAX-ACCESS      read-only
        STATUS          current
        DESCRIPTION  
                        " Describes the condition type i.e RMVD or LOS etc.
        "
        ::= { nmsNotificationBase 5}

neServEffect            OBJECT-TYPE
        SYNTAX          NMSServiceEffect
        MAX-ACCESS      read-only
        STATUS          current
        DESCRIPTION   
                        " Describes whether the notification is ServiceAffecting 
        or not.
        @see NMSServiceEffect.
        "
        ::= { nmsNotificationBase 6}


neLocation              OBJECT-TYPE
        SYNTAX          NMSCondLocation
        MAX-ACCESS      read-only
        STATUS          current
        DESCRIPTION 
                        " Describes if the  location is applicable for this
        notification, if it is applicable describes the location.
        @see NMSCondLocation.
        "
        ::= { nmsNotificationBase 7}

neDirection             OBJECT-TYPE
        SYNTAX          NMSCondDirection
        MAX-ACCESS      read-only
        STATUS          current
        DESCRIPTION 
                        "Describes if the direction is a applicable and if 
        it is applicable the direction.
        @see NMSCondDirection.
        "
        ::= { nmsNotificationBase 8}


neCondDescription       OBJECT-TYPE
        SYNTAX          OCTET STRING
        MAX-ACCESS      read-only
        STATUS          current
        DESCRIPTION 
                        " Textual Description of the notification.
        "
        ::= { nmsNotificationBase 9}

nmsNotifTimeStamp       OBJECT-TYPE
        SYNTAX          DateAndTime
        MAX-ACCESS      read-only
        STATUS          current
        DESCRIPTION 
                        " Time when NMS received this event.
        "
        ::= { nmsNotificationBase 10}

neNotifTimeStamp        OBJECT-TYPE
        SYNTAX          DateAndTime
        MAX-ACCESS      read-only
        STATUS          current
        DESCRIPTION 
                        " Time when NE raised  this event.
        "
        ::= { nmsNotificationBase 11}
nmsTrapSeqNumber        OBJECT-TYPE
        SYNTAX          NMSTrapSeqNumber
        MAX-ACCESS      read-only
        STATUS          current
        DESCRIPTION 
                        " @See NMSTrapSeqNumber. 
        "
        ::= { nmsNotificationBase 12}


nmsNEConnState          OBJECT-TYPE
        SYNTAX          NMSNEConnState
        MAX-ACCESS      read-only
        STATUS          current
	DESCRIPTION 
                        " Describes the state of connection between
        an NE and NMS.
        "
        ::= { nmsNotificationBase 13 }

neOperation OBJECT-TYPE
        SYNTAX          INTEGER {
                                created(1),
                                deleted(2)
        }
        MAX-ACCESS      read-only
        STATUS          current
        DESCRIPTION 
                        " Indicates if a new NE is added to NETSMART
        or if it is removed. Addition always implies a nmsNEConnState with
        value notConnected and NEType of Unknown.
        "
        ::= { nmsNotificationBase 14 }

nmsNEEvent              NOTIFICATION-TYPE
        OBJECTS  {      

                notifTID,
                neEntityID,
                neEntityType,
                neSeverity,
                neCondType,
                neServEffect,
                neLocation,
                neDirection,
                neCondDescription,
                nmsNotifTimeStamp,
                neNotifTimeStamp,
                nmsTrapSeqNumber
        } 

        STATUS          current

        DESCRIPTION 
                        " The agent generates this notification when a rept 
        alarm or rept  evt is generated.
        "
        ::=  {nmsNotificationTrapBase 1}



nmsNEStateChangeEvent   NOTIFICATION-TYPE
        OBJECTS {
                notifTID,
                nmsNEConnState,
                nmsTrapSeqNumber
        }
        STATUS current
        DESCRIPTION
                        " The agent generates this notification when a NMS  
        changes its connection state to the NE.
        @see NMSConnState.
        "
      ::= { nmsNotificationTrapBase 2 }


nmsNEOperationEvent     NOTIFICATION-TYPE
        OBJECTS {
                notifTID,
                neOperation,
                nmsTrapSeqNumber
        }

        STATUS          current

        DESCRIPTION    
                        " The agent generates this notification when a NE is 
        created or deleted.
        @see neOperation.
        "
      ::= { nmsNotificationTrapBase 3 }


-- Module Conformance statement

fncNMSMIBConformance OBJECT IDENTIFIER ::= { nmsNEMgmtMIB 3 }
fncNMSMIBCompliances OBJECT IDENTIFIER ::= { fncNMSMIBConformance  1 }
fncNMSMIBGroups OBJECT IDENTIFIER ::= { fncNMSMIBConformance 2 }
 
fncNMSMIBCompliance MODULE-COMPLIANCE
        STATUS current
        DESCRIPTION 
                " Module Compliancy "
        MODULE SNMPv2-MIB
           MANDATORY-GROUPS { system }

        MODULE 
         MANDATORY-GROUPS {
                        nmsNEMgmtGroup,
                        nmsNEAlarmGroup,
                        nmsNETrapGroup,
                        nmsNETrapObjects
        }
   ::= {fncNMSMIBCompliances 1}


nmsNEMgmtGroup OBJECT-GROUP 
        OBJECTS {
                neTID,
                neType,
                neConnState
                }
        STATUS current
        DESCRIPTION 
                " This Group defines objects which are common to all NE Table related retrievals "
        ::= { fncNMSMIBGroups 1 }

               
nmsNEAlarmGroup OBJECT-GROUP
        OBJECTS {
                alarmTID,
                alarmIndex,
                alarmEntityId,
                alarmEntityType,
                alarmSeverity,
                alarmCondType,
                alarmServEffect,
                alarmLocation,
                alarmDirection,
                alarmDescription,
                neAlarmTimeStamp,
                nmsAlarmTimeStamp,
                nmsLastMsgNumber,
                nmsTrapHistoryIndex,
                nmsTrapHistoryTID
        }
        STATUS current
        DESCRIPTION 
                " This Group defines objects which are common to all Alarm Table related retrievals "
        ::= { fncNMSMIBGroups 2 }
                

nmsNETrapGroup NOTIFICATION-GROUP
        NOTIFICATIONS {
                

                nmsNEEvent,
                nmsNEStateChangeEvent,
                nmsNEOperationEvent                
        }
        STATUS current
        DESCRIPTION 
                " This Group defines objects which are used part of notifications "
        ::= { fncNMSMIBGroups 3 }
                        

nmsNETrapObjects OBJECT-GROUP
        OBJECTS { 
                notifTID,
                neEntityID,
                neEntityType,
                neSeverity,
                neCondType,
                neServEffect,
                neLocation,
                neDirection,
                neCondDescription,
                nmsNotifTimeStamp,
                neNotifTimeStamp,
                nmsTrapSeqNumber,
                nmsNEConnState,
                neOperation
        }
        STATUS current
        DESCRIPTION
                " This Group defines objects reported as part of notifications. "
        ::= { fncNMSMIBGroups 4 }

END
