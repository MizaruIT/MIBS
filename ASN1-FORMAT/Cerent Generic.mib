-- **************************************************************
-- File name: cerentGeneric.mib
-- Module name: Cerent-GENERIC-MIB module
--
-- This module contains the generic objects and generic events 
-- for the Cisco ONS Network Element ONS 15327 .

-- Copyright (c) 1998-1999 by Cerent Corporation, Inc.
-- Copyright (c) 1999-2000, 2001 by Cisco Systems, Inc.
-- All rights reserved.
--
-- **************************************************************

CERENT-GENERIC-MIB DEFINITIONS ::= BEGIN

IMPORTS
    MODULE-IDENTITY,
    OBJECT-TYPE,
    OBJECT-IDENTITY,
    NOTIFICATION-TYPE,
    Integer32,
    Unsigned32,
    Counter32
                      FROM SNMPv2-SMI
    TEXTUAL-CONVENTION,
    DisplayString, 
    TruthValue,
    TimeStamp
                      FROM SNMPv2-TC
    MODULE-COMPLIANCE, 
    OBJECT-GROUP, 
    NOTIFICATION-GROUP 
                      FROM SNMPv2-CONF
    cerentGeneric,
    cerentRequirements,
    cerentModules
                      FROM CERENT-GLOBAL-REGISTRY
    CerentNotificationClass
                      FROM CERENT-TC;

cerentGenericMibModule MODULE-IDENTITY
    LAST-UPDATED "011005000000Z" -- 2001/Oct/05
    ORGANIZATION "Cisco Systems, Inc."
    CONTACT-INFO
        "         support@Cisco.com

         Postal:  Cisco Systems
                  1450 N. McDowell Blvd.
                  Petaluma, CA  94954
                  USA

            Tel:  +1-877-323-7368"
    DESCRIPTION
        "This module provides the definitions for 
         generic objects and notifications of 
         Cisco ONS network device, ONS 15327" 

    REVISION "011005000000Z" -- 2001/Oct/05
    DESCRIPTION
        "This file can be used with R3.0.3 (taka) release."

    REVISION "010620000000Z" -- 2001/Jun/20
    DESCRIPTION
        "This file can be used with R3.0.1 (Shekel) release.

         o) Has no changes from the previous version"

    REVISION "010202000000Z" -- 2001/Jan/02
    DESCRIPTION
        "o) This file can be used with R3.0 (DaGama) release.

         o) The following new traps have been added.

            traceIdentifierMismatchSTSPath
            nodePowerFailureAtConnectorA
            nodePowerFailureAtConnectorB
            exerciseRing 
            exerciseSpan 
            squelchingPath
            extraTrafficPreempted
            farEndLockoutOfWorkingRing 
            farEndLockoutOfWorkingSpan
            farEndLockoutOfProtectionRing 
            farEndLockoutOfProtectionAllSpans 
            farEndWorkingFacilityForcedToSwitchToProtectionUnitRing
            farEndWorkingFacilityForcedToSwitchToProtectionUnitSpan
            farEndManualSwitchOfWorkingFacilityToProtectionUnitRing
            farEndManualSwitchOfWorkingFacilityToProtectionUnitSpan
            farEndExerciseRing
            farEndExerciseSpan
            farEndBERThresholdPassedForSignalFailureRing
            farEndBERThresholdPassedForSignalFailureSpan
            farEndBERThresholdPassedForSignalDegradeRing
            farEndBERThresholdPassedForSignalDegradeSpan
            channelFarEndProtectionLineSignalDegradeAPS
            ringSwitchIsActiveOnTheEastSide
            ringSwitchIsActiveOnTheWestSide
            spanSwitchIsActiveOnTheEastSide
            spanSwitchIsActiveOnTheWestSide
            uniDirectionalFullPassThroughIsActive
            biDirectionalFullPassThroughIsActive
            kBytesPassThroughIsActive
            ringIsSegmented
            ringTopologyIsUnderConstruction
            lockoutOfProtectionAllSpansSpans
            farEndOfFiberIsProvisionedWithDifferentRingID
            bothEndsOfFiberProvisionedAsEastOrBothAsWest
            invalidLoginSeeAuditTrail
            farEndOfFiberIsProvisionedWithDifferentRingID
            bothEndsOfFiberProvisionedAsEastOrBothAsWest
            invalidLoginSeeAuditTrail
            autonomousMessagesInhibited
            trafficStormLANTemporarilyDisabled
            tl1ReptDbchgMessagesInhibited
            userIDHasExpired
            partialFanFailure
            forceSwitchRequestOnRing
            forceSwitchRequestOnSpan
            lockoutSwitchRequestOnRing
            lockoutSwitchRequestOnSpan
            manualSwitchRequestOnRing
            manualSwitchRequestOnSpan
            peerToPeerSlotCommunicationFailure
            peerToPeerSlotCommunicationFailure
            TCCAToShelfSlotCommunicationFailure
            TCCBToShelfSlotCommunicationFailure
            interconnectionEquipmentFailureWorkingPayloadBus
            interconnectionEquipmentFailureProtectPayloadBus,
            inhibitSwitchToProtectRequestInEffectOnEquipment,
            inhibitSwitchToWorkingRequestInEffectOnEquipment,
            passedBERThresholdForSignalDegradeLine,
            passedBERThresholdForSignalDegradePath,
            passedBERThresholdForSignalFailLine,
            passedBERThresholdForSignalFailPath "

    REVISION "000825000000Z" -- 2000/Aug/25
    DESCRIPTION
        "o) This file can be used with R2.3 (LnC/DaVinci) release.

         o) A new trap, rmonThresholdCrossingAlarm has been added."

    REVISION "0006210000Z" -- 2000/June/21
    DESCRIPTION
        "The inital version of the module"

    ::= { cerentModules 40 }

cerentConformance OBJECT-IDENTITY
      STATUS      current
      DESCRIPTION
            "This node is created for compliance. Has 
             objects as required by the RFCs"
      ::= { cerentRequirements 10 }

--  ********************************************************

cerentGenericGroups OBJECT-IDENTITY
      STATUS      current
      DESCRIPTION
            "All the objects and events are
             grouped under this for conformance"
      ::= { cerentConformance 10 }

cerentCompliance OBJECT-IDENTITY
      STATUS      current
      DESCRIPTION
            "The compliance statements
             for Cisco ONS 15327."
      ::= { cerentConformance 20 }

-- **************************************************************
-- Cisco ONS generic textual conventions
-- **************************************************************

CerentGenericAlarmType ::= TEXTUAL-CONVENTION
--   DISPLAY-HINT "d"
   STATUS current
   DESCRIPTION
       "This TC is used by the NMS to map the alarm type
        received by the trap and and display the string
        shown in LHS."
   SYNTAX INTEGER {
       alarmUnknown                                      (  1 ), 
       alarmCutoffIsInManualMode                         ( 10 ), 
       failureDetectedexternalToTheNE                    ( 20 ),
       externalError                                     ( 30 ), 
       excessiveSwitching                                ( 40 ), 
       terminationFailureSDCC                            ( 50 ), 
       incomingFailureCondition                          ( 60 ), 
       alarmIndicationSignal                             ( 70 ), 
       alarmIndicationSignalLine                         ( 80 ), 
       alarmIndicationSignalPath                         ( 90 ), 
       alarmIndicationSignalVT                           ( 100 ),
       channelFailureAPS                                 ( 110 ), 
       channelByteFailureAPS                             ( 120 ), 
       channelProtectionSwitchingChannelMatchFailureAPS  ( 130 ), 
       channelAutomaticProtectionSwitchModeMismatchAPS   ( 140 ), 
       channelFarEndProtectionLineFailureAPS             ( 150 ), 
       channelBLSRInconsistentAPSCode                    ( 160 ), 
       channelBLSRImproperAPSCodeAPS                     ( 170 ), 
       channelBLSRNodeIdMismatchAPS                      ( 180 ), 
       channelBLSRDefaultKAPS                            ( 190 ), 
       channelBLSRConnectionLossAPS                      ( 200 ), 

       bipolarViolation                                  ( 210 ), 
       carrierLossOnTheLAN                               ( 220 ), 
       concatenationErrorSTS                             ( 230 ), 
       excessCollisionsOnTheLAN                          ( 240 ), 
       facilityCriticalAlarmCausedByDS3FacilityFailure   ( 250 ), 
       farEndAIS                                         ( 260 ), 
       farEndMultipleDS1LOSDetectedOnDS3                 ( 270 ), 
       farEndDS1EqptFailNonServiceAffecting              ( 280 ), 
       farEndDS1EqptFailServiceAffecting                 ( 290 ), 
       farEndSingleDS1LOS                                ( 300 ), 
       farEndDS3EqptFailNonServiceAffecting              ( 310 ), 
       farEndDS3EqptFailServiceAffecting                 ( 320 ), 
       farEndCmnEqptFailNonServiceAffecting              ( 330 ), 
       farEndIDLE                                        ( 340 ), 
       farEndLOS                                         ( 350 ), 
       farEndLOF                                         ( 360 ), 
       farEndBlockError                                  ( 370 ), 
       idleConditionDS3                                  ( 380 ), 
       lossOfFrame                                       ( 390 ), 
       lossOfPointer                                     ( 400 ), 

       lossOfPointerPath                                 ( 410 ), 
       lossOfPointerVT                                   ( 420 ), 
       lossOfSignal                                      ( 430 ), 
       outOfFrame                                        ( 440 ), 
       pathSelectorInabilityToSwitchToAValidSignal       ( 450 ), 
       remoteAlarmIndication                             ( 460 ), 
       remoteFailureIndication                           ( 470 ), 
       remoteFailureIndicationLine                       ( 480 ), 
       remoteFailureIndicationPath                       ( 490 ), 
       remoteFailureIndicationVT                         ( 500 ), 

       facilityHasPassedBERThresholdForSignalDegrade     ( 510 ), 
       severelyErroredFrame                              ( 520 ), 
       facilityHasPassedBERThresholdForSignalFailure     ( 530 ), 
       signalLabelMismatchFailuresSONET                  ( 540 ), 
       signalLabelMismatchFailurePayloadDefectIndication ( 550 ), 

       signalLabelMismatchFailurePayloadDefectIndicationPath  ( 560 ), 
       signalLabelMismatchFailurePayloadLabelMismatchPath     ( 570 ), 
       signalLabelMismatchFailurePayloadLabelMismatchVT       ( 580 ), 
       signalLabelMismatchFailureUnequippedPath               ( 590 ), 
       signalLabelMismatchFailureUnequippedVT                 ( 600 ), 
       lossOfTimingOnSynchronizationLink                      ( 610 ), 
       lossOfTimingOnAllSpecifiedSynchronizationLinks         ( 620 ), 
       lossOfTimingOnPrimarySynchronizationLink               ( 630 ), 
       lossOfTimingOnSecondarySynchronizationLink             ( 640 ), 
       lossOfTimingOnThirdSynchronizationLink                 ( 650 ), 
       lossOfTimingOnFourthSynchronizationLink                ( 660 ), 
       lossOfTimingOnFifthSynchronizationLink                 ( 670 ), 
       lossOfTimingOnSixthSynchronizationLink                 ( 680 ), 

       failedToReceiveSynchronizationStatusMessage             ( 690 ),
       synchronizationStatusMessagesAreDisabledOnThisInterface ( 700 ),
       primaryReferenceSourceStratum1Traceable                 ( 710 ),
       synchronizedTraceabilityUnknown                         ( 720 ),
       stratum2Traceable                                       ( 730 ),
       transiTNodeClockTraceable                               ( 740 ),

       stratum3ETraceable                    ( 750 ),
       stratum3Traceable                     ( 760 ),
       minimumClockTraceableSONET            ( 770 ),
       stratum4Traceable                     ( 780 ),
       doNotUseForSynchronization            ( 790 ),
       reservedForNetworkSynchronizationUse  ( 800 ),

       outgoingFailureCondition          ( 810 ), 
       remoteDefectIndicationLine        ( 820 ), 
       remoteDefectIndicationPath        ( 830 ), 
       freeRunningSynchronizationMode    ( 840 ), 
       holdoverSynchronizationMode       ( 850 ), 
       fastStartSynchronizationMode      ( 860 ), 
       internalHardwareFaultOrFailure    ( 870 ), 
       errorInternalToTheNEDetected      ( 880 ), 
       internalMessageError              ( 890 ), 
       mismatchOfEquipmentAndAttributes  ( 900 ), 
       watchdogTimerTimeout              ( 910 ), 
       softwareFaultOrFailure            ( 920 ), 
       softwareFaultDataIntegrityFault   ( 930 ), 
       programFailure                    ( 940 ), 

       controlEquipmentFailure                                 ( 950 ), 
       controlEquipmentPrimaryNonVolatileBackupMemoryFailure   ( 960 ), 
       controlEquipmentSecondaryNonVolatileBackupMemoryFailure ( 970 ), 
       controlEquipmentControlBusFailure                       ( 980 ), 
       controlEquipmentControlBus1Failure                      ( 990 ), 
       controlEquipmentControlBus2Failure                      ( 1000 ),

       communicationFailureTCCAToShelfSLOT1      ( 1010 ),
       communicationFailureTCCAToShelfSLOT2      ( 1020 ),
       communicationFailureTCCAToShelfSLOT3      ( 1030 ),
       communicationFailureTCCAToShelfSLOT4      ( 1040 ),
       communicationFailureTCCAToShelfSLOT5      ( 1050 ),
       communicationFailureTCCAToShelfSLOT6      ( 1060 ),
       communicationFailureTCCAToShelfSLOT7      ( 1070 ),
       communicationFailureTCCAToShelfSLOT8      ( 1080 ),
       communicationFailureTCCAToShelfSLOT9      ( 1090 ),
       communicationFailureTCCAToShelfSLOT10     ( 1100 ),
       communicationFailureTCCAToShelfSLOT11     ( 1110 ),
       communicationFailureTCCAToShelfSLOT12     ( 1120 ),
       communicationFailureTCCAToShelfSLOT13     ( 1130 ),
       communicationFailureTCCAToShelfSLOT14     ( 1140 ),
       communicationFailureTCCAToShelfSLOT15     ( 1150 ),
       communicationFailureTCCAToShelfSLOT16     ( 1160 ),
       communicationFailureTCCAToShelfSLOT17     ( 1170 ),
       communicationFailureTCCPAToTCCJAprocessor ( 1180 ),
       communicationFailureTCCBToShelfSLOT1      ( 1190 ),
       communicationFailureTCCBToShelfSLOT2      ( 1200 ),
       communicationFailureTCCBToShelfSLOT3      ( 1210 ),
       communicationFailureTCCBToShelfSLOT4      ( 1220 ),
       communicationFailureTCCBToShelfSLOT5      ( 1230 ),
       communicationFailureTCCBToShelfSLOT6      ( 1240 ),
       communicationFailureTCCBToShelfSLOT7      ( 1250 ),
       communicationFailureTCCBToShelfSLOT8      ( 1260 ),
       communicationFailureTCCBToShelfSLOT9      ( 1270 ),
       communicationFailureTCCBToShelfSLOT10     ( 1280 ),
       communicationFailureTCCBToShelfSLOT11     ( 1290 ),
       communicationFailureTCCBToShelfSLOT12     ( 1300 ),
       communicationFailureTCCBToShelfSLOT13     ( 1310 ),
       communicationFailureTCCBToShelfSLOT14     ( 1320 ),
       communicationFailureTCCBToShelfSLOT15     ( 1330 ),
       communicationFailureTCCBToShelfSLOT16     ( 1340 ),
       communicationFailureTCCBToShelfSLOT17     ( 1350 ),
       communicationFailureTCCPBToTCCJAprocessor ( 1360 ),

       controlEquipmentControlCommunicationsEquipmentFailure ( 1370 ),
       controlEquipmentControlProcessorFailure               ( 1380 ),
       controlEquipmentWorkingMemoryFailure                  ( 1390 ),

       interconnectionEquipmentFailure                     ( 1400 ),
       interconnectionEquipmentFailurePayloadBus1Working    ( 1410 ),
       interconnectionEquipmentFailurePayloadBus2Working    ( 1420 ),
       interconnectionEquipmentFailurePayloadBus3Working    ( 1430 ),
       interconnectionEquipmentFailurePayloadBus4Working    ( 1440 ),
       interconnectionEquipmentFailurePayloadBus5Working    ( 1450 ),
       interconnectionEquipmentFailurePayloadBus6Working    ( 1460 ),
       interconnectionEquipmentFailurePayloadBus7Working    ( 1470 ),
       interconnectionEquipmentFailurePayloadBus8Working    ( 1480 ),
       interconnectionEquipmentFailurePayloadBus9Working    ( 1490 ),
       interconnectionEquipmentFailurePayloadBus10Working   ( 1500 ),
       interconnectionEquipmentFailurePayloadBus11Working   ( 1510 ),
       interconnectionEquipmentFailurePayloadBus12Working   ( 1520 ),
       interconnectionEquipmentFailurePayloadBus1Protect   ( 1530 ),
       interconnectionEquipmentFailurePayloadBus2Protect   ( 1540 ),
       interconnectionEquipmentFailurePayloadBus3Protect   ( 1550 ),
       interconnectionEquipmentFailurePayloadBus4Protect   ( 1560 ),
       interconnectionEquipmentFailurePayloadBus5Protect   ( 1570 ),
       interconnectionEquipmentFailurePayloadBus6Protect   ( 1580 ),
       interconnectionEquipmentFailurePayloadBus7Protect   ( 1590 ),
       interconnectionEquipmentFailurePayloadBus8Protect   ( 1600 ),
       interconnectionEquipmentFailurePayloadBus9Protect   ( 1610 ),
       interconnectionEquipmentFailurePayloadBus10Protect  ( 1620 ),
       interconnectionEquipmentFailurePayloadBus11Protect  ( 1630 ),
       interconnectionEquipmentFailurePayloadBus12Protect  ( 1640 ),
       interconnectionEqptTimeSlotInterchangeEqptFailure   ( 1650 ),

       criticalAlarmCausedByEquipmentFailure               ( 1660 ),
       equipmentFailureHighTemperature                     ( 1670 ),
       equipmentFailureInvalidMACAddress                   ( 1680 ),
       equipmentFailureBoardFailure                        ( 1690 ),
       equipmentFailureDiagnosticsFailure                  ( 1700 ),
       equipmentFailureMediumAccessControl                 ( 1710 ),
       facilityTerminationEquipmentFailure                 ( 1720 ),
       facilityTerminationEquipmentAutomaticLaserShutdown  ( 1730 ),
       failureToReleaseFromProtection                      ( 1740 ),
       facilityTerminationEquipmentReceiverFailure         ( 1750 ),
       facilityTerminationEquipmentTransmitFailure         ( 1760 ),
       facilityTerminationEquipmentReceiverMissing         ( 1770 ),
       facilityTerminationEquipmentTransmitterMissing      ( 1780 ),
       failureToSwitchToProtection                         ( 1790 ),
       failureToSwitchToProtectionRing                     ( 1800 ),

       failureToSwitchToProtectionSpan                     ( 1810 ),
       failureToSwitchToProtectionPath                     ( 1820 ),
       failureOfCoolingFanTray                             ( 1830 ),
       equipmentUnitPlugIn                                 ( 1840 ),
       powerFailureDetectedInternalToNE                    ( 1850 ),
       powerFailureFuseAlarm                               ( 1860 ),
       synchronizationUnitFailure                          ( 1870 ),
       synchronizationSwitchingEquipmentFailure            ( 1880 ),
       equipmentUnitUnplug                                 ( 1890 ),
       loopback                                            ( 1900 ),

       loopbackDueToFEACCommandDS1                         ( 1910 ),
       loopbackCommandSentToFarEndDS1                      ( 1920 ),
       loopbackDueToFEACCommandDS3                         ( 1930 ),
       loopbackCommandSentToFarEndDS3                      ( 1940 ),
       loopbackDueToFarEndCommandDS2                       ( 1950 ),
       loopbackCommandSentToFarEndDS2                      ( 1960 ),
       loopbackFacility                                    ( 1970 ),
       loopbackNetwork                                     ( 1980 ),
       loopbackTerminal                                    ( 1990 ),
       manuallyCausedAbnormalCondition                     ( 2000 ),
       newRootDiscoveredInBridgedNetwork                   ( 2010 ),
       topologyChangeDiscoveredInBridgedNetwork            ( 2020 ),
       normalCondition                                     ( 2030 ),
       embeddedOperationsChannelFailureLinkDown            ( 2040 ),
       peerStateMismatch                                   ( 2050 ),
       proceduralError                                     ( 2060 ),
       proceduralErrorImproperRemoval                      ( 2070 ),
       proceduralErrorDuplicateNodeID                      ( 2080 ),
       proceduralErrorBLSROutOfSync                        ( 2090 ),
       resynchronizedBLSRTables                            ( 2100 ),
       protectionUnitNotAvailable                          ( 2110 ),
       performanceMonitorThresholdCrossingAlert            ( 2120 ),
       occurrenceOfAProtectionSwitchingEvent               ( 2130 ),
       recoveryOrServiceProtectionActionHasBeenInitiated   ( 2140 ),
       automaticSystemReset                                ( 2150 ),
       automacticUPSRSwitchCausedByAIS          ( 2160 ),
       automacticUPSRSwitchCausedByLOP          ( 2170 ),
       automacticUPSRSwitchCausedByUneq         ( 2180 ),
       automacticUPSRSwitchCausedByPDI          ( 2190 ),
       automacticUPSRSwitchCausedBySfber        ( 2200 ),
       automacticUPSRSwitchCausedBySdber        ( 2210 ),
       coldRestart                              ( 2220 ),
       workingFacilityOrEqptForcedSwitchedToWorking      ( 2230 ),
       workingFacilityOrEqptForcedSwitchedToWorkingRing  ( 2240 ),
       workingFacilityOrEqptForcedSwitchedToWorkingSpan  ( 2250 ),
       workingFacilityOrEqptForcedSwitchedProtectionUnit ( 2260 ),

       workingFacilityOrEqptForcedSwitchedProtectionUnitRing ( 2270 ),
       workingFacilityOrEqptForcedSwitchedProtectionUnitSpan ( 2280 ),
       workingFacilityOrEqptForcedSwitchedProtectionUnitPath ( 2290 ),

       initializationInitiated   ( 2300 ),
       lockoutOfProtection       ( 2310 ),
       lockoutOfProtectionRing   ( 2320 ),
       lockoutOfProtectionSpan   ( 2330 ),
       lockoutOfProtectionPath   ( 2340 ),
       lockoutOfWorking          ( 2350 ),
       lockoutOfWorkingRing      ( 2360 ),
       lockoutOfWorkingSpan      ( 2370 ),

       manualSystemReset         ( 2380 ),

       manualSynchronizationSwitchToInternalClock    ( 2390 ),
       manualSynchronizationSwitchToPrimaryRefernce  ( 2400 ),
       manualSynchronizationSwitchToSecondRefernce   ( 2410 ),
       manualSynchronizationSwitchToThirdRefernce    ( 2420 ),
       manualSynchronizationSwitchToFourthRefernce   ( 2430 ),
       manualSynchronizationSwitchToFifthRefernce    ( 2440 ),
       manualSynchronizationSwitchToSixthRefernce    ( 2450 ),

       manualSwitchOfWorkingFacilityOrEqptToProtectionRing   ( 2460 ),
       manualSwitchOfWorkingFacilityOrEqptToProtectionSpan   ( 2470 ),
       manualSwitchOfWorkingFacilityOrEqptToProtection       ( 2480 ),
       manualSwitchOfWorkingFacilityOrEqptToProtectionUnit   ( 2490 ),
       workingFacilityOrEqptManualSwitchToProtectionUnitRing ( 2500 ),
       workingFacilityOrEqptManualSwitchToProtectionUnitSpan ( 2510 ),
       manualSwitchOfWorkingFacilityOrEqptToProtectionPath   ( 2520 ),

       powerFailureRestart        ( 2530 ),
       ringIsSquelchingTraffic    ( 2540 ),
       softwareDownloadInProgress ( 2550 ),

       synchronizationSwitchToInternalClock   ( 2560 ),
       synchronizationSwitchToPrimaryRefernce ( 2570 ),
       synchronizationSwitchToSecondRefernce  ( 2580 ),
       synchronizationSwitchToThirdRefernce   ( 2590 ),
       synchronizationSwitchToFourthRefernce  ( 2600 ),
       synchronizationSwitchToFifthRefernce   ( 2610 ),
       synchronizationSwitchToSixthRefernce   ( 2620 ),

       systemReboot                                        ( 2630 ),
       workingFacilityOrEquipmentSwitchedBackToWorking     ( 2640 ),
       workingFacilityOrEquipmentSwitchedToProtectionUnit  ( 2650 ),
       warmRestart                                         ( 2660 ),
       lineIsInWaitToRestoreStateSONET                     ( 2670 ),
       manualSwitchRequestOnFacilityOrEquipment            ( 2680 ),
       forceSwitchRequestOnFacilityOrEquipment             ( 2690 ),
       lockoutSwitchRequestOnFacilityOrEquipment           ( 2700 ),
       rmonHistoriesAndAlarmsReset                ( 2710 ),
       rmonThresholdCrossingAlarm                 ( 2720 ),

         -- 2730 thru 2790 have been allotted for
         -- a future release

       traceIdentifierMismatchSTSPath             ( 2800 ),
       nodePowerFailureAtConnectorA               ( 2810 ),
       nodePowerFailureAtConnectorB               ( 2820 ),

       freeMemoryOnCardVeryLow                    ( 2830 ),
       freeMemoryOnCardAlmostGone                 ( 2840 ),

       exerciseRing                               ( 2850 ),
       exerciseSpan                               ( 2860 ),
       squelchingPath                             ( 2870 ),
       extraTrafficPreemptted                     ( 2880 ),

       farEndLockoutOfWorkingRing                 ( 2890 ),
       farEndLockoutOfWorkingSpan                 ( 2900 ),
       farEndLockoutOfProtectionRing              ( 2910 ),
       farEndLockoutOfProtectionAllSpans          ( 2920 ),

       farEndWorkingFacilityForcedToSwitchToProtectionUnitRing ( 2930 ),
       farEndWorkingFacilityForcedToSwitchToProtectionUnitSpan ( 2940 ),

       farEndManualSwitchOfWorkingFacilityToProtectionUnitRing ( 2950 ),
       farEndManualSwitchOfWorkingFacilityToProtectionUnitSpan ( 2960 ),
       farEndExerciseRing                                      ( 2970 ),
       farEndExerciseSpan                                      ( 2980 ),
       farEndBERThresholdPassedForSignalFailureRing ( 2990 ),
       farEndBERThresholdPassedForSignalFailureSpan ( 3000 ),
       farEndBERThresholdPassedForSignalDegradeRing ( 3010 ),
       farEndBERThresholdPassedForSignalDegradeSpan ( 3020 ),
       channelFarEndProtectionLineSignalDegradeAPS  ( 3030 ),

       ringSwitchIsActiveOnTheEastSide      ( 3040 ),
       ringSwitchIsActiveOnTheWestSide      ( 3050 ),
       spanSwitchIsActiveOnTheEastSide      ( 3060 ),
       spanSwitchIsActiveOnTheWestSide      ( 3070 ),

       uniDirectionalFullPassThroughIsActive  ( 3080 ),
       biDirectionalFullPassThroughIsActive   ( 3090 ),

       kBytePassThroughIsActive        ( 3100 ),
       ringIsSegmented                 ( 3110 ),
       ringTopologyIsUnderConstruction ( 3120 ),

       lockoutOfProtectionAllSpans                   ( 3130 ),
       farEndOfFiberIsProvisionedWithDifferentRingID ( 3140 ),
       bothEndsOfFiberProvisionedAsEastOrBothAsWest  ( 3150 ),
       invalidLoginSeeAuditTrail                     ( 3160 ),

       autonomousMessagesInhibited        ( 3170 ),
       trafficStormLANtemporarilyDisabled ( 3180 ),

       tl1ReptDbchgMessagesInhibited ( 3190 ),
       userIdHasExpired              ( 3200 ),
       partialFanFailure             ( 3210 ),
       forceSwitchRequestOnRing      ( 3220 ),
       forceSwitchRequestOnSpan      ( 3230 ),
       lockoutSwitchRequestOnRing    ( 3240 ),
       lockoutSwitchRequestOnSpan    ( 3250 ),
       manualSwitchRequestOnRing     ( 3260 ),
       manualSwitchRequestOnSpan     ( 3270 ),

       communicationFailurePeerToPeerSlotControlBusA  ( 3280 ),
       communicationFailurePeerToPeerSlotControlBusB  ( 3290 ),
       communicationFailureTCCAToShelfSlot  ( 3300 ),
       communicationFailureTCCBToShelfSlot  ( 3310 ),

       interconnectionEquipmentFailureWorkingPayloadBus ( 3320 ),
       interconnectionEquipmentFailureProtectPayloadBus ( 3330 ),

       inhibitSwitchToProtectRequestInEffectOnEquipment ( 3340 ),
       inhibitSwitchToWorkingRequestInEffectOnEquipment ( 3350 ),

       passedBERThresholdForSignalDegradeLine ( 3360 ),
       passedBERThresholdForSignalDegradePath ( 3370 ),
       passedBERThresholdForSignalFailLine    ( 3380 ),
       passedBERThresholdForSignalFailPath    ( 3390 )
} 

CerentGenericEntityClass ::= TEXTUAL-CONVENTION
--   DISPLAY-HINT "d"
   STATUS current
   DESCRIPTION
       "This is the TC used to find out to which cerentGenericEntityClass
        an alarm belongs to. The first octet of the alarmIndex value is
        mapped to the following enum. Look at cerentGenericAlarmIndex for
        more details."
   SYNTAX INTEGER {
  unknownEntity   (  1 ),
  ne              ( 10 ),
  ccNe            ( 20 ),
  backplane       ( 30 ),
  ccBackplane     ( 40 ),
  eqpt            ( 50 ),
  ccEqpt          ( 60 ),
  ocn             ( 70 ),
  ccOcn           ( 80 ),
  thOcn           ( 90 ),
  sdcc            ( 100 ),
  ds3             ( 110 ),
  ccDs3           ( 120 ),
  thDs3           ( 130 ),
  stsMon          ( 140 ),
  ccStsMon        ( 150 ),
  stsTerm         ( 160 ),
  ccStsTerm       ( 170 ),
  thStsTerm       ( 180 ),
  psSts           ( 190 ),
  ccPsSts         ( 200 ),
  xcSts           ( 210 ),
  bits            ( 220 ),
  ccBits          ( 230 ),
  neSynchref      ( 240 ),
  ccNeSynchref    ( 250 ),
  extSynchref     ( 260 ),
  ccExtSynchref   ( 270 ),
  envalrm         ( 280 ),
  envctrl         ( 290 ),
  javaSpe         ( 300 ),
  ringMap         ( 310 ),
  squelchTable    ( 320 ),
  payloadTable    ( 330 ),
  userTable       ( 340 ),
  routingTable    ( 350 ),
  stsRing         ( 360 ),
  ifGrp           ( 370 ),
  craft           ( 380 ),
  ds1             ( 390 ),
  ccDs1           ( 400 ),
  thDs1           ( 410 ),
  vtTerm          ( 420 ),
  ccVtTerm        ( 430 ),
  thVtTerm        ( 440 ),
  spareSdcc       ( 450 ),
  ccSdcc          ( 460 ),
  thSdcc          ( 470 ),
  ds2             ( 480 ),
  ccDs2           ( 490 ),
  thDs2           ( 500 ),
  ec112           ( 510 ),
  ps              ( 520 ),
  psVt            ( 530 ),
  e100t           ( 540 ),
  e1000f          ( 550 ),
  etherBridge     ( 560 ),
  entNb           ( 570 ),

  entDs1             ( 1010 ),
  entDs3             ( 1020 ),
  ringPort           ( 1180 ),
  ringPath           ( 1190 ),
  entOc3             ( 1200 ),
  entOc12            ( 1210 ),
  entOc48            ( 1220 ),
  entOc192           ( 1230 ),
  entSts1            ( 1240 ),
  entSts3c           ( 1250 ),
  entSts12c          ( 1260 ),
  entSts48c          ( 1270 ),
  entSyncn           ( 1280 ) 
}

-- **************************************************************
cerentGenericObjects OBJECT-IDENTITY
      STATUS      current
      DESCRIPTION
            "All the generic objects definitions are grouped
             under this" 
      ::= { cerentGeneric 10 }

-- **************************************************************

cerentCommonObjectsGroup OBJECT-IDENTITY
      STATUS      current
      DESCRIPTION
            "The group to combine all the Cisco OTBU common 
             objects" 
      ::= { cerentGenericObjects 10 }

cerentEnableNotification   OBJECT-TYPE
       SYNTAX      TruthValue
       MAX-ACCESS  read-write
       STATUS      current
       DESCRIPTION
               "This variable indicates whether the system produces
                notifications.  A value=FALSE will prevent notifications
                from being sent by this system."
       DEFVAL { true }
       ::= { cerentCommonObjectsGroup 10 }

cerentNodeTime OBJECT-TYPE
       SYNTAX       DisplayString 
       MAX-ACCESS   read-only
       STATUS current
       DESCRIPTION
       "Indicates current local time as reflected by
        the Cisco OTBU equipment. The format this scalar is
        YYYYMMDDhhmmss{S/D}. E.g., 
        20011103133453D means 1:34:53 PM PDT on 03/Nov/2001
        19990614095436S means 9:54:36 AM PST on 14/Jun/1999.
        If the last octet is S then the time is standard time.
        Otherwise it is D to indicate it is daylight saving
        time, if applicable"
       ::= { cerentCommonObjectsGroup 20 }

cerentNotificationsSent OBJECT-TYPE  
       SYNTAX      Counter32 
       MAX-ACCESS read-only
       STATUS current
       DESCRIPTION
              "A count of v1+v2 notifications sent out
               by the agent. Resets to zero after
               cold/warm start."
       ::= { cerentCommonObjectsGroup 30 }

cerentLastChangeTime OBJECT-TYPE
    SYNTAX      TimeStamp
    MAX-ACCESS  read-only
    STATUS      current
    DESCRIPTION
            "The value of sysUpTime at the time 
             a conceptual row is created or deleted 
             in cerentGenericAlarmTable "
    ::= { cerentCommonObjectsGroup 40 }

-- **************************************************************
-- 
cerentGenericGeneralGroup OBJECT-IDENTITY
       STATUS       current
       DESCRIPTION
              "Another class of objects found in
               Cisco ONS 15327"
       ::= { cerentGenericObjects 20 }

cerentGenericSoftwareVersion OBJECT-TYPE
       SYNTAX       DisplayString
       MAX-ACCESS   read-only
       STATUS current
       DESCRIPTION
       "Indicates the version of software that is
        used in Cisco ONS Network element 
        ONS 15327. E.g., 2.2.03"
       ::= { cerentGenericGeneralGroup 10 }

cerentGenericAlarmGroup OBJECT-IDENTITY
       STATUS       current
       DESCRIPTION
              "The group that will represent all the
               alarm info in the Cisco ONS network element 
               ONS 15327"
       ::= { cerentGenericObjects 30 }

cerentGenericAlarmCount       OBJECT-TYPE
       SYNTAX       Unsigned32
       MAX-ACCESS   read-only
       STATUS current
       DESCRIPTION
           "Total number of active alarms in the 
            Cisco ONS network element ONS 15327.
            This equals the total number of rows in
            cerentGenericAlarmTable at any time."
       ::= { cerentGenericAlarmGroup 10 }

cerentGenericAlarmTable       OBJECT-TYPE
       SYNTAX SEQUENCE OF CerentGenericAlarmEntry
       MAX-ACCESS not-accessible 
       STATUS current
       DESCRIPTION
              "This table holds all the current raised
               alarms.  When an alarm is raised, it will
               appear a new entry in the table.
               Whenever an alarm is cleared it will be 
               removed from the table and all the entries 
               from below will be moved up by another row."
       ::= { cerentGenericAlarmGroup 20 }

cerentGenericAlarmEntry       OBJECT-TYPE
       SYNTAX CerentGenericAlarmEntry
       MAX-ACCESS not-accessible
       STATUS current
       DESCRIPTION
              "Row definition for cerentGenericAlarmTable"
       INDEX { cerentGenericAlarmIndex, cerentGenericAlarmType }
       ::= { cerentGenericAlarmTable 1 }

CerentGenericAlarmEntry ::= SEQUENCE {
       cerentGenericAlarmIndex           Integer32,
       cerentGenericAlarmObjectType      CerentGenericEntityClass,
       cerentGenericAlarmSlotNumber      Integer32,
       cerentGenericAlarmPortNumber      Integer32,
       cerentGenericAlarmLineNumber      Integer32,
       cerentGenericAlarmObjectIndex     Integer32,
       cerentGenericAlarmType            CerentGenericAlarmType, 
       cerentGenericAlarmState           CerentNotificationClass,
       cerentGenericAlarmTimeStamp       TimeStamp,
       cerentGenericAlarmObjectName      DisplayString
       }

cerentGenericAlarmIndex       OBJECT-TYPE
       SYNTAX Integer32 ( 1..2147483647 ) -- all +ve values
       MAX-ACCESS not-accessible
       STATUS current
       DESCRIPTION
              "Uniquely identifies each entry in alarm table.
               So when an alarm in the alarm table clears,
               the alarms located below the this cleared
               alarm will have to change their alarm index.
               Hence there will be holes in the alarm table.
               May not start with one and there will be some
               missing numbers."
       ::= { cerentGenericAlarmEntry 10 }

cerentGenericAlarmObjectType       OBJECT-TYPE
       SYNTAX CerentGenericEntityClass
       MAX-ACCESS read-only
       STATUS current
       DESCRIPTION
              "This will indicate what is the type
               of the entity which raised this alarm.
               ( E.g., DS3, etherBridge, VT-TERM, etc ) 
               The NMS is expected to use this value
               to decide which table to poll for 
               further info about the alarm"
       ::= { cerentGenericAlarmEntry 20 }

cerentGenericAlarmSlotNumber           OBJECT-TYPE
       SYNTAX Integer32
       MAX-ACCESS read-only
       STATUS current
       DESCRIPTION
              "This will indicate what is the slot 
               of the object which raised this alarm.
               If not relevant to the alarm, will be
               zero."
       ::= { cerentGenericAlarmEntry 30 }

cerentGenericAlarmPortNumber          OBJECT-TYPE
       SYNTAX Integer32
       MAX-ACCESS read-only
       STATUS current
       DESCRIPTION
              "This will indicate what is the port
               of the object which raised this alarm.
               If not relevant to the alarm, will be
               zero."
       ::= { cerentGenericAlarmEntry 40 }
 
cerentGenericAlarmLineNumber           OBJECT-TYPE
       SYNTAX Integer32
       MAX-ACCESS read-only
       STATUS     current
       DESCRIPTION
              "This will indicate what is the port
               of the object which raised this alarm.
               If not relevant to the alarm, will be
               zero."
       ::= { cerentGenericAlarmEntry 50 }

cerentGenericAlarmObjectIndex       OBJECT-TYPE
       SYNTAX Integer32
       MAX-ACCESS read-only
       STATUS current
       DESCRIPTION
              "Every alarm is raised by an object and 
               this object is an entry in a specific 
               table. This is the index of the object
               in that table E.g., if the alarm is interface
               related, this index is the index of the
               interface in the interface table."
       ::= { cerentGenericAlarmEntry 60 }

cerentGenericAlarmType       OBJECT-TYPE
       SYNTAX CerentGenericAlarmType
       MAX-ACCESS read-only
       STATUS current
       DESCRIPTION
              "Indicates what the exact nature of the
               alarm. See the CerentGenericAlarmType TC
               for mapping details "
       ::= {cerentGenericAlarmEntry  70 }

cerentGenericAlarmState OBJECT-TYPE  
       SYNTAX        CerentNotificationClass
       MAX-ACCESS read-only
       STATUS current
       DESCRIPTION
              "Specifies alarm severity and service 
               affecting status ( SA/NSA ). Only 
               {minor|major|critical}+{NA|NSA} alarms and
               standing conditions will be represented here."
       ::= { cerentGenericAlarmEntry 80 }

cerentGenericAlarmTimeStamp OBJECT-TYPE  
       SYNTAX   TimeStamp
       MAX-ACCESS read-only
       STATUS current
       DESCRIPTION
              "Indicates when the alarm occurred.
               The value is number of ticks
               that has lasped since 1/1/1970 "
       ::= { cerentGenericAlarmEntry 90 }

cerentGenericAlarmObjectName OBJECT-TYPE
       SYNTAX  DisplayString
       MAX-ACCESS read-only
       STATUS current
       DESCRIPTION
              "TL1-style user-visible name which uniquely
               identifies an object in the system"
       ::= { cerentGenericAlarmEntry 100 }

--  All Cisco ONS Generic Notifications definitions.

cerentGenericEvents OBJECT-IDENTITY
      STATUS      current
      DESCRIPTION
            "Place holder for all notifications
             of Cisco ONS network device ONS 15327"
      ::= { cerentGeneric 20 }

cerentGenericV2Events OBJECT-IDENTITY
      STATUS      current
      DESCRIPTION
                 "The sub-identifier has to be zero, as part
                  of the interoperability agreement between
                  SNMPv1 and SNMPv2 worlds."
      ::= { cerentGenericEvents 0  } 

-- ---------------------------------------------
-- All the Cisco ONS generic notifications definitions
-- ---------------------------------------------

-- object and event groups

alarmUnknown
  NOTIFICATION-TYPE 
    OBJECTS { 
        cerentNodeTime, 
        cerentGenericAlarmState, 
        cerentGenericAlarmObjectType, 
        cerentGenericAlarmObjectIndex,
        cerentGenericAlarmSlotNumber, 
        cerentGenericAlarmPortNumber, 
        cerentGenericAlarmLineNumber,
        cerentGenericAlarmObjectName
    }
    STATUS current 
    DESCRIPTION "alarm unknown" 
    ::= { cerentGenericV2Events  1 } 

alarmCutoffIsInManualMode
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "alarm cutoff is in manual mode" 
    ::= { cerentGenericV2Events 10 }
 
failureDetectedExternalToTheNE
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "failure detected External to the NE" 
    ::= { cerentGenericV2Events 20 }

externalError
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "external error" 
    ::= { cerentGenericV2Events 30 }
 
excessiveSwitching
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "excessive switching" 
    ::= { cerentGenericV2Events 40 }
 
terminationFailureSDCC
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "SDCC Termination failure" 
    ::= { cerentGenericV2Events 50 }
 
incomingFailureCondition
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "incoming failure condition" 
    ::= { cerentGenericV2Events 60 }
 
alarmIndicationSignal       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "alarm indication signal" 
    ::= { cerentGenericV2Events 70 }
 
alarmIndicationSignalLine
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "alarm indication signal LINE" 
    ::= { cerentGenericV2Events 80 }
 
alarmIndicationSignalPath  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "alarm indication signal Path" 
    ::= { cerentGenericV2Events 90 }
 
alarmIndicationSignalVT    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "alarm indication signal VT" 
    ::= { cerentGenericV2Events 100 }

channelFailureAPS           
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "channel failure APS" 
    ::= { cerentGenericV2Events 110 }
 
channelByteFailureAPS      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "channel Byte failure APS" 
    ::= { cerentGenericV2Events 120 }
 
channelProtectionSwitchingChannelMatchFailureAPS   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "channel Protection Switching Channel Match failure APS" 
    ::= { cerentGenericV2Events 130 }
 
channelAutomaticProtectionSwitchModeMismatchAPS    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "channel Automatic Protection Switch Mode Mismatch APS" 
    ::= { cerentGenericV2Events 140 }
 
channelFarEndProtectionLineFailureAPS              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "channel far end protection line failure APS" 
    ::= { cerentGenericV2Events 150 }
 
channelBLSRInconsistentAPSCode       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "channel BLSR inconsistent APS code" 
    ::= { cerentGenericV2Events 160 }
 
channelBLSRImproperAPSCodeAPS       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "channel BLSR Improper APS code APS" 
    ::= { cerentGenericV2Events 170 }
 
channelBLSRNodeIdMismatchAPS        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "channel BLSR Node Id Mismatch APS" 
    ::= { cerentGenericV2Events 180 }
 
channelBLSRDefaultKAPS    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "channel BLSR Default K APS" 
    ::= { cerentGenericV2Events 190 }
 
channelBLSRConnectionLossAPS         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "channel BLSR Connection loss APS" 
    ::= { cerentGenericV2Events 200 }
 
bipolarViolation             
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "bipolar Violation" 
    ::= { cerentGenericV2Events 210 }
 
carrierLossOnTheLAN       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "carrier Loss on the LAN" 
    ::= { cerentGenericV2Events 220 }
 
concatenationErrorSTS       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "concatenation error STS" 
    ::= { cerentGenericV2Events 230 }
 
excessCollisionsOnTheLAN  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "excess collisions on the LAN" 
    ::= { cerentGenericV2Events 240 }
 
facilityCriticalAlarmCausedByDS3FacilityFailure   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "facility critical alarm caused by DS3 facility failure" 
    ::= { cerentGenericV2Events 250 }
 
farEndAIS   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far end AIS" 
    ::= { cerentGenericV2Events 260 }
 
farEndMultipleDS1LOSDetectedOnDS3 
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far end Multiple DS1 LOS detected on DS3" 
    ::= { cerentGenericV2Events 270 }
 
farEndDS1EqptFailNonServiceAffecting              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far end DS1 eqpt fail non service affecting" 
    ::= { cerentGenericV2Events 280 }
 
farEndDS1EqptFailServiceAffecting  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far end DS1 Eqpt fail service affecting" 
    ::= { cerentGenericV2Events 290 }
 
farEndSingleDS1LOS        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far end Single DS1 LOS" 
    ::= { cerentGenericV2Events 300 }
 
farEndDS3EqptFailNonServiceAffecting              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far end DS3 Eqpt failure non service affecting" 
    ::= { cerentGenericV2Events 310 }
 
farEndDS3EqptFailServiceAffecting  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far end DS3 Eqpt failure service affecting" 
    ::= { cerentGenericV2Events 320 }
 
farEndCmnEqptFailNonServiceAffecting              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far end common Eqpt failure non service affecting" 
    ::= { cerentGenericV2Events 330 }
 
farEndIDLE  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far end IDLE" 
    ::= { cerentGenericV2Events 340 }
 
farEndLOS   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far end LOS" 
    ::= { cerentGenericV2Events 350 }
 
farEndLOF   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far end LOF" 
    ::= { cerentGenericV2Events 360 }
 
farEndBlockError           
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "far End Block Error" 
    ::= { cerentGenericV2Events 370 }
 
idleConditionDS3            
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "idle Condition DS3" 
    ::= { cerentGenericV2Events 380 }
 
lossOfFrame 
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of Frame" 
    ::= { cerentGenericV2Events 390 }
 
lossOfPointer               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of Pointer" 
    ::= { cerentGenericV2Events 400 }
 
lossOfPointerPath
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of Pointer Path " 
    ::= { cerentGenericV2Events 410 }
 
lossOfPointerVT            
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of Pointer VT" 
    ::= { cerentGenericV2Events 420 }
 
lossOfSignal                
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of Signal" 
    ::= { cerentGenericV2Events 430 }
 
outOfFrame  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "out of Frame" 
    ::= { cerentGenericV2Events 440 }
 
pathSelectorInabilityToSwitchToAValidSignal      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "path Selector inability to swtich to a valid signal" 
    ::= { cerentGenericV2Events 450 }
 
remoteAlarmIndication       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "remote Alarm Indication" 
    ::= { cerentGenericV2Events 460 }
 
remoteFailureIndication     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "remote Failure Indication" 
    ::= { cerentGenericV2Events 470 }
 
remoteFailureIndicationLine           
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "remote Failure Indication LINE" 
    ::= { cerentGenericV2Events 480 }
 
remoteFailureIndicationPath           
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "remote Failure Indication Path" 
    ::= { cerentGenericV2Events 490 }
 
remoteFailureIndicationVT  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "remote Failure Indication VT" 
    ::= { cerentGenericV2Events 500 }
 
facilityHasPassedBERThresholdForSignalDegrade     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "facility has passed BER Threshold for Signal Degrade" 
    ::= { cerentGenericV2Events 510 }
 
severelyErroredFrame        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "severely Errored Frame" 
    ::= { cerentGenericV2Events 520 }
 
facilityHasPassedBERThresholdForSignalFailure     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "facility has passed BER threshold for Signal Failure" 
    ::= { cerentGenericV2Events 530 }
 
signalLabelMismatchFailuresSONET     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "signal Label Mismatch Failures SONET" 
    ::= { cerentGenericV2Events 540 }
 
signalLabelMismatchFailurePayloadDefectIndication  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "signal Label Mismatch Failure Payload Defect Indication" 
    ::= { cerentGenericV2Events 550 }
 
signalLabelMismatchFailurePayloadDefectIndicationPath   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "signal Label Mismatch Failure Payload Defect Indication Path" 
    ::= { cerentGenericV2Events 560 }
 
signalLabelMismatchFailurePayloadLabelMismatchPath      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "signal Label Mismatch Failure Payload Label Mismatch Path" 
    ::= { cerentGenericV2Events 570 }
 
signalLabelMismatchFailurePayloadLabelMismatchVT        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "signal Label Mismatch Failure Payload Label Mismatch VT" 
    ::= { cerentGenericV2Events 580 }
 
signalLabelMismatchFailureUnequippedPath  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "signal Label Mismatch Failure Unequipped Path" 
    ::= { cerentGenericV2Events 590 }
 
signalLabelMismatchFailureUnequippedVT    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "signal Label Mismatch Failure Unequipped VT" 
    ::= { cerentGenericV2Events 600 }
 
lossOfTimingOnSynchronizationLink         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of timing on Synchronization link" 
    ::= { cerentGenericV2Events 610 }
 
lossOfTimingOnAllSpecifiedSynchronizationLinks          
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of timing on all specified synchronization links" 
    ::= { cerentGenericV2Events 620 }
 
lossOfTimingOnPrimarySynchronizationLink 
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of timing on primary synchronization link" 
    ::= { cerentGenericV2Events 630 }
 
lossOfTimingOnSecondarySynchronizationLink               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of timing on secondary synchronization link" 
    ::= { cerentGenericV2Events 640 }
 
lossOfTimingOnThirdSynchronizationLink   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of timing on third synchronization link" 
    ::= { cerentGenericV2Events 650 }
 
lossOfTimingOnFourthSynchronizationLink  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of timing on fourth synchronization link" 
    ::= { cerentGenericV2Events 660 }
 
lossOfTimingOnFifthSynchronizationLink   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of timing on fifth synchronization link" 
    ::= { cerentGenericV2Events 670 }
 
lossOfTimingOnSixthSynchronizationLink   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loss of timing on sixth synchronization link" 
    ::= { cerentGenericV2Events 680 }
 
failedToReceiveSynchronizationStatusMessage 
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "failed to receive Synchronization Status Message" 
    ::= { cerentGenericV2Events 690 }

synchronizationStatusMessagesAreDisabledOnThisInterface   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "synchronization Status Messages are disabled on this interface" 
    ::= { cerentGenericV2Events 700 }

primaryReferenceSourceStratum1Traceable     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "primary Reference Source Stratum 1 Traceable" 
    ::= { cerentGenericV2Events 710 }

synchronizedTraceabilityUnknown     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "synchronized Traceability Unknown" 
    ::= { cerentGenericV2Events 720 }

stratum2Traceable   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "stratum 2 Traceable " 
    ::= { cerentGenericV2Events 730 }

transitNodeClockTraceable          
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "transit Node clock Traceable" 
    ::= { cerentGenericV2Events 740 }

stratum3ETraceable  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "stratum 3E Traceable" 
    ::= { cerentGenericV2Events 750 }

stratum3Traceable   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "stratum 3 Traceable" 
    ::= { cerentGenericV2Events 760 }

minimumClockTraceableSONET        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "SONET Minimum clock Traceable" 
    ::= { cerentGenericV2Events 770 }

stratum4Traceable   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "stratum 4 Traceable" 
    ::= { cerentGenericV2Events 780 }

doNotUseForSynchronization        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "do not Use for Synchronization" 
    ::= { cerentGenericV2Events 790 }

reservedForNetworkSynchronizationUse         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "reserved for Network Synchronization Use" 
    ::= { cerentGenericV2Events 800 }

outgoingFailureCondition            
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "outgoing failure condition" 
    ::= { cerentGenericV2Events 810 }
 
remoteDefectIndicationLine         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "remote Defect Indication LINE" 
    ::= { cerentGenericV2Events 820 }
 
remoteDefectIndicationPath         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "remote Defect Indication Path" 
    ::= { cerentGenericV2Events 830 }
 
freeRunningSynchronizationMode     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "free Running Synchronization mode" 
    ::= { cerentGenericV2Events 840 }
 
holdoverSynchronizationMode         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "holdover synchronization mode" 
    ::= { cerentGenericV2Events 850 }
 
fastStartSynchronizationMode       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "fast Start synchronization mode" 
    ::= { cerentGenericV2Events 860 }
 
internalHardwareFaultOrFailure    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "internal hardware fault or failure" 
    ::= { cerentGenericV2Events 870 }
 
errorInternalToTheNEDetected     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "error Internal to the NE Detected" 
    ::= { cerentGenericV2Events 880 }
 
internalMessageError                
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "internal Message Error" 
    ::= { cerentGenericV2Events 890 }
 
mismatchOfEquipmentAndAttributes  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "mismatch of Equipment and Attributes" 
    ::= { cerentGenericV2Events 900 }
 
watchdogTimerTimeout                
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "watchdog Timer Timeout" 
    ::= { cerentGenericV2Events 910 }
 
softwareFaultOrFailure             
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "software Fault or failure" 
    ::= { cerentGenericV2Events 920 }
 
softwareFaultDataIntegrityFault   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "software Fault -  Data integrity fault :
                 The newly added provisioning or hardware has 
                 caused the database to grow beyond its limit. 
                 That is, the newly added object(s) in the system 
                 has(have) enough memory to exist onboard but
                 too large to be saved in the database." 
    ::= { cerentGenericV2Events 930 }
 
programFailure       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "program failure " 
    ::= { cerentGenericV2Events 940 }
 
controlEquipmentFailure            
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "control Equipment failure" 
    ::= { cerentGenericV2Events 950 }
 
controlEquipmentPrimaryNonVolatileBackupMemoryFailure    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "control Equipment Primary non volatile Backup Memory failure" 
    ::= { cerentGenericV2Events 960 }
 
controlEquipmentSecondaryNonVolatileBackupMemoryFailure  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "control Equipment Secondary non volatile Backup Memory failure" 
    ::= { cerentGenericV2Events 970 }
 
controlEquipmentControlBusFailure           
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "control Equipment Control Bus failure" 
    ::= { cerentGenericV2Events 980 }
 
controlEquipmentControlBus1Failure         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "control Equipment Control Bus 1 failure" 
    ::= { cerentGenericV2Events 990 }
 
controlEquipmentControlBus2Failure         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "control Equipment Control Bus 2 failure" 
    ::= { cerentGenericV2Events 1000 }

communicationFailureTCCAToShelfSLOT1  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 1"
    ::= { cerentGenericV2Events 1010 }

communicationFailureTCCAToShelfSLOT2       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 2" 
    ::= { cerentGenericV2Events 1020 }

communicationFailureTCCAToShelfSLOT3     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 3" 
    ::= { cerentGenericV2Events 1030 }

communicationFailureTCCAToShelfSLOT4      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 4" 
    ::= { cerentGenericV2Events 1040 }

communicationFailureTCCAToShelfSLOT5
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 5" 
    ::= { cerentGenericV2Events 1050 }

communicationFailureTCCAToShelfSLOT6       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 6" 
    ::= { cerentGenericV2Events 1060 }

communicationFailureTCCAToShelfSLOT7       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 7 " 
    ::= { cerentGenericV2Events 1070 }

communicationFailureTCCAToShelfSLOT8       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 8" 
    ::= { cerentGenericV2Events 1080 }

communicationFailureTCCAToShelfSLOT9       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 9" 
    ::= { cerentGenericV2Events 1090 }

communicationFailureTCCAToShelfSLOT10      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 10" 
    ::= { cerentGenericV2Events 1100 }

communicationFailureTCCAToShelfSLOT11      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 11" 
    ::= { cerentGenericV2Events 1110 }

communicationFailureTCCAToShelfSLOT12      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 12" 
    ::= { cerentGenericV2Events 1120 }

communicationFailureTCCAToShelfSLOT13      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 13" 
    ::= { cerentGenericV2Events 1130 }

communicationFailureTCCAToShelfSLOT14      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 14" 
    ::= { cerentGenericV2Events 1140 }

communicationFailureTCCAToShelfSLOT15      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 15" 
    ::= { cerentGenericV2Events 1150 }

communicationFailureTCCAToShelfSLOT16      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 16" 
    ::= { cerentGenericV2Events 1160 }

communicationFailureTCCAToShelfSLOT17      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC A to Shelf SLOT 17 " 
    ::= { cerentGenericV2Events 1170 }

communicationFailureTCCPAToTCCJAprocessor  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCCP A to TCCJ A processor" 
    ::= { cerentGenericV2Events 1180 }

communicationFailureTCCBToShelfSLOT1       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 1 " 
    ::= { cerentGenericV2Events 1190 }

communicationFailureTCCBToShelfSLOT2       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 2" 
    ::= { cerentGenericV2Events 1200 }

communicationFailureTCCBToShelfSLOT3       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 3" 
    ::= { cerentGenericV2Events 1210 }

communicationFailureTCCBToShelfSLOT4       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 4" 
    ::= { cerentGenericV2Events 1220 }

communicationFailureTCCBToShelfSLOT5       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 5" 
    ::= { cerentGenericV2Events 1230 }

communicationFailureTCCBToShelfSLOT6       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 6" 
    ::= { cerentGenericV2Events 1240 }

communicationFailureTCCBToShelfSLOT7       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 7" 
    ::= { cerentGenericV2Events 1250 }

communicationFailureTCCBToShelfSLOT8       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 8" 
    ::= { cerentGenericV2Events 1260 }

communicationFailureTCCBToShelfSLOT9       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 9" 
    ::= { cerentGenericV2Events 1270 }

communicationFailureTCCBToShelfSLOT10      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 10" 
    ::= { cerentGenericV2Events 1280 }

communicationFailureTCCBToShelfSLOT11      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 11" 
    ::= { cerentGenericV2Events 1290 }

communicationFailureTCCBToShelfSLOT12      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 12" 
    ::= { cerentGenericV2Events 1300 }

communicationFailureTCCBToShelfSLOT13      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 13" 
    ::= { cerentGenericV2Events 1310 }

communicationFailureTCCBToShelfSLOT14      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 14" 
    ::= { cerentGenericV2Events 1320 }

communicationFailureTCCBToShelfSLOT15      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 15" 
    ::= { cerentGenericV2Events 1330 }

communicationFailureTCCBToShelfSLOT16      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 16" 
    ::= { cerentGenericV2Events 1340 }

communicationFailureTCCBToShelfSLOT17      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCC B to Shelf SLOT 17" 
    ::= { cerentGenericV2Events 1350 }

communicationFailureTCCPBToTCCJAprocessor  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "communication failure TCCP B to TCCJ A processor" 
    ::= { cerentGenericV2Events 1360 }

controlEquipmentControlCommunicationsEquipmentFailure  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "control Equipment Control Communications equipment failure" 
    ::= { cerentGenericV2Events 1370 }

controlEquipmentControlProcessorFailure 
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "control Equipment Control processor failure" 
    ::= { cerentGenericV2Events 1380 }

controlEquipmentWorkingMemoryFailure    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "control Equipment Working memory failure" 
    ::= { cerentGenericV2Events 1390 }

interconnectionEquipmentFailure         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure" 
    ::= { cerentGenericV2Events 1400 }

interconnectionEquipmentFailurePayloadBus1Working               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 1 Working" 
    ::= { cerentGenericV2Events 1410 }

interconnectionEquipmentFailurePayloadBus2Working               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 2 Working" 
    ::= { cerentGenericV2Events 1420 }

interconnectionEquipmentFailurePayloadBus3Working               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 3 Working" 
    ::= { cerentGenericV2Events 1430 }

interconnectionEquipmentFailurePayloadBus4Working               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 4 Working" 
    ::= { cerentGenericV2Events 1440 }

interconnectionEquipmentFailurePayloadBus5Working               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 5 Working" 
    ::= { cerentGenericV2Events 1450 }

interconnectionEquipmentFailurePayloadBus6Working               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 6 Working" 
    ::= { cerentGenericV2Events 1460 }

interconnectionEquipmentFailurePayloadBus7Working               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 7 Working" 
    ::= { cerentGenericV2Events 1470 }

interconnectionEquipmentFailurePayloadBus8Working               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 8 Working" 
    ::= { cerentGenericV2Events 1480 }

interconnectionEquipmentFailurePayloadBus9Working               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 9 Working" 
    ::= { cerentGenericV2Events 1490 }

interconnectionEquipmentFailurePayloadBus10Working              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 10 Working" 
    ::= { cerentGenericV2Events 1500 }

interconnectionEquipmentFailurePayloadBus11Working              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 11 Working" 
    ::= { cerentGenericV2Events 1510 }

interconnectionEquipmentFailurePayloadBus12Working              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 12 Working" 
    ::= { cerentGenericV2Events 1520 }

interconnectionEquipmentFailurePayloadBus1Protect              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 1 Protect" 
    ::= { cerentGenericV2Events 1530 }

interconnectionEquipmentFailurePayloadBus2Protect              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 2 Protect" 
    ::= { cerentGenericV2Events 1540 }

interconnectionEquipmentFailurePayloadBus3Protect              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 3 Protect" 
    ::= { cerentGenericV2Events 1550 }

interconnectionEquipmentFailurePayloadBus4Protect              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 4 Protect" 
    ::= { cerentGenericV2Events 1560 }

interconnectionEquipmentFailurePayloadBus5Protect              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 5 Protect" 
    ::= { cerentGenericV2Events 1570 }

interconnectionEquipmentFailurePayloadBus6Protect              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 6 Protect" 
    ::= { cerentGenericV2Events 1580 }

interconnectionEquipmentFailurePayloadBus7Protect              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 7 Protect" 
    ::= { cerentGenericV2Events 1590 }

interconnectionEquipmentFailurePayloadBus8Protect              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 8 Protect" 
    ::= { cerentGenericV2Events 1600 }

interconnectionEquipmentFailurePayloadBus9Protect              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 9 Protect" 
    ::= { cerentGenericV2Events 1610 }

interconnectionEquipmentFailurePayloadBus10Protect             
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 10 Protect" 
    ::= { cerentGenericV2Events 1620 }

interconnectionEquipmentFailurePayloadBus11Protect             
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 11 Protect" 
    ::= { cerentGenericV2Events 1630 }

interconnectionEquipmentFailurePayloadBus12Protect             
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Equipment failure Payload Bus 12 Protect" 
    ::= { cerentGenericV2Events 1640 }

interconnectionEqptTimeSlotInterchangeEqptFailure              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "interconnection Eqpt Time slot interchange eqpt failure" 
    ::= { cerentGenericV2Events 1650 }

criticalAlarmCausedByEquipmentFailure           
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "critical alarm caused by equipment failure" 
    ::= { cerentGenericV2Events 1660 }

equipmentFailureHighTemperature        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "equipment failure High temperature" 
    ::= { cerentGenericV2Events 1670 }

equipmentFailureInvalidMACAddress     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "equipment failure Invalid MAC Address" 
    ::= { cerentGenericV2Events 1680 }

equipmentFailureBoardFailure           
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "equipment failure Board Failure" 
    ::= { cerentGenericV2Events 1690 }

equipmentFailureDiagnosticsFailure     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "equipment failure Diagnostics Failure" 
    ::= { cerentGenericV2Events 1700 }

equipmentFailureMediumAccessControl   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "equipment failure Medium Access Control" 
    ::= { cerentGenericV2Events 1710 }

facilityTerminationEquipmentFailure    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "facility Termination equipment failure" 
    ::= { cerentGenericV2Events 1720 }

facilityTerminationEquipmentAutomaticLaserShutdown              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "facility Termination Equipment Automatic Laser Shutdown" 
    ::= { cerentGenericV2Events 1730 }

failureToReleaseFromProtection        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "failure To Release from protection" 
    ::= { cerentGenericV2Events 1740 }

facilityTerminationEquipmentReceiverFailure      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "facility Termination equipment Receiver failure" 
    ::= { cerentGenericV2Events 1750 }

facilityTerminationEquipmentTransmitFailure      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "facility Termination equipment Transmit failure" 
    ::= { cerentGenericV2Events 1760 }

facilityTerminationEquipmentReceiverMissing      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName,
      cerentGenericAlarmObjectName
    }
    STATUS current 
    DESCRIPTION "facility Termination equipment Receiver missing" 
    ::= { cerentGenericV2Events 1770 }

facilityTerminationEquipmentTransmitterMissing   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "facility Termination equipment Transmitter missing" 
    ::= { cerentGenericV2Events 1780 }

failureToSwitchToProtection           
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "failure To Switch to protection" 
    ::= { cerentGenericV2Events 1790 }

failureToSwitchToProtectionRing      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "failure To Switch to protection Ring" 
    ::= { cerentGenericV2Events 1800 }

failureToSwitchToProtectionSpan      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "failure To Switch to protection Span" 
    ::= { cerentGenericV2Events 1810 }

failureToSwitchToProtectionPath      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "failure to Switch to protection Path" 
    ::= { cerentGenericV2Events 1820 }

failureOfCoolingFanTray               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "failure of cooling fan tray" 
    ::= { cerentGenericV2Events 1830 }

equipmentUnitPlugIn    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "equipment unit plug in" 
    ::= { cerentGenericV2Events 1840 }

powerFailureDetectedInternalToNE     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "power failure detected internal to NE" 
    ::= { cerentGenericV2Events 1850 }

powerFailureFuseAlarm  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "power failure Fuse Alarm" 
    ::= { cerentGenericV2Events 1860 }

synchronizationUnitFailure              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "synchronization unit failure" 
    ::= { cerentGenericV2Events 1870 }

synchronizationSwitchingEquipmentFailure          
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "synchronization switching Equipment failure" 
    ::= { cerentGenericV2Events 1880 }

equipmentUnitUnplug    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "equipment unit un plug" 
    ::= { cerentGenericV2Events 1890 }

loopback                 
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loop back" 
    ::= { cerentGenericV2Events 1900 }

loopbackDueToFEACCommandDS1          
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loopback due to FEAC command DS1" 
    ::= { cerentGenericV2Events 1910 }

loopbackCommandSentToFarEndDS1      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loopback Command sent to Far End DS1" 
    ::= { cerentGenericV2Events 1920 }

loopbackDueToFEACCommandDS3          
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loopback due to FEAC command DS3" 
    ::= { cerentGenericV2Events 1930 }

loopbackCommandSentToFarEndDS3      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loopback Command sent to Far End DS3" 
    ::= { cerentGenericV2Events 1940 }

loopbackDueToFarEndCommandDS2       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loopback due to Far End Command DS2" 
    ::= { cerentGenericV2Events 1950 }

loopbackCommandSentToFarEndDS2      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loopback Command sent to Far End DS2" 
    ::= { cerentGenericV2Events 1960 }

loopbackFacility        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loop back facility" 
    ::= { cerentGenericV2Events 1970 }

loopbackNetwork         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loop back Network" 
    ::= { cerentGenericV2Events 1980 }

loopbackTerminal        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "loop back Terminal" 
    ::= { cerentGenericV2Events 1990 }

manuallyCausedAbnormalCondition        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manually caused abnormal condition" 
    ::= { cerentGenericV2Events 2000 }

newRootDiscoveredInBridgedNetwork    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "new Root discovered in bridged network" 
    ::= { cerentGenericV2Events 2010 }

topologyChangeDiscoveredInBridgedNetwork        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "topology change discovered in bridged network" 
    ::= { cerentGenericV2Events 2020 }

normalCondition          
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "normal condition" 
    ::= { cerentGenericV2Events 2030 }

embeddedOperationsChannelFailureLinkDown        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "embedded Operations Channel failure link down" 
    ::= { cerentGenericV2Events 2040 }

peerStateMismatch       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "peer state mismatch" 
    ::= { cerentGenericV2Events 2050 }

proceduralError          
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "procedural Error" 
    ::= { cerentGenericV2Events 2060 }

proceduralErrorImproperRemoval         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "procedural Error Improper Removal" 
    ::= { cerentGenericV2Events 2070 }

proceduralErrorDuplicateNodeID        
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "procedural Error Duplicate Node ID" 
    ::= { cerentGenericV2Events 2080 }

proceduralErrorBLSROutOfSync         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "procedural Error BLSR out of sync" 
    ::= { cerentGenericV2Events 2090 }

resynchronizedBLSRTables
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "BLSR tables resynchronized" 
    ::= { cerentGenericV2Events 2100 }

protectionUnitNotAvailable             
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "protection unit not available" 
    ::= { cerentGenericV2Events 2110 }

performanceMonitorThresholdCrossingAlert         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "performance Monitor Threshold Crossing Alert" 
    ::= { cerentGenericV2Events 2120 }

occurrenceOfAProtectionSwitchingEvent           
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "occurrence of a protection switching event" 
    ::= { cerentGenericV2Events 2130 }

recoveryOrServiceProtectionActionHasBeenInitiated             
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "recovery or service protection action has been initiated" 
    ::= { cerentGenericV2Events 2140 }

automaticSystemReset    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "automatic system Reset" 
    ::= { cerentGenericV2Events 2150 }

automacticUPSRSwitchCausedByAIS      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "automactic UPSR switch caused by AIS" 
    ::= { cerentGenericV2Events 2160 }

automacticUPSRSwitchCausedByLOP      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "automactic UPSR switch caused by Lop" 
    ::= { cerentGenericV2Events 2170 }

automacticUPSRSwitchCausedByUneq     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "automactic UPSR switch caused by Uneq" 
    ::= { cerentGenericV2Events 2180 }

automacticUPSRSwitchCausedByPDI      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "automactic UPSR switch caused by PDI" 
    ::= { cerentGenericV2Events 2190 }

automacticUPSRSwitchCausedBySfber    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "automactic UPSR switch caused by Sfber" 
    ::= { cerentGenericV2Events 2200 }

automacticUPSRSwitchCausedBySdber    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "automactic UPSR switch caused by Sdber"
    ::= { cerentGenericV2Events 2210 }

coldRestart              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "cold Restart" 
    ::= { cerentGenericV2Events 2220 }

workingFacilityOrEqptForcedSwitchedToWorking       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "working facility or eqpt forced switched to working" 
    ::= { cerentGenericV2Events 2230 }

workingFacilityOrEqptForcedSwitchedToWorkingRing  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "working facility or eqpt forced switched to working Ring" 
    ::= { cerentGenericV2Events 2240 }

workingFacilityOrEqptForcedSwitchedToWorkingSpan  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "working facility or eqpt forced switched to working Span" 
    ::= { cerentGenericV2Events 2250 }

workingFacilityOrEqptForcedSwitchedProtectionUnit  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "working facility or eqpt forced switched protection unit" 
    ::= { cerentGenericV2Events 2260 }

workingFacilityOrEqptForcedSwitchedProtectionUnitRing  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "working facility or eqpt forced switched protection unit Ring" 
    ::= { cerentGenericV2Events 2270 }

workingFacilityOrEqptForcedSwitchedProtectionUnitSpan  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "working facility or eqpt forced switched protection unit Span" 
    ::= { cerentGenericV2Events 2280 }

workingFacilityOrEqptForcedSwitchedProtectionUnitPath  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "working facility or eqpt forced switched protection unit Path" 
    ::= { cerentGenericV2Events 2290 }

initializationInitiated      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "initialization initiated" 
    ::= { cerentGenericV2Events 2300 }

lockoutOfProtection         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "lockout of Protection" 
    ::= { cerentGenericV2Events 2310 }

lockoutOfProtectionRing    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "lockout of Protection Ring" 
    ::= { cerentGenericV2Events 2320 }

lockoutOfProtectionSpan    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "lockout of Protection Span" 
    ::= { cerentGenericV2Events 2330 }

lockoutOfProtectionPath    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "lockout of Protection Path" 
    ::= { cerentGenericV2Events 2340 }

lockoutOfWorking            
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "lockout of working" 
    ::= { cerentGenericV2Events 2350 }

lockoutOfWorkingRing       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "lockout of working Ring" 
    ::= { cerentGenericV2Events 2360 }

lockoutOfWorkingSpan       
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "lockout of working Span" 
    ::= { cerentGenericV2Events 2370 }

manualSystemReset           
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manual system Reset" 
    ::= { cerentGenericV2Events 2380 }

manualSynchronizationSwitchToInternalClock     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manual synchronization switch to internal clock" 
    ::= { cerentGenericV2Events 2390 }

manualSynchronizationSwitchToPrimaryRefernce   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manual synchronization Switch To Primary refernce" 
    ::= { cerentGenericV2Events 2400 }

manualSynchronizationSwitchToSecondRefernce    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manual synchronization Switch To Second refernce" 
    ::= { cerentGenericV2Events 2410 }

manualSynchronizationSwitchToThirdRefernce     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manual synchronization Switch To Third refernce" 
    ::= { cerentGenericV2Events 2420 }

manualSynchronizationSwitchToFourthRefernce    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manual synchronization Switch To Fourth refernce" 
    ::= { cerentGenericV2Events 2430 }

manualSynchronizationSwitchToFifthRefernce     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manual synchronization Switch To Fifth refernce" 
    ::= { cerentGenericV2Events 2440 }

manualSynchronizationSwitchToSixthRefernce     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manual synchronization Switch To Sixth refernce" 
    ::= { cerentGenericV2Events 2450 }

manualSwitchOfWorkingFacilityOrEqptToProtectionRing    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manualSwitch of working facility or eqpt to protection Ring" 
    ::= { cerentGenericV2Events 2460 }

manualSwitchOfWorkingFacilityOrEqptToProtectionSpan    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manualSwitch of working facility or eqpt to protection Span" 
    ::= { cerentGenericV2Events 2470 }

manualSwitchOfWorkingFacilityOrEqptToProtection         
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manualSwitch of working facility or eqpt to protection" 
    ::= { cerentGenericV2Events 2480 }

manualSwitchOfWorkingFacilityOrEqptToProtectionUnit    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manualSwitch of Working facility or eqpt to Protection unit" 
    ::= { cerentGenericV2Events 2490 }

workingFacilityOrEqptManualSwitchToProtectionUnitRing  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "working facility or eqpt manualSwitch to Protection unit Ring" 
    ::= { cerentGenericV2Events 2500 }

workingFacilityOrEqptManualSwitchToProtectionUnitSpan  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "working facility or eqpt manualSwitch to Protection unit Span" 
    ::= { cerentGenericV2Events 2510 }

manualSwitchOfWorkingFacilityOrEqptToProtectionPath    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manualSwitch of working facility or eqpt to Protection Path" 
    ::= { cerentGenericV2Events 2520 }

powerFailureRestart          
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "power failure Restart" 
    ::= { cerentGenericV2Events 2530 }

ringIsSquelchingTraffic     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "ring is squelching traffic" 
    ::= { cerentGenericV2Events 2540 }

softwareDownloadInProgress  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "software download in progress"
    ::= { cerentGenericV2Events 2550 }

synchronizationSwitchToInternalClock    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "synchronization Switch To Internal clock" 
    ::= { cerentGenericV2Events 2560 }

synchronizationSwitchToPrimaryRefernce  
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "synchronization Switch To Primary refernce" 
    ::= { cerentGenericV2Events 2570 }

synchronizationSwitchToSecondRefernce   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "synchronization Switch To Second refernce" 
    ::= { cerentGenericV2Events 2580 }

synchronizationSwitchToThirdRefernce    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "synchronization Switch To Third refernce" 
    ::= { cerentGenericV2Events 2590 }

synchronizationSwitchToFourthRefernce   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "synchronization Switch To Fourth refernce" 
    ::= { cerentGenericV2Events 2600 }

synchronizationSwitchToFifthRefernce    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "synchronization Switch To Fifth refernce" 
    ::= { cerentGenericV2Events 2610 }

synchronizationSwitchToSixthRefernce    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "synchronization Switch To Sixth refernce" 
    ::= { cerentGenericV2Events 2620 }

systemReboot    
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "system reboot" 
    ::= { cerentGenericV2Events 2630 }

workingFacilityOrEquipmentSwitchedBackToWorking      
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "working facility or equipment switched back to working" 
    ::= { cerentGenericV2Events 2640 }

workingFacilityOrEquipmentSwitchedToProtectionUnit   
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "working facility or equipment switched to protection unit" 
    ::= { cerentGenericV2Events 2650 }

warmRestart     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "warm Restart" 
    ::= { cerentGenericV2Events 2660 }

isInWaitToRestoreStateSONETLine     
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "SONET line is in Wait To Restore state " 
    ::= { cerentGenericV2Events 2670 }

manualSwitchRequestOnFacilityOrEquipment              
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "manual switch request on facility or equipment" 
    ::= { cerentGenericV2Events 2680 }

forceSwitchRequestOnFacilityOrEquipment               
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "force switch request on facility or equipment" 
    ::= { cerentGenericV2Events 2690 }

lockoutSwitchRequestOnFacilityOrEquipment             
  NOTIFICATION-TYPE 
    OBJECTS { 
      cerentNodeTime, 
      cerentGenericAlarmState, 
      cerentGenericAlarmObjectType, 
      cerentGenericAlarmObjectIndex,
      cerentGenericAlarmSlotNumber, 
      cerentGenericAlarmPortNumber, 
      cerentGenericAlarmLineNumber,
      cerentGenericAlarmObjectName
    }
    STATUS current 
    DESCRIPTION "lockout switch request on facility or equipment" 
    ::= { cerentGenericV2Events 2700 } 

rmonHistoriesAndAlarmsReset
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "RMON histories and alarms have been reset due to chipset reboot"
    ::= { cerentGenericV2Events 2710 }

rmonThresholdCrossingAlarm
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
   }
   STATUS current
    DESCRIPTION "Crossing of Falling/Rising Threshold detected"
    ::= { cerentGenericV2Events 2720 }

traceIdentifierMismatchSTSPath
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "STS path trace identifier mismatch"

    ::= { cerentGenericV2Events 2800 }

nodePowerFailureAtConnectorA
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "NE power failure at connector A"

    ::= { cerentGenericV2Events 2810 }

nodePowerFailureAtConnectorB
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "NE power failure at connector B"

    ::= { cerentGenericV2Events 2820 }

freeMemoryOnCardVeryLow
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Free memory on the card is very low"
    ::= { cerentGenericV2Events 2830 }

freeMemoryOnCardAlmostGone
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Free memory on the card is almost gone"
    ::= { cerentGenericV2Events 2840 }

exerciseRing
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Exercise Ring."

    ::= { cerentGenericV2Events 2850 }

exerciseSpan
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Exercise Span."

    ::= { cerentGenericV2Events 2860 }

squelchingPath
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Squelching Path: "

    ::= { cerentGenericV2Events 2870 }

extraTrafficPreemptted
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Extra Traffic Preempted."

    ::= { cerentGenericV2Events 2880 }

farEndLockoutOfWorkingRing
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End Lockout of working - Ring."

    ::= { cerentGenericV2Events 2890 }

farEndLockoutOfWorkingSpan
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End Lockout of working - Span."

    ::= { cerentGenericV2Events 2900 }

farEndLockoutOfProtectionRing
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End Lockout of Protection - Ring."

    ::= { cerentGenericV2Events 2910 }

farEndLockoutOfProtectionAllSpans
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End Lockout of Protection - All Spans."

    ::= { cerentGenericV2Events 2920 }

farEndWorkingFacilityForcedToSwitchToProtectionUnitRing
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End Working facility forced to switch to protection unit - Ring."

    ::= { cerentGenericV2Events 2930 }

farEndWorkingFacilityForcedToSwitchToProtectionUnitSpan
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End Working facility forced to switch to protection unit - Span."

    ::= { cerentGenericV2Events 2940 }

farEndManualSwitchOfWorkingFacilityToProtectionUnitRing
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End Manual Switch of Working facility to Protection unit - Ring."

    ::= { cerentGenericV2Events 2950 }

farEndManualSwitchOfWorkingFacilityToProtectionUnitSpan
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End Manual Switch of Working facility to Protection unit - Span."

    ::= { cerentGenericV2Events 2960 }

farEndExerciseRing
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End Exercise Ring."

    ::= { cerentGenericV2Events 2970 }

farEndExerciseSpan
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End Exercise Span."

    ::= { cerentGenericV2Events 2980 }

farEndBERThresholdPassedForSignalFailureRing
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End BER threshold passed for Signal Failure - Ring."

    ::= { cerentGenericV2Events 2990 }

farEndBERThresholdPassedForSignalFailureSpan
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End BER threshold passed for Signal Failure - Span."

    ::= { cerentGenericV2Events 3000 }

farEndBERThresholdPassedForSignalDegradeRing
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End BER threshold passed for Signal Degrade - Ring."

    ::= { cerentGenericV2Events 3010 }

farEndBERThresholdPassedForSignalDegradeSpan
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far End BER threshold passed for Signal Degrade - Span."

    ::= { cerentGenericV2Events 3020 }

channelFarEndProtectionLineSignalDegradeAPS
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "APS Channel - Far End Protection Line Signal Degrade."

    ::= { cerentGenericV2Events 3030 }

ringSwitchIsActiveOnTheEastSide
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Ring Switch is active on the East Side."

    ::= { cerentGenericV2Events 3040 }

ringSwitchIsActiveOnTheWestSide
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Ring Switch is active on the West Side."

    ::= { cerentGenericV2Events 3050 }

spanSwitchIsActiveOnTheEastSide
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Span Switch is active on the East Side."

    ::= { cerentGenericV2Events 3060 }

spanSwitchIsActiveOnTheWestSide
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Span Switch is active on the West Side."

    ::= { cerentGenericV2Events 3070 }

uniDirectionalFullPassThroughIsActive
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Uni-directional Full Pass Through is active."

    ::= { cerentGenericV2Events 3080 }

biDirectionalFullPassThroughIsActive
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Bi-directional Full Pass Through is active."

    ::= { cerentGenericV2Events 3090 }

kBytePassThroughIsActive
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "K Bytes Pass Through is active."

    ::= { cerentGenericV2Events 3100 }

ringIsSegmented
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Ring is Segmented."

    ::= { cerentGenericV2Events 3110 }

ringTopologyIsUnderConstruction
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Ring Topology is under construction."

    ::= { cerentGenericV2Events 3120 }

lockoutOfProtectionAllSpans
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Lockout of Protection - All Spans."

    ::= { cerentGenericV2Events 3130 }

farEndOfFiberIsProvisionedWithDifferentRingID
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Far end of fiber is provisioned with different ring ID"

    ::= { cerentGenericV2Events 3140 }

bothEndsOfFiberProvisionedAsEastOrBothAsWest    
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Both ends of fiber provisioned as East, or both as West"

    ::= { cerentGenericV2Events 3150 }

invalidLoginSeeAuditTrail                 
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Security: invalid login (see Audit Trail)"

    ::= { cerentGenericV2Events 3160 }

autonomousMessagesInhibited
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Autonomous messages inhibited"

    ::= { cerentGenericV2Events 3170 }

trafficStormLANtemporarilyDisabled
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Traffic storm on LAN. LAN temporarily disabled."

    ::= { cerentGenericV2Events 3180 }

tl1ReptDbchgMessagesInhibited
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "REPT^DBCHG messages of TL1 inhibited"

    ::= { cerentGenericV2Events 3190 }

userIdHasExpired
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Security: user ID has expired"

    ::= { cerentGenericV2Events 3200 }

partialFanFailure
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Partial Fan Failure"

    ::= { cerentGenericV2Events 3210 }
forceSwitchRequestOnRing
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Force switch request on Ring"

    ::= { cerentGenericV2Events 3220 }

forceSwitchRequestOnSpan
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Force switch request on Span"

    ::= { cerentGenericV2Events 3230 }

lockoutSwitchRequestOnRing
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Lockout switch request on Ring"

    ::= { cerentGenericV2Events 3240 }

lockoutSwitchRequestOnSpan
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Lockout switch request on Span"

    ::= { cerentGenericV2Events 3250 }

manualSwitchRequestOnRing
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Manual switch request on Ring"

    ::= { cerentGenericV2Events 3260 }

manualSwitchRequestOnSpan
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Manual switch request on Span"

    ::= { cerentGenericV2Events 3270 }

communicationFailurePeerToPeerSlotControlBusA
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Peer to Peer Slot communication failure - Control Bus A"

    ::= { cerentGenericV2Events 3280 }

communicationFailurePeerToPeerSlotControlBusB
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Peer to Peer Slot communication failure - Control Bus B"

    ::= { cerentGenericV2Events 3290 }

communicationFailureTCCAToShelfSlot
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "TCC A to Shelf Slot communication failure"

    ::= { cerentGenericV2Events 3300 }

communicationFailureTCCBToShelfSlot
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "TCC B to Shelf Slot communication failure"

    ::= { cerentGenericV2Events 3310 }

interconnectionEquipmentFailureWorkingPayloadBus
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Interconnection Equipment Failure - Working Payload Bus"

    ::= { cerentGenericV2Events 3320 }

interconnectionEquipmentFailureProtectPayloadBus
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Interconnection Equipment Failure - Protect Payload Bus"

    ::= { cerentGenericV2Events 3330 }

inhibitSwitchToProtectRequestInEffectOnEquipment
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Inhibit Switch to Protect Request in effect on equipment"
    ::= { cerentGenericV2Events 3340 }

inhibitSwitchToWorkingRequestInEffectOnEquipment
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "Inhibit Switch to Working Request in effect on equipment"
    ::= { cerentGenericV2Events 3350 }

passedBERThresholdForSignalDegradeLine
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "BER Threshold exceeded for Signal Degrade - Line"
    ::= { cerentGenericV2Events 3360 }

passedBERThresholdForSignalDegradePath
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "BER Threshold exceeded for Signal Degrade - Path"
    ::= { cerentGenericV2Events 3370 }

passedBERThresholdForSignalFailLine
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "BER Threshold exceeded for Signal Fail - Line"
    ::= { cerentGenericV2Events 3380 }

passedBERThresholdForSignalFailPath
  NOTIFICATION-TYPE
    OBJECTS {
      cerentNodeTime,
      cerentGenericAlarmState,
      cerentGenericAlarmObjectType,
      cerentGenericAlarmObjectIndex,
      cerentGenericAlarmSlotNumber,
      cerentGenericAlarmPortNumber,
      cerentGenericAlarmLineNumber,
      cerentGenericAlarmObjectName
    }
    STATUS current
    DESCRIPTION "BER Threshold exceeded for Signal Fail - Path"
   ::= { cerentGenericV2Events 3390 }

nodeGroup OBJECT-GROUP
        OBJECTS { 
          cerentGenericSoftwareVersion }
        STATUS current
        DESCRIPTION
          "The group for node related objects"
        ::= { cerentGenericGroups 10 }
        
alarmGroup OBJECT-GROUP
        OBJECTS {
          cerentGenericAlarmCount,
          cerentGenericAlarmObjectIndex,
          cerentGenericAlarmObjectType,
          cerentGenericAlarmSlotNumber,
          cerentGenericAlarmPortNumber,
          cerentGenericAlarmLineNumber,
          cerentGenericAlarmType,
          cerentGenericAlarmState,
          cerentGenericAlarmTimeStamp,
          cerentGenericAlarmObjectName
        }
        STATUS current
        DESCRIPTION
          "The group for node related objects"
        ::= { cerentGenericGroups 20 }
        
eventGroup NOTIFICATION-GROUP
     NOTIFICATIONS {
       alarmUnknown,
       alarmCutoffIsInManualMode,
       failureDetectedExternalToTheNE,
       externalError,
       excessiveSwitching,
       terminationFailureSDCC,
       incomingFailureCondition,
       alarmIndicationSignal,
       alarmIndicationSignalLine,
       alarmIndicationSignalPath,
       alarmIndicationSignalVT,
       channelFailureAPS,
       channelByteFailureAPS,
       channelProtectionSwitchingChannelMatchFailureAPS,
       channelAutomaticProtectionSwitchModeMismatchAPS,
       channelFarEndProtectionLineFailureAPS,
       channelBLSRInconsistentAPSCode,
       channelBLSRImproperAPSCodeAPS,
       channelBLSRNodeIdMismatchAPS,
       channelBLSRDefaultKAPS,
       channelBLSRConnectionLossAPS,
       bipolarViolation,
       carrierLossOnTheLAN,
       concatenationErrorSTS,
       excessCollisionsOnTheLAN,
       facilityCriticalAlarmCausedByDS3FacilityFailure,
       farEndAIS,
       farEndMultipleDS1LOSDetectedOnDS3,
       farEndDS1EqptFailNonServiceAffecting,
       farEndDS1EqptFailServiceAffecting,
       farEndSingleDS1LOS,
       farEndDS3EqptFailNonServiceAffecting,
       farEndDS3EqptFailServiceAffecting,
       farEndCmnEqptFailNonServiceAffecting,
       farEndIDLE,
       farEndLOS,
       farEndLOF,
       farEndBlockError,
       idleConditionDS3,
       lossOfFrame,
       lossOfPointer,
       lossOfPointerPath,
       lossOfPointerVT,
       lossOfSignal,
       outOfFrame,
       pathSelectorInabilityToSwitchToAValidSignal,
       remoteAlarmIndication,
       remoteFailureIndication,
       remoteFailureIndicationLine,
       remoteFailureIndicationPath,
       remoteFailureIndicationVT,
       facilityHasPassedBERThresholdForSignalDegrade,
       severelyErroredFrame,
       facilityHasPassedBERThresholdForSignalFailure,
       signalLabelMismatchFailuresSONET,
       signalLabelMismatchFailurePayloadDefectIndication,
       signalLabelMismatchFailurePayloadDefectIndicationPath,
       signalLabelMismatchFailurePayloadLabelMismatchPath,
       signalLabelMismatchFailurePayloadLabelMismatchVT,
       signalLabelMismatchFailureUnequippedPath,
       signalLabelMismatchFailureUnequippedVT,
       lossOfTimingOnSynchronizationLink,
       lossOfTimingOnAllSpecifiedSynchronizationLinks,
       lossOfTimingOnPrimarySynchronizationLink,
       lossOfTimingOnSecondarySynchronizationLink,
       lossOfTimingOnThirdSynchronizationLink,
       lossOfTimingOnFourthSynchronizationLink,
       lossOfTimingOnFifthSynchronizationLink,
       lossOfTimingOnSixthSynchronizationLink,
       failedToReceiveSynchronizationStatusMessage,
       synchronizationStatusMessagesAreDisabledOnThisInterface,
       primaryReferenceSourceStratum1Traceable,
       synchronizedTraceabilityUnknown,
       stratum2Traceable,
       transitNodeClockTraceable,
       stratum3ETraceable,
       stratum3Traceable,
       minimumClockTraceableSONET,
       stratum4Traceable,
       doNotUseForSynchronization,
       reservedForNetworkSynchronizationUse,
       outgoingFailureCondition,
       remoteDefectIndicationLine,
       remoteDefectIndicationPath,
       freeRunningSynchronizationMode,
       holdoverSynchronizationMode,
       fastStartSynchronizationMode,
       internalHardwareFaultOrFailure,
       errorInternalToTheNEDetected,
       internalMessageError,
       mismatchOfEquipmentAndAttributes,
       watchdogTimerTimeout,
       softwareFaultOrFailure,
       softwareFaultDataIntegrityFault,
       programFailure,
       controlEquipmentFailure,
       controlEquipmentPrimaryNonVolatileBackupMemoryFailure,
       controlEquipmentSecondaryNonVolatileBackupMemoryFailure,
       controlEquipmentControlBusFailure,
       controlEquipmentControlBus1Failure,
       controlEquipmentControlBus2Failure,
       communicationFailureTCCAToShelfSLOT1,
       communicationFailureTCCAToShelfSLOT2,
       communicationFailureTCCAToShelfSLOT3,
       communicationFailureTCCAToShelfSLOT4,
       communicationFailureTCCAToShelfSLOT5,
       communicationFailureTCCAToShelfSLOT6,
       communicationFailureTCCAToShelfSLOT7,
       communicationFailureTCCAToShelfSLOT8,
       communicationFailureTCCAToShelfSLOT9,
       communicationFailureTCCAToShelfSLOT10,
       communicationFailureTCCAToShelfSLOT11,
       communicationFailureTCCAToShelfSLOT12,
       communicationFailureTCCAToShelfSLOT13,
       communicationFailureTCCAToShelfSLOT14,
       communicationFailureTCCAToShelfSLOT15,
       communicationFailureTCCAToShelfSLOT16,
       communicationFailureTCCAToShelfSLOT17,
       communicationFailureTCCPAToTCCJAprocessor,
       communicationFailureTCCBToShelfSLOT1,
       communicationFailureTCCBToShelfSLOT2,
       communicationFailureTCCBToShelfSLOT3,
       communicationFailureTCCBToShelfSLOT4,
       communicationFailureTCCBToShelfSLOT5,
       communicationFailureTCCBToShelfSLOT6,
       communicationFailureTCCBToShelfSLOT7,
       communicationFailureTCCBToShelfSLOT8,
       communicationFailureTCCBToShelfSLOT9,
       communicationFailureTCCBToShelfSLOT10,
       communicationFailureTCCBToShelfSLOT11,
       communicationFailureTCCBToShelfSLOT12,
       communicationFailureTCCBToShelfSLOT13,
       communicationFailureTCCBToShelfSLOT14,
       communicationFailureTCCBToShelfSLOT15,
       communicationFailureTCCBToShelfSLOT16,
       communicationFailureTCCBToShelfSLOT17,
       communicationFailureTCCPBToTCCJAprocessor,
       controlEquipmentControlCommunicationsEquipmentFailure,
       controlEquipmentControlProcessorFailure,
       controlEquipmentWorkingMemoryFailure,
       interconnectionEquipmentFailure,
       interconnectionEquipmentFailurePayloadBus1Working,
       interconnectionEquipmentFailurePayloadBus2Working,
       interconnectionEquipmentFailurePayloadBus3Working,
       interconnectionEquipmentFailurePayloadBus4Working,
       interconnectionEquipmentFailurePayloadBus5Working,
       interconnectionEquipmentFailurePayloadBus6Working,
       interconnectionEquipmentFailurePayloadBus7Working,
       interconnectionEquipmentFailurePayloadBus8Working,
       interconnectionEquipmentFailurePayloadBus9Working,
       interconnectionEquipmentFailurePayloadBus10Working,
       interconnectionEquipmentFailurePayloadBus11Working,
       interconnectionEquipmentFailurePayloadBus12Working,
       interconnectionEquipmentFailurePayloadBus1Protect,
       interconnectionEquipmentFailurePayloadBus2Protect,
       interconnectionEquipmentFailurePayloadBus3Protect,
       interconnectionEquipmentFailurePayloadBus4Protect,
       interconnectionEquipmentFailurePayloadBus5Protect,
       interconnectionEquipmentFailurePayloadBus6Protect,
       interconnectionEquipmentFailurePayloadBus7Protect,
       interconnectionEquipmentFailurePayloadBus8Protect,
       interconnectionEquipmentFailurePayloadBus9Protect,
       interconnectionEquipmentFailurePayloadBus10Protect,
       interconnectionEquipmentFailurePayloadBus11Protect,
       interconnectionEquipmentFailurePayloadBus12Protect,
       interconnectionEqptTimeSlotInterchangeEqptFailure,
       criticalAlarmCausedByEquipmentFailure,
       equipmentFailureHighTemperature,
       equipmentFailureInvalidMACAddress,
       equipmentFailureBoardFailure,
       equipmentFailureDiagnosticsFailure,
       equipmentFailureMediumAccessControl,
       facilityTerminationEquipmentFailure,
       facilityTerminationEquipmentAutomaticLaserShutdown,
       failureToReleaseFromProtection,
       facilityTerminationEquipmentReceiverFailure,
       facilityTerminationEquipmentTransmitFailure,
       facilityTerminationEquipmentReceiverMissing,
       facilityTerminationEquipmentTransmitterMissing,
       failureToSwitchToProtection,
       failureToSwitchToProtectionRing,
       failureToSwitchToProtectionSpan,
       failureToSwitchToProtectionPath,
       failureOfCoolingFanTray,
       equipmentUnitPlugIn,
       powerFailureDetectedInternalToNE,
       powerFailureFuseAlarm,
       synchronizationUnitFailure,
       synchronizationSwitchingEquipmentFailure,
       equipmentUnitUnplug,
       loopback,
       loopbackDueToFEACCommandDS1,
       loopbackCommandSentToFarEndDS1,
       loopbackDueToFEACCommandDS3,
       loopbackCommandSentToFarEndDS3,
       loopbackDueToFarEndCommandDS2,
       loopbackCommandSentToFarEndDS2,
       loopbackFacility,
       loopbackNetwork,
       loopbackTerminal,
       manuallyCausedAbnormalCondition,
       newRootDiscoveredInBridgedNetwork,
       topologyChangeDiscoveredInBridgedNetwork,
       normalCondition,
       embeddedOperationsChannelFailureLinkDown,
       peerStateMismatch,
       proceduralError,
       proceduralErrorImproperRemoval,
       proceduralErrorDuplicateNodeID,
       proceduralErrorBLSROutOfSync,
       resynchronizedBLSRTables,
       protectionUnitNotAvailable,
       performanceMonitorThresholdCrossingAlert,
       occurrenceOfAProtectionSwitchingEvent,
       recoveryOrServiceProtectionActionHasBeenInitiated,
       automaticSystemReset,
       automacticUPSRSwitchCausedByAIS,
       automacticUPSRSwitchCausedByLOP,
       automacticUPSRSwitchCausedByUneq,
       automacticUPSRSwitchCausedByPDI,
       automacticUPSRSwitchCausedBySfber,
       automacticUPSRSwitchCausedBySdber,
       coldRestart,
       workingFacilityOrEqptForcedSwitchedToWorking,
       workingFacilityOrEqptForcedSwitchedToWorkingRing,
       workingFacilityOrEqptForcedSwitchedToWorkingSpan,
       workingFacilityOrEqptForcedSwitchedProtectionUnit,
       workingFacilityOrEqptForcedSwitchedProtectionUnitRing,
       workingFacilityOrEqptForcedSwitchedProtectionUnitSpan,
       workingFacilityOrEqptForcedSwitchedProtectionUnitPath,
       initializationInitiated,
       lockoutOfProtection,
       lockoutOfProtectionRing,
       lockoutOfProtectionSpan,
       lockoutOfProtectionPath,
       lockoutOfWorking,
       lockoutOfWorkingRing,
       lockoutOfWorkingSpan,
       manualSystemReset,
       manualSynchronizationSwitchToInternalClock,
       manualSynchronizationSwitchToPrimaryRefernce,
       manualSynchronizationSwitchToSecondRefernce,
       manualSynchronizationSwitchToThirdRefernce,
       manualSynchronizationSwitchToFourthRefernce,
       manualSynchronizationSwitchToFifthRefernce,
       manualSynchronizationSwitchToSixthRefernce,
       manualSwitchOfWorkingFacilityOrEqptToProtectionRing,
       manualSwitchOfWorkingFacilityOrEqptToProtectionSpan,
       manualSwitchOfWorkingFacilityOrEqptToProtection,
       manualSwitchOfWorkingFacilityOrEqptToProtectionUnit,
       workingFacilityOrEqptManualSwitchToProtectionUnitRing,
       workingFacilityOrEqptManualSwitchToProtectionUnitSpan,
       manualSwitchOfWorkingFacilityOrEqptToProtectionPath,
       powerFailureRestart,
       ringIsSquelchingTraffic,
       softwareDownloadInProgress,
       synchronizationSwitchToInternalClock,
       synchronizationSwitchToPrimaryRefernce,
       synchronizationSwitchToSecondRefernce,
       synchronizationSwitchToThirdRefernce,
       synchronizationSwitchToFourthRefernce,
       synchronizationSwitchToFifthRefernce,
       synchronizationSwitchToSixthRefernce,
       systemReboot,
       workingFacilityOrEquipmentSwitchedBackToWorking,
       workingFacilityOrEquipmentSwitchedToProtectionUnit,
       warmRestart,
       isInWaitToRestoreStateSONETLine,
       manualSwitchRequestOnFacilityOrEquipment,
       forceSwitchRequestOnFacilityOrEquipment,
       lockoutSwitchRequestOnFacilityOrEquipment,

       rmonHistoriesAndAlarmsReset,
       rmonThresholdCrossingAlarm,
       traceIdentifierMismatchSTSPath,
       nodePowerFailureAtConnectorA,
       nodePowerFailureAtConnectorB,
       freeMemoryOnCardVeryLow,
       freeMemoryOnCardAlmostGone,
       exerciseRing,
       exerciseSpan,
       squelchingPath,
       extraTrafficPreemptted,
       farEndLockoutOfWorkingRing,
       farEndLockoutOfWorkingSpan,
       farEndLockoutOfProtectionRing,
       farEndLockoutOfProtectionAllSpans,
       farEndWorkingFacilityForcedToSwitchToProtectionUnitRing,
       farEndWorkingFacilityForcedToSwitchToProtectionUnitSpan,
       farEndManualSwitchOfWorkingFacilityToProtectionUnitRing,
       farEndManualSwitchOfWorkingFacilityToProtectionUnitSpan,
       farEndExerciseRing,
       farEndExerciseSpan,
       farEndBERThresholdPassedForSignalFailureRing,
       farEndBERThresholdPassedForSignalFailureSpan,
       farEndBERThresholdPassedForSignalDegradeRing,
       farEndBERThresholdPassedForSignalDegradeSpan,
       channelFarEndProtectionLineSignalDegradeAPS,
       ringSwitchIsActiveOnTheEastSide,
       ringSwitchIsActiveOnTheWestSide,
       spanSwitchIsActiveOnTheEastSide,
       spanSwitchIsActiveOnTheWestSide,
       uniDirectionalFullPassThroughIsActive,
       biDirectionalFullPassThroughIsActive,
       kBytePassThroughIsActive,
       ringIsSegmented,
       ringTopologyIsUnderConstruction,
       lockoutOfProtectionAllSpans,
       farEndOfFiberIsProvisionedWithDifferentRingID,
       bothEndsOfFiberProvisionedAsEastOrBothAsWest,
       invalidLoginSeeAuditTrail,
       autonomousMessagesInhibited,
       trafficStormLANtemporarilyDisabled,
       tl1ReptDbchgMessagesInhibited,
       userIdHasExpired,
       partialFanFailure,
       forceSwitchRequestOnRing,
       forceSwitchRequestOnSpan,
       lockoutSwitchRequestOnRing,
       lockoutSwitchRequestOnSpan,
       manualSwitchRequestOnRing,
       manualSwitchRequestOnSpan,
       communicationFailurePeerToPeerSlotControlBusA,
       communicationFailurePeerToPeerSlotControlBusB,
       communicationFailureTCCAToShelfSlot,
       communicationFailureTCCBToShelfSlot,
       interconnectionEquipmentFailureWorkingPayloadBus,
       interconnectionEquipmentFailureProtectPayloadBus,
       inhibitSwitchToProtectRequestInEffectOnEquipment,
       inhibitSwitchToWorkingRequestInEffectOnEquipment,
       passedBERThresholdForSignalDegradeLine,
       passedBERThresholdForSignalFailLine,
       passedBERThresholdForSignalFailPath,
       passedBERThresholdForSignalDegradePath
     }
        STATUS current
        DESCRIPTION
          "The generic notifications for Cisco ONS 
           network device, ONS 15327 "
        ::= { cerentGenericGroups 30 }

-- This definition of group will move to a cerentCommon modules
-- eventually. 
        
cerentCommonGroup OBJECT-GROUP
        OBJECTS {
          cerentEnableNotification,
          cerentNodeTime,
          cerentNotificationsSent,
          cerentLastChangeTime   
          }
        STATUS current
        DESCRIPTION
          "The objects related to traps dispatch"
        ::= { cerentGenericGroups 40 }

-- the compliance specification for agent developers

cerentGenericBasicCompliance MODULE-COMPLIANCE
       STATUS current
       DESCRIPTION
         "The basic implementation requirements 
          for Cisco ONS network device, ONS 15327 "
       MODULE
         MANDATORY-GROUPS {
           nodeGroup,
           eventGroup
        }
       ::= { cerentCompliance 10 }
          
END
