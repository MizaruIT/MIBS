--
-- HUAWEI-ATM-CM-RM-MIB.MIB
-- MIB generated by MG-SOFT Visual MIB Builder Version 3.0 Build 253
-- Wednesday, September 26, 2007 at 16:42:17
--

--  HUAWEI-ATM-CM-RM-MIB.mib
-- MIB generated by MG-SOFT Visual MIB Builder Version 2.5 Build 225
-- Monday, Dec 10, 2003 at 08:03:05
-- 

	HUAWEI-ATM-CM-RM-MIB DEFINITIONS ::= BEGIN
 
		IMPORTS
			atmVclVpi, atmVclVci			
				FROM ATM-MIB			
			hwFrameIndex, hwSlotIndex, hwFrameIndex, hwSlotIndex			
				FROM HUAWEI-DEVICE-MIB			
			hwAtmCmRm			
				FROM HUAWEI-MIB			
			ifIndex			
				FROM IF-MIB			
			IpAddress, Integer32, OBJECT-TYPE			
				FROM SNMPv2-SMI			
			MacAddress			
				FROM SNMPv2-TC;
	
	
	
--
-- Node definitions
--
	
--  Node definitions
-- 
		-- 1.3.6.1.4.1.2011.5.10.1
		hwAtmPortBandWidthTable OBJECT-TYPE
			SYNTAX SEQUENCE OF HwAtmPortBandWidthEntry
			MAX-ACCESS not-accessible
			STATUS current
			DESCRIPTION
				"BandWidth Resource table"
			::= { hwAtmCmRm 1 }
		
		-- 1.3.6.1.4.1.2011.5.10.1.1
		hwAtmPortBandWidthEntry OBJECT-TYPE
			SYNTAX HwAtmPortBandWidthEntry
			MAX-ACCESS not-accessible
			STATUS current
			DESCRIPTION
				"BandWidth Resource table"
			INDEX { ifIndex }
			::= { hwAtmPortBandWidthTable 1 }
		
		HwAtmPortBandWidthEntry ::=
			SEQUENCE { 
				hwAtmPortBandWidthValue
					INTEGER
			 }

		-- 1.3.6.1.4.1.2011.5.10.1.1.1
		hwAtmPortBandWidthValue OBJECT-TYPE
			SYNTAX INTEGER (1..32)
			MAX-ACCESS read-write
			STATUS current
			DESCRIPTION
				"The bandwidth value of the port"
			DEFVAL { 0 }
			::= { hwAtmPortBandWidthEntry 1 }
		
		-- 1.3.6.1.4.1.2011.5.10.2
		hwApmBandWidthTable OBJECT-TYPE
			SYNTAX SEQUENCE OF HwApmBandWidthEntry
			MAX-ACCESS not-accessible
			STATUS current
			DESCRIPTION
				"BandWidth Resource table"
			::= { hwAtmCmRm 2 }
		
		-- 1.3.6.1.4.1.2011.5.10.2.1
		hwApmBandWidthEntry OBJECT-TYPE
			SYNTAX HwApmBandWidthEntry
			MAX-ACCESS not-accessible
			STATUS current
			DESCRIPTION
				"BandWidth Resource table"
			INDEX { hwFrameIndex, hwSlotIndex, hwApmBandWidthType }
			::= { hwApmBandWidthTable 1 }
		
		HwApmBandWidthEntry ::=
			SEQUENCE { 
				hwApmBandWidthType
					INTEGER,
				hwApmBandWidthValue
					INTEGER
			 }

		-- 1.3.6.1.4.1.2011.5.10.2.1.1
		hwApmBandWidthType OBJECT-TYPE
			SYNTAX INTEGER
				{
				vpring(1),
				relay(2),
				inner(3)
				}
			MAX-ACCESS not-accessible
			STATUS current
			DESCRIPTION
				"BandWidth Value"
			::= { hwApmBandWidthEntry 1 }
		
		-- 1.3.6.1.4.1.2011.5.10.2.1.2
		hwApmBandWidthValue OBJECT-TYPE
			SYNTAX INTEGER (1..32)
			MAX-ACCESS read-write
			STATUS current
			DESCRIPTION
				"The bandwidth value of the apm"
			DEFVAL { 0 }
			::= { hwApmBandWidthEntry 2 }
		
--  VCL attibute table definitions
-- 
		-- 1.3.6.1.4.1.2011.5.10.3
		hwVclAttrTable OBJECT-TYPE
			SYNTAX SEQUENCE OF HwVclAttrEntry
			MAX-ACCESS not-accessible
			STATUS current
			DESCRIPTION
				"VCL attribute table"
			::= { hwAtmCmRm 3 }
		
		-- 1.3.6.1.4.1.2011.5.10.3.1
		hwVclAttrEntry OBJECT-TYPE
			SYNTAX HwVclAttrEntry
			MAX-ACCESS not-accessible
			STATUS current
			DESCRIPTION
				"BandWidth Resource table"
			INDEX { ifIndex, atmVclVpi, atmVclVci }
			::= { hwVclAttrTable 1 }
		
		HwVclAttrEntry ::=
			SEQUENCE { 
				hwVclEncapType
					INTEGER,
				hwVclUserSrcMac
					MacAddress,
				hwVclGatewayMac
					MacAddress,
				hwVclUserSrcIP
					IpAddress,
				hwVclGatewayIP
					IpAddress,					
				hwVclUserSrcIpMode
					INTEGER,
				hwVclUserSessionId
					Integer32,
				hwVclUserActualType
					INTEGER
			 }

		-- 1.3.6.1.4.1.2011.5.10.3.1.1
		hwVclEncapType OBJECT-TYPE
			SYNTAX INTEGER
				{
				auto(1),
				llcBridge(2),
				llcPPP(3),
				llcIP(4),
				vcmuxBridge(5),
				vcmuxPPP(6),
				vcmuxIP(7)
				}
			MAX-ACCESS read-create
			STATUS current
			DESCRIPTION
				"
				The encapsulation type of PVC,the default is llc_bridge.
				"
			DEFVAL { llcBridge }
			::= { hwVclAttrEntry 1 }
		
		-- 1.3.6.1.4.1.2011.5.10.3.1.2
		hwVclUserSrcMac OBJECT-TYPE
			SYNTAX MacAddress
			MAX-ACCESS read-only
			STATUS current
			DESCRIPTION
				"
				The source MAC address of PVC.
				"
			::= { hwVclAttrEntry 2 }
		
		-- 1.3.6.1.4.1.2011.5.10.3.1.3
		hwVclGatewayMac OBJECT-TYPE
			SYNTAX MacAddress
			MAX-ACCESS read-only
			STATUS current
			DESCRIPTION
				"
				The destination MAC address of the PVC.
				"
			::= { hwVclAttrEntry 3 }
		
		-- 1.3.6.1.4.1.2011.5.10.3.1.4
		hwVclUserSrcIP OBJECT-TYPE
			SYNTAX IpAddress
			MAX-ACCESS read-write
			STATUS current
			DESCRIPTION
				"
				The protocal IP address of PVC.
				"
			::= { hwVclAttrEntry 4 }

		-- 1.3.6.1.4.1.2011.5.10.3.1.5
		hwVclGatewayIP OBJECT-TYPE
			SYNTAX IpAddress
			MAX-ACCESS read-write
			STATUS current
			DESCRIPTION
				"
				The destination gateway IP address of static IP mode PVC.
				"
			::= { hwVclAttrEntry 5 }
		
		-- 1.3.6.1.4.1.2011.5.10.3.1.6
		hwVclUserSrcIpMode OBJECT-TYPE
			SYNTAX INTEGER
				{
				dynamicIP(1),
				staticIP(2)
				}
			MAX-ACCESS read-only
			STATUS current
			DESCRIPTION
				"
				The mode of fetching the protocal IP address of PVC.
				"
			::= { hwVclAttrEntry 6 }
		
		-- 1.3.6.1.4.1.2011.5.10.3.1.7
		hwVclUserSessionId OBJECT-TYPE
			SYNTAX Integer32 (0..65535)
			MAX-ACCESS read-only
			STATUS current
			DESCRIPTION
				"
				sessionid of the pvc.
				"
			::= { hwVclAttrEntry 7 }
		
		-- 1.3.6.1.4.1.2011.5.10.3.1.8
		hwVclUserActualType OBJECT-TYPE
			SYNTAX INTEGER
				{
				bridge(1),
				llcPPP(2),
				llcIP(3),
				vcPPP(4),
				llcBridge(5),
				vcmuxBridge(6),
				vcmuxIP(7)
				}
			MAX-ACCESS read-only
			STATUS current
			DESCRIPTION
				"
				The actual encapsulation type of PVC.
				"
			::= { hwVclAttrEntry 8 }
		
	
	END

--
-- HUAWEI-ATM-CM-RM-MIB.MIB
--
