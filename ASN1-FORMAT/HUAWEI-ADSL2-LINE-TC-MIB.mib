HUAWEI-ADSL2-LINE-TC-MIB DEFINITIONS ::= BEGIN


   IMPORTS
      MODULE-IDENTITY,
      huaweiUtility			
		 FROM HUAWEI-MIB 

      TEXTUAL-CONVENTION
         FROM SNMPv2-TC;
         
   ------------------------------------------------
   --          Textual Conventions               --
   ------------------------------------------------

   Adsl2Unit ::= TEXTUAL-CONVENTION
      STATUS      current
      DESCRIPTION
         "Identifies a transceiver as being either atuc or
          atur.  An ADSL line consists of two transceivers, an atuc
          and an atur.  Attributes with this syntax reference the two
          sides of a line.  Specified as an INTEGER, the two values
          are:
           atuc(1)  -- central site transceiver
           atur(2)  -- remote site transceiver"
      SYNTAX      INTEGER {
                     atuc(1),
                     atur(2)
                  }

   Adsl2Direction ::= TEXTUAL-CONVENTION
        STATUS current
        DESCRIPTION
           "Identifies the direction of a band as being
            either upstream or downstream.  Specified as an INTEGER,
            the two values are:
             upstream(1)
             downstream(2)"
        SYNTAX INTEGER {
          upstream(1),
          downstream(2)
       }



   Adsl2TransmissionModeType ::= TEXTUAL-CONVENTION
      STATUS      current
      DESCRIPTION
         "A set of ADSL2 line transmission modes, with one bit
          per mode.  The notes (F) and (L) denote Full-Rate
          and Lite/splitterless respectively:
             Bit 00 : Regional Std. (ANSI T1.413) (F)
             Bit 01 : Regional Std. (ETSI DTS/TM06006) (F)
             Bit 02 : G.992.1 POTS non-overlapped (F)
             Bit 03 : G.992.1 POTS overlapped (F)
             Bit 04 : G.992.1 ISDN non-overlapped (F)
             Bit 05 : G.992.1 ISDN overlapped (F)
             Bit 06 : G.992.1 TCM-ISDN non-overlapped (F)
             Bit 07 : G.992.1 TCM-ISDN overlapped (F)
             Bit 08 : G.992.2 POTS non-overlapped (L)
             Bit 09 : G.992.2 POTS overlapped (L)
             Bit 10 : G.992.2 with TCM-ISDN non-overlapped (L)
             Bit 11 : G.992.2 with TCM-ISDN overlapped (L)
             Bit 12 : G.992.1 TCM-ISDN symmetric (F) --- not in G.997.1
             Bit 13-17: Reserved
             Bit 18 : G.992.3 POTS non-overlapped (F)
             Bit 19 : G.992.3 POTS overlapped (F)
             Bit 20 : G.992.3 ISDN non-overlapped (F)
             Bit 21 : G.992.3 ISDN overlapped (F)
             Bit 22-23: Reserved
             Bit 24 : G.992.4 POTS non-overlapped (L)
             Bit 25 : G.992.4 POTS overlapped (L)
             Bit 26-27: Reserved
             Bit 28 : G.992.3 Annex I All-Digital non-overlapped (F)
             Bit 29 : G.992.3 Annex I All-Digital overlapped (F)
             Bit 30 : G.992.3 Annex J All-Digital non-overlapped (F)
             Bit 31 : G.992.3 Annex J All-Digital overlapped (F)
             Bit 32 : G.992.4 Annex I All-Digital non-overlapped (L)
             Bit 33 : G.992.4 Annex I All-Digital overlapped (L)
             Bit 34 : G.992.3 Annex L POTS non-overlapped, mode 1,
                                      wide U/S (F)
             Bit 35 : G.992.3 Annex L POTS non-overlapped, mode 2,
                                      narrow U/S(F)
             Bit 36 : G.992.3 Annex L POTS overlapped, mode 3,
                                      wide U/S (F)
             Bit 37 : G.992.3 Annex L POTS overlapped, mode 4,
                                      narrow U/S (F)
             Bit 38 : G.992.3 Annex M POTS non-overlapped (F)
             Bit 39 : G.992.3 Annex M POTS overlapped (F)
             Bit 40 : G.992.5 POTS non-overlapped (F)
             Bit 41 : G.992.5 POTS overlapped (F)
             Bit 42 : G.992.5 ISDN non-overlapped (F)
             Bit 43 : G.992.5 ISDN overlapped (F)
             Bit 44-45: Reserved
             Bit 46 : G.992.5 Annex I All-Digital non-overlapped (F)
             Bit 47 : G.992.5 Annex I All-Digital overlapped (F)
             Bit 48 : G.992.5 Annex J All-Digital non-overlapped (F)
             Bit 49 : G.992.5 Annex J All-Digital overlapped (F)
             Bit 50 : G.992.5 Annex M POTS non-overlapped (F)
             Bit 51 : G.992.5 Annex M POTS overlapped (F)
             Bit 52-63: Reserved
             "
      SYNTAX      BITS {
                     ansit1413(0),
                     etsi(1),
                     g9921PotsNonOverlapped(2),
                     g9921PotsOverlapped(3),
                     g9921IsdnNonOverlapped(4),
                     g9921isdnOverlapped(5),
                     g9921tcmIsdnNonOverlapped(6),
                     g9921tcmIsdnOverlapped(7),
                     g9922potsNonOverlapeed(8),
                     g9922potsOverlapped(9),
                     g9922tcmIsdnNonOverlapped(10),
                     g9922tcmIsdnOverlapped(11),
                     g9921tcmIsdnSymmetric(12),
                     reserved1(13),
                     reserved2(14),
                     reserved3(15),
                     reserved4(16),
                     reserved5(17),
                     g9923PotsNonOverlapped(18),
                     g9923PotsOverlapped(19),
                     g9923IsdnNonOverlapped(20),
                     g9923isdnOverlapped(21),
                     reserved6(22),
                     reserved7(23),
                     g9924potsNonOverlapeed(24),
                     g9924potsOverlapped(25),
                     reserved8(26),
                     reserved9(27),
                     g9923AnnexIAllDigNonOverlapped(28),
                     g9923AnnexIAllDigOverlapped(29),
                     g9923AnnexJAllDigNonOverlapped(30),
                     g9923AnnexJAllDigOverlapped(31),
                     g9924AnnexIAllDigNonOverlapped(32),
                     g9924AnnexIAllDigOverlapped(33),
                     g9923AnnexLMode1NonOverlapped(34),
                     g9923AnnexLMode2NonOverlapped(35),
                     g9923AnnexLMode3Overlapped(36),
                     g9923AnnexLMode4Overlapped(37),
                     g9923AnnexMPotsNonOverlapped(38),
                     g9923AnnexMPotsOverlapped(39),
                     g9925PotsNonOverlapped(40),
                     g9925PotsOverlapped(41),
                     g9925IsdnNonOverlapped(42),
                     g9925isdnOverlapped(43),
                     reserved10(44),
                     reserved11(45),
                     g9925AnnexIAllDigNonOverlapped(46),
                     g9925AnnexIAllDigOverlapped(47),
                     g9925AnnexJAllDigNonOverlapped(48),
                     g9925AnnexJAllDigOverlapped(49),
                     g9925AnnexMPotsNonOverlapped(50),
                     g9925AnnexMPotsOverlapped(51),
                     reserved12(52),
                     reserved13(53),
                     reserved14(54),
                     reserved15(55)
                  }

   Adsl2RaMode ::= TEXTUAL-CONVENTION
      STATUS      current
      DESCRIPTION
         "Specifies the rate adaptation behavior for the line.
          The three possible behaviors are:
           manual (1)   - No Rate-Adaptation.  The initialization
                          process attempts to synchronize to a
                          specified rate.
           raInit (2)   - Rate-Adaptation during initialization process
                          only, which attempts to synchronize to a rate
                          between minimum and maximum specified values.
           dynamicRa (3)- Dynamic Rate-Adaptation during initialization
                          process as well as during SHOWTIME"
      SYNTAX      INTEGER {
                     manual(1),
                     raInit(2),
                     dynamicRa(3)
                  }

   Adsl2InitResult ::= TEXTUAL-CONVENTION
      STATUS      current
      DESCRIPTION
         "Specifies the result of full initialization attempt; the
          six possible result values are:
           noFail (0)            - Successful initialization
           configError (1)       - Configuration failure
           configNotFeasible (2) - Configuration details not supported
           commFail (3)          - Communication failure
           noPeerAtu (4)         - Peer ATU not detected
           otherCause (5)        - Other initialization failure reason

          The values used are as defined in ITU-T G.997.1,
          paragraph 7.5.1.3"

      SYNTAX      INTEGER {
                     noFail(0),
                     configError(1),
                     configNotFeasible(2),
                     commFail(3),
                     noPeerAtu(4),
                     otherCause(5)
                  }
                  
   Adsl2OperationModes ::= TEXTUAL-CONVENTION
      STATUS      current
      DESCRIPTION
         "The ADSL2 management model specified includes an ADSL Mode
          attribute which identifies an instance of ADSL Mode-Specific
          PSD Configuration object in the ADSL Line Profile.  The
          following classes of ADSL operating mode are defined. "
      SYNTAX      INTEGER {
                     defMode (1),
                     adsl (2),
                     adsl2Pots (3),
                     adsl2Isdn (4),
                     adsl2PlusPots (5),
                     adsl2PlusIsdn (6),
                     adsl2ReachExtended (7)
                  }

   Adsl2PowerMngState ::= TEXTUAL-CONVENTION
      STATUS      current
      DESCRIPTION
         "Attributes with this syntax uniquely identify each power
          management state defined for the ADSL/ADSL2 or ADSL2+ link.
          The possible values are:
            l0(1) - L0 - Full power management state
            l1(2) - L1 - Low power management state (for G.992.2)
            l2(3) - L2 - Low power management state (for G.992.3,
                         G.992.4, and G.992.5)
            l3(4) - L3 - Idle power management state"

      SYNTAX      INTEGER {
                     l0(1),
                     l1(2),
                     l2(3),
                     l3(4)
                  }

   Adsl2ConfPmsForce ::= TEXTUAL-CONVENTION
      STATUS      current
      DESCRIPTION
         "Attributes with this syntax are configuration parameters
          that reference the desired power management state for the
          ADSL/ADSL2 or ADSL2+ link:
            l3toL0 (0)         - Perform a transition from L3 to L0
                                 (Full power management state)
            l0toL2 (2)         - Perform a transition from L0 to L2
                                 (Low power management state)
            l0orL2toL3 (3)     - Perform a transition into L3 (Idle
                                 power management state)
          The values used are as defined in ITU-T G.997.1,
          paragraph 7.3.1.1.3"

      SYNTAX      INTEGER {
                     l3toL0 (0),
                     l0toL2 (2),
                     l0orL2toL3 (3)
                  }

   Adsl2LConfProfPmMode ::= TEXTUAL-CONVENTION
      STATUS current
      DESCRIPTION
         "Attributes with this syntax are configuration parameters
          that reference the power modes/states into which the ATU-C or
          ATU-R may autonomously transit.

          It is a BITS structure that allows control of the following
          transit options:
           allowTransitionsToIdle (0)    - xTU may autonomously transit
                                           to idle (L3) state.
           allowTransitionsToLowPower (1)- xTU may autonomously transit
                                           to low-power (L2) state."

      SYNTAX BITS {
          allowTransitionsToIdle(0),
          allowTransitionsToLowPower(1)
        }

   Adsl2LineLdsf ::= TEXTUAL-CONVENTION
      STATUS current
      DESCRIPTION
         "Attributes with this syntax are configuration parameters
          that control the Loop Diagnostic mode for the ADSL/ADSL2 or
          ADSL2+ link.  The possible values are:
            inhibit (0)  - Inhibit Loop Diagnostic mode
            force   (1)  - Force/Initiate Loop Diagnostic mode

          The values used are as defined in ITU-T G.997.1,
          paragraph 7.3.1.1.8"

      SYNTAX INTEGER {
          inhibit(0),
          force(1)
        }

   Adsl2LdsfResult ::= TEXTUAL-CONVENTION
        STATUS current
        DESCRIPTION
           "Possible failure reasons associated with performing
            Dual Ended Loop Test (DELT) on a DSL line.
            Possible values are:
             none        (1) - The default value in case LDSF was never
                               requested for the associated line.
             success     (2) - The recent command completed
                               successfully.
             inProgress  (3) - The Loop Diagnostics process is in
                               progress.
             unsupported (4) - The NE or the line card doesn't support
                               LDSF.
             cannotRun   (5) - The NE cannot initiate the command, due
                               to a non specific reason.
             aborted     (6) - The Loop Diagnostics process aborted.
             failed      (7) - The Loop Diagnostics process failed.
             illegalMode (8) - The NE cannot initiate the command, due
                               to the specific mode of the relevant
                               line.
             adminUp     (9) - The NE cannot initiate the command, as
                               the relevant line is administratively
                               'Up'.
             tableFull   (10)- The NE cannot initiate the command, due
                               to reaching the maximum number of rows
                               in the results table.
             noResources (11)- The NE cannot initiate the command, due
                               to lack of internal memory resources."
        SYNTAX INTEGER {
             none (1),
             success (2),
             inProgress (3),
             unsupported (4),
             cannotRun (5),
             aborted (6),
             failed (7),
             illegalMode (8),
             adminUp (9),
             tableFull (10),
             noResources (11)
        }

   Adsl2SymbolProtection ::= TEXTUAL-CONVENTION
      STATUS      current
      DESCRIPTION
         "Attributes with this syntax are configuration parameters
          that reference the minimum length impulse noise protection
          (INP) in terms of number of symbols.  The possible values are:
          noProtection (i.e., INP not required), halfSymbol (i.e., INP
          length is 1/2 symbol), and 1-16 symbols in steps of 1 symbol"
      SYNTAX      INTEGER {
                  noProtection (1),
                  halfSymbol (2),
                  singleSymbol (3),
                  twoSymbols (4),
                  threeSymbols (5),
                  fourSymbols (6),
                  fiveSymbols (7),
                  sixSymbols (8),
                  sevenSymbols (9),
                  eightSymbols (10),
                  nineSymbols (11),
                  tenSymbols (12),
                  elevenSymbols (13),
                  twelveSymbols (14),
                  thirteeSymbols (15),
                  fourteenSymbols (16),
                  fifteenSymbols (17),
                  sixteenSymbols (18)
                }
   Adsl2MaxBer ::= TEXTUAL-CONVENTION
      STATUS      current
      DESCRIPTION
         "Attributes with this syntax are configuration parameters
          that reference the maximum Bit Error Rate (BER).
          The possible values are:

            eminus3 (1)  - Maximum BER=E^-3
            eminus5 (2)  - Maximum BER=E^-5
            eminus7 (3)  - Maximum BER=E^-7"
      SYNTAX      INTEGER {
                     eminus3(1),
                     eminus5(2),
                     eminus7(3)
                  }

   Adsl2ScMaskDs ::= TEXTUAL-CONVENTION
      STATUS      current
      DESCRIPTION
         "Each one of the 512 bits in this OCTET
          STRING array represents the corresponding bin
          in the downstream direction.  A value of one
          indicates that the bin is not in use."
      SYNTAX      OCTET STRING (SIZE(0..64))

   Adsl2ScMaskUs ::= TEXTUAL-CONVENTION
      STATUS      current
      DESCRIPTION
         "Each one of the 64 bits in this OCTET
         STRING array represents the corresponding bin
         in the upstream direction.  A value of one
         indicates that the bin is not in use."
      SYNTAX      OCTET STRING (SIZE(0..8))

   Adsl2RfiDs ::= TEXTUAL-CONVENTION
      STATUS      current
      DESCRIPTION
         "Each one of the 512 bits in this OCTET
         STRING array represents the corresponding bin
         in the downstream direction.  A value of one
         indicates that the bin is part of a notch
         filter."
      SYNTAX      OCTET STRING (SIZE(0..64))

   Adsl2PsdMaskDs ::= TEXTUAL-CONVENTION
      STATUS      current
      DESCRIPTION
         "This is a structure that represents up to
         32 PSD Mask breakpoints.
         Each breakpoint occupies 3 octets: The first
         two octets hold the index of the sub-carrier
         associated with the breakpoint.  The third octet
         holds the PSD reduction at the breakpoint from 0
         (0dBm/Hz) to 255 (-127.5 dBm/Hz) using units of
         0.5dBm/Hz."
      SYNTAX      OCTET STRING (SIZE(0..96))

   Adsl2PsdMaskUs ::= TEXTUAL-CONVENTION
      STATUS      current
      DESCRIPTION
         "This is a structure that represents up to
         4 PSD Mask breakpoints.
         Each breakpoint occupies 3 octets: The first
         two octets hold the index of the sub-carrier
         associated with the breakpoint.  The third octet
         holds the PSD reduction at the breakpoint from 0
         (0dBm/Hz) to 255 (-127.5 dBm/Hz) using units of
         0.5dBm/Hz."
      SYNTAX      OCTET STRING (SIZE(0..12))

   Adsl2Tssi ::= TEXTUAL-CONVENTION
      STATUS      current
      DESCRIPTION
         "This is a structure that represents up to
         32 transmit spectrum shaping (TSSi) breakpoints.
         Each breakpoint occupies 3 octets: The first
         two octets hold the index of the sub-carrier
         associated with the breakpoint.  The third octet
         holds the shaping parameter at the breakpoint. It
         is a value from 0 to 127 (units of -0.5dB). The
         special value 127 indicates that the sub-carrier
         is not transmitted."
      SYNTAX      OCTET STRING (SIZE(0..96))

   Adsl2LastTransmittedState ::= TEXTUAL-CONVENTION
        STATUS current
        DESCRIPTION
           "This parameter represents the last successful
            transmitted initialization state in the last full
            initialization performed on the line.  States are
            per the specific xDSL technology and are numbered
            from 0 (if G.994.1 is used) or 1 (if G.994.1 is
            not used) up to Showtime."
        SYNTAX      INTEGER {
          atucG9941(0),
          atucQuiet1(1),
          atucComb1(2),
          atucQuiet2(3),
          atucComb2(4),
          atucIcomb1(5),
          atucLineprob(6),
          atucQuiet3(7),
          atucComb3(8),
          atucIComb2(9),
          atucMsgfmt(10),
          atucMsgpcb(11),
          atucQuiet4(12),
          atucReverb1(13),
          atucTref1(14),
          atucReverb2(15),
          atucEct(16),
          atucReverb3(17),
          atucTref2(18),
          atucReverb4(19),
          atucSegue1(20),
          atucMsg1(21),
          atucReverb5(22),
          atucSegue2(23),
          atucMedley(24),
          atucExchmarker(25),
          atucMsg2(26),
          atucReverb6(27),
          atucSegue3(28),
          atucParams(29),
          atucReverb7(30),
          atucSegue4(31),
          atucShowtime(32),
          --
          aturG9941(100),
          aturQuiet1(101),
          aturComb1(102),
          aturQuiet2(103),
          aturComb2(104),
          aturIcomb1(105),
          aturLineprob(106),
          aturQuiet3(107),
          aturComb3(108),
          aturIcomb2(109),
          aturMsgfmt(110),
          aturMsgpcb(111),
          aturReverb1(112),
          aturQuiet4(113),
          aturReverb2(114),
          aturQuiet5(115),
          aturReverb3(116),
          aturEct(117),
          aturReverb4(118),
          aturSegue1(119),
          aturReverb5(120),
          aturSegue2(121),
          aturMsg1(122),
          aturMedley(123),
          aturExchmarker(124),
          aturMsg2(125),
          aturReverb6(126),
          aturSegue3(127),
          aturParams(128),
          aturReverb7(129),
          aturSegue4(130),
          aturShowtime(131)
        }

   Adsl2LineStatus ::= TEXTUAL-CONVENTION
      STATUS current
      DESCRIPTION
         "Attributes with this syntax are status parameters
          that reflect the failure status for a given endpoint of
          ADSL/ADSL2 or ADSL2+ link.

          This BITS structure can report the following failures:

           noDefect (0)      - This bit position positively reports
                               that no defect or failure exist.
           lossOfFraming (1) - Loss of frame synchronization
           lossOfSignal (2)  - Loss of signal
           lossOfPower (3)   - Loss of power.  Usually this failure may
                               be reported for CPE units only
           initFailure (4)   - Recent initialization process failed.
                               Never active on ATU-R."

      SYNTAX BITS {
          noDefect(0),
          lossOfFraming(1),
          lossOfSignal(2),
          lossOfPower(3),
          initFailure(4)
        }

   Adsl2ChAtmStatus ::= TEXTUAL-CONVENTION
      STATUS current
      DESCRIPTION
        "Attributes with this syntax are status parameters that
         reflect the failure status for Transmission Convergence (TC)
         layer of a given ATM interface (data path over an ADSL/ADSL2
         or ADSL2+ link).

         This BITS structure can report the following failures:
          noDefect (0)            - This bit position positively
                                    reports that no defect or failure
                                    exist.
          noCellDelineation (1)   - The link was successfully

                                    initialized but cell delineation

                                    was never acquired on the

                                    associated ATM data path.
          lossOfCellDelineation (2)- Loss of cell delineation on the
                                     associated ATM data path"

      SYNTAX BITS {
          noDefect(0),
          noCellDelineation(1),
          lossOfCellDelineation(2)
        }

   Adsl2ChPtmStatus ::= TEXTUAL-CONVENTION
      STATUS current
      DESCRIPTION
        "Attributes with this syntax are status parameters that
         reflect the failure status for a given PTM interface (packet
         data path over an ADSL/ADSL2 or ADSL2+ link).

         This BITS structure can report the following failures:
             noDefect (0)    - This bit position positively
                               reports that no defect or failure exist.
             outOfSync (1)   - Out of synchronization. "

         SYNTAX BITS {
             noDefect(0),
             outOfSync(1)
        }

   Adsl2TrellisMode ::= TEXTUAL-CONVENTION
      STATUS current
      DESCRIPTION
        "Enables and disables the Trellions mode. This
 	      object is defaulted enabled(2)."

         SYNTAX INTEGER {
             disable(1),
             enable(2)
        }

   Adsl2BitSwap ::= TEXTUAL-CONVENTION
      STATUS current
      DESCRIPTION
        "Enables and disables the bit swap upstream or downstream of a line."

         SYNTAX INTEGER {
             disable(1),
             enable(2)
        }
     
        
   Adsl2CfgMode ::= TEXTUAL-CONVENTION
      STATUS current
      DESCRIPTION
         "The configured ADSL management mode.  Specified as an INTEGER, the two values
          are:
             adslMode(1)    -- ADSL management mode
             ngadslMode(2)  -- NGADSL management mode"
         SYNTAX INTEGER {
             adslMode(1),
             ngadslMode(2)
        }

   END
