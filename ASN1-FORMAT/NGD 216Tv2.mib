--  Title:    NGD_G42v2.MIB
--  Version:  v4.2 for SNMPv2c
--
--  Copyright @ 2006 DPS Inc. All Rights Reserved
--
--  This MIB defines supplemental objects for the DPS NetGuardian 4.0 series.
--
--

DPS-MIB-NGD-V10-V2 DEFINITIONS ::= BEGIN

IMPORTS
	dpsRTUv2
		FROM DPS-MIB-V38-V2;

dpsRTUv2p8001Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 1 is set."
	::= { dpsRTUv2 8001 }

dpsRTUv2p9001Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 1 clears."
	::= { dpsRTUv2 9001 }

dpsRTUv2p8002Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 2 is set."
	::= { dpsRTUv2 8002 }

dpsRTUv2p9002Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 2 clears."
	::= { dpsRTUv2 9002 }

dpsRTUv2p8003Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 3 is set."
	::= { dpsRTUv2 8003 }

dpsRTUv2p9003Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 3 clears."
	::= { dpsRTUv2 9003 }

dpsRTUv2p8004Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 4 is set."
	::= { dpsRTUv2 8004 }

dpsRTUv2p9004Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 4 clears."
	::= { dpsRTUv2 9004 }

dpsRTUv2p8005Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 5 is set."
	::= { dpsRTUv2 8005 }

dpsRTUv2p9005Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 5 clears."
	::= { dpsRTUv2 9005 }

dpsRTUv2p8006Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 6 is set."
	::= { dpsRTUv2 8006 }

dpsRTUv2p9006Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 6 clears."
	::= { dpsRTUv2 9006 }

dpsRTUv2p8007Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 7 is set."
	::= { dpsRTUv2 8007 }

dpsRTUv2p9007Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 7 clears."
	::= { dpsRTUv2 9007 }

dpsRTUv2p8008Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 8 is set."
	::= { dpsRTUv2 8008 }

dpsRTUv2p9008Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 8 clears."
	::= { dpsRTUv2 9008 }

dpsRTUv2p8009Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 9 is set."
	::= { dpsRTUv2 8009 }

dpsRTUv2p9009Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 9 clears."
	::= { dpsRTUv2 9009 }

dpsRTUv2p8010Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 10 is set."
	::= { dpsRTUv2 8010 }

dpsRTUv2p9010Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 10 clears."
	::= { dpsRTUv2 9010 }

dpsRTUv2p8011Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 11 is set."
	::= { dpsRTUv2 8011 }

dpsRTUv2p9011Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 11 clears."
	::= { dpsRTUv2 9011 }

dpsRTUv2p8012Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 12 is set."
	::= { dpsRTUv2 8012 }

dpsRTUv2p9012Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 12 clears."
	::= { dpsRTUv2 9012 }

dpsRTUv2p8013Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 13 is set."
	::= { dpsRTUv2 8013 }

dpsRTUv2p9013Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 13 clears."
	::= { dpsRTUv2 9013 }

dpsRTUv2p8014Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 14 is set."
	::= { dpsRTUv2 8014 }

dpsRTUv2p9014Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 14 clears."
	::= { dpsRTUv2 9014 }

dpsRTUv2p8015Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 15 is set."
	::= { dpsRTUv2 8015 }

dpsRTUv2p9015Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 15 clears."
	::= { dpsRTUv2 9015 }

dpsRTUv2p8016Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 16 is set."
	::= { dpsRTUv2 8016 }

dpsRTUv2p9016Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 16 clears."
	::= { dpsRTUv2 9016 }

dpsRTUv2p8017Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 17 is set."
	::= { dpsRTUv2 8017 }

dpsRTUv2p9017Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 17 clears."
	::= { dpsRTUv2 9017 }

dpsRTUv2p8018Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 18 is set."
	::= { dpsRTUv2 8018 }

dpsRTUv2p9018Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 18 clears."
	::= { dpsRTUv2 9018 }

dpsRTUv2p8019Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 19 is set."
	::= { dpsRTUv2 8019 }

dpsRTUv2p9019Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 19 clears."
	::= { dpsRTUv2 9019 }

dpsRTUv2p8020Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 20 is set."
	::= { dpsRTUv2 8020 }

dpsRTUv2p9020Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 20 clears."
	::= { dpsRTUv2 9020 }

dpsRTUv2p8021Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 21 is set."
	::= { dpsRTUv2 8021 }

dpsRTUv2p9021Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 21 clears."
	::= { dpsRTUv2 9021 }

dpsRTUv2p8022Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 22 is set."
	::= { dpsRTUv2 8022 }

dpsRTUv2p9022Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 22 clears."
	::= { dpsRTUv2 9022 }

dpsRTUv2p8023Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 23 is set."
	::= { dpsRTUv2 8023 }

dpsRTUv2p9023Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 23 clears."
	::= { dpsRTUv2 9023 }

dpsRTUv2p8024Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 24 is set."
	::= { dpsRTUv2 8024 }

dpsRTUv2p9024Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 24 clears."
	::= { dpsRTUv2 9024 }

dpsRTUv2p8025Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 25 is set."
	::= { dpsRTUv2 8025 }

dpsRTUv2p9025Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 25 clears."
	::= { dpsRTUv2 9025 }

dpsRTUv2p8026Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 26 is set."
	::= { dpsRTUv2 8026 }

dpsRTUv2p9026Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 26 clears."
	::= { dpsRTUv2 9026 }

dpsRTUv2p8027Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 27 is set."
	::= { dpsRTUv2 8027 }

dpsRTUv2p9027Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 27 clears."
	::= { dpsRTUv2 9027 }

dpsRTUv2p8028Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 28 is set."
	::= { dpsRTUv2 8028 }

dpsRTUv2p9028Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 28 clears."
	::= { dpsRTUv2 9028 }

dpsRTUv2p8029Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 29 is set."
	::= { dpsRTUv2 8029 }

dpsRTUv2p9029Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 29 clears."
	::= { dpsRTUv2 9029 }

dpsRTUv2p8030Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 30 is set."
	::= { dpsRTUv2 8030 }

dpsRTUv2p9030Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 30 clears."
	::= { dpsRTUv2 9030 }

dpsRTUv2p8031Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 31 is set."
	::= { dpsRTUv2 8031 }

dpsRTUv2p9031Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 31 clears."
	::= { dpsRTUv2 9031 }

dpsRTUv2p8032Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 32 is set."
	::= { dpsRTUv2 8032 }

dpsRTUv2p9032Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 32 clears."
	::= { dpsRTUv2 9032 }

dpsRTUv2p8033Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 33 is set."
	::= { dpsRTUv2 8033 }

dpsRTUv2p9033Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 33 clears."
	::= { dpsRTUv2 9033 }

dpsRTUv2p8034Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 34 is set."
	::= { dpsRTUv2 8034 }

dpsRTUv2p9034Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 34 clears."
	::= { dpsRTUv2 9034 }

dpsRTUv2p8035Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 35 is set."
	::= { dpsRTUv2 8035 }

dpsRTUv2p9035Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 35 clears."
	::= { dpsRTUv2 9035 }

dpsRTUv2p8036Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 36 is set."
	::= { dpsRTUv2 8036 }

dpsRTUv2p9036Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 36 clears."
	::= { dpsRTUv2 9036 }

dpsRTUv2p8037Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 37 is set."
	::= { dpsRTUv2 8037 }

dpsRTUv2p9037Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 37 clears."
	::= { dpsRTUv2 9037 }

dpsRTUv2p8038Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 38 is set."
	::= { dpsRTUv2 8038 }

dpsRTUv2p9038Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 38 clears."
	::= { dpsRTUv2 9038 }

dpsRTUv2p8039Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 39 is set."
	::= { dpsRTUv2 8039 }

dpsRTUv2p9039Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 39 clears."
	::= { dpsRTUv2 9039 }

dpsRTUv2p8040Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 40 is set."
	::= { dpsRTUv2 8040 }

dpsRTUv2p9040Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 40 clears."
	::= { dpsRTUv2 9040 }

dpsRTUv2p8041Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 41 is set."
	::= { dpsRTUv2 8041 }

dpsRTUv2p9041Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 41 clears."
	::= { dpsRTUv2 9041 }

dpsRTUv2p8042Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 42 is set."
	::= { dpsRTUv2 8042 }

dpsRTUv2p9042Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 42 clears."
	::= { dpsRTUv2 9042 }

dpsRTUv2p8043Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 43 is set."
	::= { dpsRTUv2 8043 }

dpsRTUv2p9043Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 43 clears."
	::= { dpsRTUv2 9043 }

dpsRTUv2p8044Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 44 is set."
	::= { dpsRTUv2 8044 }

dpsRTUv2p9044Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 44 clears."
	::= { dpsRTUv2 9044 }

dpsRTUv2p8045Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 45 is set."
	::= { dpsRTUv2 8045 }

dpsRTUv2p9045Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 45 clears."
	::= { dpsRTUv2 9045 }

dpsRTUv2p8046Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 46 is set."
	::= { dpsRTUv2 8046 }

dpsRTUv2p9046Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 46 clears."
	::= { dpsRTUv2 9046 }

dpsRTUv2p8047Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 47 is set."
	::= { dpsRTUv2 8047 }

dpsRTUv2p9047Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 47 clears."
	::= { dpsRTUv2 9047 }

dpsRTUv2p8048Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 48 is set."
	::= { dpsRTUv2 8048 }

dpsRTUv2p9048Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 48 clears."
	::= { dpsRTUv2 9048 }

dpsRTUv2p8049Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 49 is set."
	::= { dpsRTUv2 8049 }

dpsRTUv2p9049Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 49 clears."
	::= { dpsRTUv2 9049 }

dpsRTUv2p8050Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 50 is set."
	::= { dpsRTUv2 8050 }

dpsRTUv2p9050Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 50 clears."
	::= { dpsRTUv2 9050 }

dpsRTUv2p8051Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 51 is set."
	::= { dpsRTUv2 8051 }

dpsRTUv2p9051Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 51 clears."
	::= { dpsRTUv2 9051 }

dpsRTUv2p8052Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 52 is set."
	::= { dpsRTUv2 8052 }

dpsRTUv2p9052Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 52 clears."
	::= { dpsRTUv2 9052 }

dpsRTUv2p8053Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 53 is set."
	::= { dpsRTUv2 8053 }

dpsRTUv2p9053Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 53 clears."
	::= { dpsRTUv2 9053 }

dpsRTUv2p8054Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 54 is set."
	::= { dpsRTUv2 8054 }

dpsRTUv2p9054Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 54 clears."
	::= { dpsRTUv2 9054 }

dpsRTUv2p8055Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 55 is set."
	::= { dpsRTUv2 8055 }

dpsRTUv2p9055Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 55 clears."
	::= { dpsRTUv2 9055 }

dpsRTUv2p8056Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 56 is set."
	::= { dpsRTUv2 8056 }

dpsRTUv2p9056Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 56 clears."
	::= { dpsRTUv2 9056 }

dpsRTUv2p8057Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 57 is set."
	::= { dpsRTUv2 8057 }

dpsRTUv2p9057Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 57 clears."
	::= { dpsRTUv2 9057 }

dpsRTUv2p8058Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 58 is set."
	::= { dpsRTUv2 8058 }

dpsRTUv2p9058Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 58 clears."
	::= { dpsRTUv2 9058 }

dpsRTUv2p8059Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 59 is set."
	::= { dpsRTUv2 8059 }

dpsRTUv2p9059Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 59 clears."
	::= { dpsRTUv2 9059 }

dpsRTUv2p8060Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 60 is set."
	::= { dpsRTUv2 8060 }

dpsRTUv2p9060Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 60 clears."
	::= { dpsRTUv2 9060 }

dpsRTUv2p8061Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 61 is set."
	::= { dpsRTUv2 8061 }

dpsRTUv2p9061Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 61 clears."
	::= { dpsRTUv2 9061 }

dpsRTUv2p8062Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 62 is set."
	::= { dpsRTUv2 8062 }

dpsRTUv2p9062Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 62 clears."
	::= { dpsRTUv2 9062 }

dpsRTUv2p8063Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 63 is set."
	::= { dpsRTUv2 8063 }

dpsRTUv2p9063Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 63 clears."
	::= { dpsRTUv2 9063 }

dpsRTUv2p8064Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 64 is set."
	::= { dpsRTUv2 8064 }

dpsRTUv2p9064Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 64 clears."
	::= { dpsRTUv2 9064 }

dpsRTUv2p8065Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 1 fails."
	::= { dpsRTUv2 8065 }

dpsRTUv2p9065Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 1 reappears."
	::= { dpsRTUv2 9065 }

dpsRTUv2p8066Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 2 fails."
	::= { dpsRTUv2 8066 }

dpsRTUv2p9066Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 2 reappears."
	::= { dpsRTUv2 9066 }

dpsRTUv2p8067Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 3 fails."
	::= { dpsRTUv2 8067 }

dpsRTUv2p9067Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 3 reappears."
	::= { dpsRTUv2 9067 }

dpsRTUv2p8068Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 4 fails."
	::= { dpsRTUv2 8068 }

dpsRTUv2p9068Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 4 reappears."
	::= { dpsRTUv2 9068 }

dpsRTUv2p8069Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 5 fails."
	::= { dpsRTUv2 8069 }

dpsRTUv2p9069Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 5 reappears."
	::= { dpsRTUv2 9069 }

dpsRTUv2p8070Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 6 fails."
	::= { dpsRTUv2 8070 }

dpsRTUv2p9070Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 6 reappears."
	::= { dpsRTUv2 9070 }

dpsRTUv2p8071Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 7 fails."
	::= { dpsRTUv2 8071 }

dpsRTUv2p9071Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 7 reappears."
	::= { dpsRTUv2 9071 }

dpsRTUv2p8072Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 8 fails."
	::= { dpsRTUv2 8072 }

dpsRTUv2p9072Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 8 reappears."
	::= { dpsRTUv2 9072 }

dpsRTUv2p8073Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 9 fails."
	::= { dpsRTUv2 8073 }

dpsRTUv2p9073Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 9 reappears."
	::= { dpsRTUv2 9073 }

dpsRTUv2p8074Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 10 fails."
	::= { dpsRTUv2 8074 }

dpsRTUv2p9074Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 10 reappears."
	::= { dpsRTUv2 9074 }

dpsRTUv2p8075Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 11 fails."
	::= { dpsRTUv2 8075 }

dpsRTUv2p9075Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 11 reappears."
	::= { dpsRTUv2 9075 }

dpsRTUv2p8076Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 12 fails."
	::= { dpsRTUv2 8076 }

dpsRTUv2p9076Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 12 reappears."
	::= { dpsRTUv2 9076 }

dpsRTUv2p8077Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 13 fails."
	::= { dpsRTUv2 8077 }

dpsRTUv2p9077Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 13 reappears."
	::= { dpsRTUv2 9077 }

dpsRTUv2p8078Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 14 fails."
	::= { dpsRTUv2 8078 }

dpsRTUv2p9078Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 14 reappears."
	::= { dpsRTUv2 9078 }

dpsRTUv2p8079Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 15 fails."
	::= { dpsRTUv2 8079 }

dpsRTUv2p9079Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 15 reappears."
	::= { dpsRTUv2 9079 }

dpsRTUv2p8080Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 16 fails."
	::= { dpsRTUv2 8080 }

dpsRTUv2p9080Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 16 reappears."
	::= { dpsRTUv2 9080 }

dpsRTUv2p8081Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 17 fails."
	::= { dpsRTUv2 8081 }

dpsRTUv2p9081Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 17 reappears."
	::= { dpsRTUv2 9081 }

dpsRTUv2p8082Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 18 fails."
	::= { dpsRTUv2 8082 }

dpsRTUv2p9082Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 18 reappears."
	::= { dpsRTUv2 9082 }

dpsRTUv2p8083Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 19 fails."
	::= { dpsRTUv2 8083 }

dpsRTUv2p9083Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 19 reappears."
	::= { dpsRTUv2 9083 }

dpsRTUv2p8084Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 20 fails."
	::= { dpsRTUv2 8084 }

dpsRTUv2p9084Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 20 reappears."
	::= { dpsRTUv2 9084 }

dpsRTUv2p8085Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 21 fails."
	::= { dpsRTUv2 8085 }

dpsRTUv2p9085Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 21 reappears."
	::= { dpsRTUv2 9085 }

dpsRTUv2p8086Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 22 fails."
	::= { dpsRTUv2 8086 }

dpsRTUv2p9086Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 22 reappears."
	::= { dpsRTUv2 9086 }

dpsRTUv2p8087Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 23 fails."
	::= { dpsRTUv2 8087 }

dpsRTUv2p9087Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 23 reappears."
	::= { dpsRTUv2 9087 }

dpsRTUv2p8088Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 24 fails."
	::= { dpsRTUv2 8088 }

dpsRTUv2p9088Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 24 reappears."
	::= { dpsRTUv2 9088 }

dpsRTUv2p8089Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 25 fails."
	::= { dpsRTUv2 8089 }

dpsRTUv2p9089Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 25 reappears."
	::= { dpsRTUv2 9089 }

dpsRTUv2p8090Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 26 fails."
	::= { dpsRTUv2 8090 }

dpsRTUv2p9090Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 26 reappears."
	::= { dpsRTUv2 9090 }

dpsRTUv2p8091Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 27 fails."
	::= { dpsRTUv2 8091 }

dpsRTUv2p9091Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 27 reappears."
	::= { dpsRTUv2 9091 }

dpsRTUv2p8092Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 28 fails."
	::= { dpsRTUv2 8092 }

dpsRTUv2p9092Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 28 reappears."
	::= { dpsRTUv2 9092 }

dpsRTUv2p8093Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 29 fails."
	::= { dpsRTUv2 8093 }

dpsRTUv2p9093Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 29 reappears."
	::= { dpsRTUv2 9093 }

dpsRTUv2p8094Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 30 fails."
	::= { dpsRTUv2 8094 }

dpsRTUv2p9094Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 30 reappears."
	::= { dpsRTUv2 9094 }

dpsRTUv2p8095Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 31 fails."
	::= { dpsRTUv2 8095 }

dpsRTUv2p9095Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 31 reappears."
	::= { dpsRTUv2 9095 }

dpsRTUv2p8096Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 32 fails."
	::= { dpsRTUv2 8096 }

dpsRTUv2p9096Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when ping target 32 reappears."
	::= { dpsRTUv2 9096 }

dpsRTUv2p8097Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 97 is set."
	::= { dpsRTUv2 8097 }

dpsRTUv2p9097Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 97 clears."
	::= { dpsRTUv2 9097 }

dpsRTUv2p8098Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 98 is set."
	::= { dpsRTUv2 8098 }

dpsRTUv2p9098Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 98 clears."
	::= { dpsRTUv2 9098 }

dpsRTUv2p8099Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 99 is set."
	::= { dpsRTUv2 8099 }

dpsRTUv2p9099Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 99 clears."
	::= { dpsRTUv2 9099 }

dpsRTUv2p8100Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 64 is set."
	::= { dpsRTUv2 8100 }

dpsRTUv2p9100Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 64 clears."
	::= { dpsRTUv2 9100 }

dpsRTUv2p8101Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 101 is set."
	::= { dpsRTUv2 8101 }

dpsRTUv2p9101Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 101 clears."
	::= { dpsRTUv2 9101 }

dpsRTUv2p8102Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 102 is set."
	::= { dpsRTUv2 8102 }

dpsRTUv2p9102Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 102 clears."
	::= { dpsRTUv2 9102 }

dpsRTUv2p8103Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 103 is set."
	::= { dpsRTUv2 8103 }

dpsRTUv2p9103Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 103 clears."
	::= { dpsRTUv2 9103 }

dpsRTUv2p8104Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 104 is set."
	::= { dpsRTUv2 8104 }

dpsRTUv2p9104Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 104 clears."
	::= { dpsRTUv2 9104 }

dpsRTUv2p8105Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 105 is set."
	::= { dpsRTUv2 8105 }

dpsRTUv2p9105Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 105 clears."
	::= { dpsRTUv2 9105 }

dpsRTUv2p8106Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 106 is set."
	::= { dpsRTUv2 8106 }

dpsRTUv2p9106Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 106 clears."
	::= { dpsRTUv2 9106 }

dpsRTUv2p8107Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 107 is set."
	::= { dpsRTUv2 8107 }

dpsRTUv2p9107Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 107 clears."
	::= { dpsRTUv2 9107 }

dpsRTUv2p8108Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 108 is set."
	::= { dpsRTUv2 8108 }

dpsRTUv2p9108Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 108 clears."
	::= { dpsRTUv2 9108 }

dpsRTUv2p8109Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 109 is set."
	::= { dpsRTUv2 8109 }

dpsRTUv2p9109Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 109 clears."
	::= { dpsRTUv2 9109 }

dpsRTUv2p8110Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 110 is set."
	::= { dpsRTUv2 8110 }

dpsRTUv2p9110Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 110 clears."
	::= { dpsRTUv2 9110 }

dpsRTUv2p8111Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 111 is set."
	::= { dpsRTUv2 8111 }

dpsRTUv2p9111Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 111 clears."
	::= { dpsRTUv2 9111 }

dpsRTUv2p8112Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 112 is set."
	::= { dpsRTUv2 8112 }

dpsRTUv2p9112Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 112 clears."
	::= { dpsRTUv2 9112 }

dpsRTUv2p8113Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 113 is set."
	::= { dpsRTUv2 8113 }

dpsRTUv2p9113Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 113 clears."
	::= { dpsRTUv2 9113 }

dpsRTUv2p8114Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 114 is set."
	::= { dpsRTUv2 8114 }

dpsRTUv2p9114Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 114 clears."
	::= { dpsRTUv2 9114 }

dpsRTUv2p8115Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 115 is set."
	::= { dpsRTUv2 8115 }

dpsRTUv2p9115Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 115 clears."
	::= { dpsRTUv2 9115 }

dpsRTUv2p8116Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 116 is set."
	::= { dpsRTUv2 8116 }

dpsRTUv2p9116Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 116 clears."
	::= { dpsRTUv2 9116 }

dpsRTUv2p8117Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 117 is set."
	::= { dpsRTUv2 8117 }

dpsRTUv2p9117Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 117 clears."
	::= { dpsRTUv2 9117 }

dpsRTUv2p8118Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 118 is set."
	::= { dpsRTUv2 8118 }

dpsRTUv2p9118Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 118 clears."
	::= { dpsRTUv2 9118 }

dpsRTUv2p8119Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 119 is set."
	::= { dpsRTUv2 8119 }

dpsRTUv2p9119Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 119 clears."
	::= { dpsRTUv2 9119 }

dpsRTUv2p8120Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 120 is set."
	::= { dpsRTUv2 8120 }

dpsRTUv2p9120Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 120 clears."
	::= { dpsRTUv2 9120 }

dpsRTUv2p8121Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 121 is set."
	::= { dpsRTUv2 8121 }

dpsRTUv2p9121Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 121 clears."
	::= { dpsRTUv2 9121 }

dpsRTUv2p8122Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 122 is set."
	::= { dpsRTUv2 8122 }

dpsRTUv2p9122Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 122 clears."
	::= { dpsRTUv2 9122 }

dpsRTUv2p8123Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 123 is set."
	::= { dpsRTUv2 8123 }

dpsRTUv2p9123Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 123 clears."
	::= { dpsRTUv2 9123 }

dpsRTUv2p8124Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 124 is set."
	::= { dpsRTUv2 8124 }

dpsRTUv2p9124Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 124 clears."
	::= { dpsRTUv2 9124 }

dpsRTUv2p8125Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 125 is set."
	::= { dpsRTUv2 8125 }

dpsRTUv2p9125Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 125 clears."
	::= { dpsRTUv2 9125 }

dpsRTUv2p8126Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 126 is set."
	::= { dpsRTUv2 8126 }

dpsRTUv2p9126Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 126 clears."
	::= { dpsRTUv2 9126 }

dpsRTUv2p8127Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 127 is set."
	::= { dpsRTUv2 8127 }

dpsRTUv2p9127Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 127 clears."
	::= { dpsRTUv2 9127 }

dpsRTUv2p8128Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 128 is set."
	::= { dpsRTUv2 8128 }

dpsRTUv2p9128Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 128 clears."
	::= { dpsRTUv2 9128 }

dpsRTUv2p8129Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 1 minor under threshold is violated"
	::= { dpsRTUv2 8129 }

dpsRTUv2p9129Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 1 minor under threshold is restored"
	::= { dpsRTUv2 9129 }

dpsRTUv2p8130Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 1 minor over threshold is violated"
	::= { dpsRTUv2 8130 }

dpsRTUv2p9130Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 1 minor over threshold is restored"
	::= { dpsRTUv2 9130 }

dpsRTUv2p8131Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 1 major under threshold is violated"
	::= { dpsRTUv2 8131 }

dpsRTUv2p9131Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 1 major under threshold is restored"
	::= { dpsRTUv2 9131 }

dpsRTUv2p8132Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 1 major over threshold is violated"
	::= { dpsRTUv2 8132 }

dpsRTUv2p9132Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 1 major over threshold is restored"
	::= { dpsRTUv2 9132 }

dpsRTUv2p8133Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 133 is set."
	::= { dpsRTUv2 8133 }

dpsRTUv2p9133Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 133 clears."
	::= { dpsRTUv2 9133 }
	   
dpsRTUv2p8134Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 134 is set."
	::= { dpsRTUv2 8134 }

dpsRTUv2p9134Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 134 clears."
	::= { dpsRTUv2 9134 }
	   
dpsRTUv2p8135Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 135 is set."
	::= { dpsRTUv2 8135 }

dpsRTUv2p9135Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 135 clears."
	::= { dpsRTUv2 9135 }
	   
dpsRTUv2p8136Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 136 is set."
	::= { dpsRTUv2 8136 }

dpsRTUv2p9136Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 136 clears."
	::= { dpsRTUv2 9136 }
	   
dpsRTUv2p8137Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 137 is set."
	::= { dpsRTUv2 8137 }

dpsRTUv2p9137Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 137 clears."
	::= { dpsRTUv2 9137 }
	   
dpsRTUv2p8138Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 138 is set."
	::= { dpsRTUv2 8138 }

dpsRTUv2p9138Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 138 clears."
	::= { dpsRTUv2 9138 }
	   
dpsRTUv2p8139Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 139 is set."
	::= { dpsRTUv2 8139 }

dpsRTUv2p9139Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 139 clears."
	::= { dpsRTUv2 9139 }
	   
dpsRTUv2p8140Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 140 is set."
	::= { dpsRTUv2 8140 }

dpsRTUv2p9140Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 140 clears."
	::= { dpsRTUv2 9140 }
	   
dpsRTUv2p8141Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 141 is set."
	::= { dpsRTUv2 8141 }

dpsRTUv2p9141Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 141 clears."
	::= { dpsRTUv2 9141 }
	   
dpsRTUv2p8142Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 142 is set."
	::= { dpsRTUv2 8142 }

dpsRTUv2p9142Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 142 clears."
	::= { dpsRTUv2 9142 }
	   
dpsRTUv2p8143Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 143 is set."
	::= { dpsRTUv2 8143 }

dpsRTUv2p9143Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 143 clears."
	::= { dpsRTUv2 9143 }
	   
dpsRTUv2p8144Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 144 is set."
	::= { dpsRTUv2 8144 }

dpsRTUv2p9144Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 144 clears."
	::= { dpsRTUv2 9144 }
	   
dpsRTUv2p8145Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 145 is set."
	::= { dpsRTUv2 8145 }

dpsRTUv2p9145Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 145 clears."
	::= { dpsRTUv2 9145 }
	   
dpsRTUv2p8146Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 146 is set."
	::= { dpsRTUv2 8146 }

dpsRTUv2p9146Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 146 clears."
	::= { dpsRTUv2 9146 }
	   
dpsRTUv2p8147Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 147 is set."
	::= { dpsRTUv2 8147 }

dpsRTUv2p9147Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 147 clears."
	::= { dpsRTUv2 9147 }
	   
dpsRTUv2p8148Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 148 is set."
	::= { dpsRTUv2 8148 }

dpsRTUv2p9148Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 148 clears."
	::= { dpsRTUv2 9148 }
	   
dpsRTUv2p8149Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 149 is set."
	::= { dpsRTUv2 8149 }

dpsRTUv2p9149Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 149 clears."
	::= { dpsRTUv2 9149 }
	   
dpsRTUv2p8150Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 150 is set."
	::= { dpsRTUv2 8150 }

dpsRTUv2p9150Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 150 clears."
	::= { dpsRTUv2 9150 }
	   
dpsRTUv2p8151Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 151 is set."
	::= { dpsRTUv2 8151 }

dpsRTUv2p9151Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 151 clears."
	::= { dpsRTUv2 9151 }
	   
dpsRTUv2p8152Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 152 is set."
	::= { dpsRTUv2 8152 }

dpsRTUv2p9152Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 152 clears."
	::= { dpsRTUv2 9152 }
	   
dpsRTUv2p8153Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 153 is set."
	::= { dpsRTUv2 8153 }

dpsRTUv2p9153Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 153 clears."
	::= { dpsRTUv2 9153 }
	   
dpsRTUv2p8154Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 154 is set."
	::= { dpsRTUv2 8154 }

dpsRTUv2p9154Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 154 clears."
	::= { dpsRTUv2 9154 }
	   
dpsRTUv2p8155Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 155 is set."
	::= { dpsRTUv2 8155 }

dpsRTUv2p9155Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 155 clears."
	::= { dpsRTUv2 9155 }
	   
dpsRTUv2p8156Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 156 is set."
	::= { dpsRTUv2 8156 }

dpsRTUv2p9156Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 156 clears."
	::= { dpsRTUv2 9156 }
	   
dpsRTUv2p8157Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 157 is set."
	::= { dpsRTUv2 8157 }

dpsRTUv2p9157Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 157 clears."
	::= { dpsRTUv2 9157 }
	   
dpsRTUv2p8158Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 158 is set."
	::= { dpsRTUv2 8158 }

dpsRTUv2p9158Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 158 clears."
	::= { dpsRTUv2 9158 }
	   
dpsRTUv2p8159Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 159 is set."
	::= { dpsRTUv2 8159 }

dpsRTUv2p9159Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 159 clears."
	::= { dpsRTUv2 9159 }
	   
dpsRTUv2p8160Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 160 is set."
	::= { dpsRTUv2 8160 }

dpsRTUv2p9160Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 160 clears."
	::= { dpsRTUv2 9160 }
	   
dpsRTUv2p8161Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 161 is set."
	::= { dpsRTUv2 8161 }

dpsRTUv2p9161Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 161 clears."
	::= { dpsRTUv2 9161 }
	   
dpsRTUv2p8162Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 162 is set."
	::= { dpsRTUv2 8162 }

dpsRTUv2p9162Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 162 clears."
	::= { dpsRTUv2 9162 }
	   
dpsRTUv2p8163Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 163 is set."
	::= { dpsRTUv2 8163 }

dpsRTUv2p9163Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 163 clears."
	::= { dpsRTUv2 9163 }
	   
dpsRTUv2p8164Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 164 is set."
	::= { dpsRTUv2 8164 }

dpsRTUv2p9164Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 164 clears."
	::= { dpsRTUv2 9164 }
	   
dpsRTUv2p8165Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 165 is set."
	::= { dpsRTUv2 8165 }

dpsRTUv2p9165Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 165 clears."
	::= { dpsRTUv2 9165 }
	   
dpsRTUv2p8166Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 166 is set."
	::= { dpsRTUv2 8166 }

dpsRTUv2p9166Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 166 clears."
	::= { dpsRTUv2 9166 }
	   
dpsRTUv2p8167Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 167 is set."
	::= { dpsRTUv2 8167 }

dpsRTUv2p9167Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 167 clears."
	::= { dpsRTUv2 9167 }
	   
dpsRTUv2p8168Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 168 is set."
	::= { dpsRTUv2 8168 }

dpsRTUv2p9168Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 168 clears."
	::= { dpsRTUv2 9168 }
	   
dpsRTUv2p8169Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 169 is set."
	::= { dpsRTUv2 8169 }

dpsRTUv2p9169Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 169 clears."
	::= { dpsRTUv2 9169 }
	   
dpsRTUv2p8170Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 170 is set."
	::= { dpsRTUv2 8170 }

dpsRTUv2p9170Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 170 clears."
	::= { dpsRTUv2 9170 }
	   
dpsRTUv2p8171Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 171 is set."
	::= { dpsRTUv2 8171 }

dpsRTUv2p9171Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 171 clears."
	::= { dpsRTUv2 9171 }
	   
dpsRTUv2p8172Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 172 is set."
	::= { dpsRTUv2 8172 }

dpsRTUv2p9172Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 172 clears."
	::= { dpsRTUv2 9172 }
	   
dpsRTUv2p8173Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 173 is set."
	::= { dpsRTUv2 8173 }

dpsRTUv2p9173Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 173 clears."
	::= { dpsRTUv2 9173 }
	   
dpsRTUv2p8174Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 174 is set."
	::= { dpsRTUv2 8174 }

dpsRTUv2p9174Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 174 clears."
	::= { dpsRTUv2 9174 }
	   
dpsRTUv2p8175Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 175 is set."
	::= { dpsRTUv2 8175 }

dpsRTUv2p9175Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 175 clears."
	::= { dpsRTUv2 9175 }
	   
dpsRTUv2p8176Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 176 is set."
	::= { dpsRTUv2 8176 }

dpsRTUv2p9176Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 176 clears."
	::= { dpsRTUv2 9176 }

dpsRTUv2p8193Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 2 minor under threshold is violated"
	::= { dpsRTUv2 8193 }

dpsRTUv2p9193Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 2 minor under threshold is restored"
	::= { dpsRTUv2 9193 }

dpsRTUv2p8194Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 2 minor over threshold is violated"
	::= { dpsRTUv2 8194 }

dpsRTUv2p9194Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 2 minor over threshold is restored"
	::= { dpsRTUv2 9194 }

dpsRTUv2p8195Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 2 major under threshold is violated"
	::= { dpsRTUv2 8195 }

dpsRTUv2p9195Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 2 major under threshold is restored"
	::= { dpsRTUv2 9195 }

dpsRTUv2p8196Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 2 major over threshold is violated"
	::= { dpsRTUv2 8196 }

dpsRTUv2p9196Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 2 major over threshold is restored"
	::= { dpsRTUv2 9196 }

dpsRTUv2p8197Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 197 is set."
	::= { dpsRTUv2 8197 }

dpsRTUv2p9197Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 197 clears."
	::= { dpsRTUv2 9197 }

dpsRTUv2p8198Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 198 is set."
	::= { dpsRTUv2 8198 }

dpsRTUv2p9198Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 198 clears."
	::= { dpsRTUv2 9198 }

dpsRTUv2p8199Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 199 is set."
	::= { dpsRTUv2 8199 }

dpsRTUv2p9199Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 199 clears."
	::= { dpsRTUv2 9199 }

dpsRTUv2p8200Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 200 is set."
	::= { dpsRTUv2 8200 }

dpsRTUv2p9200Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 200 clears."
	::= { dpsRTUv2 9200 }

dpsRTUv2p8201Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 201 is set."
	::= { dpsRTUv2 8201 }

dpsRTUv2p9201Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 201 clears."
	::= { dpsRTUv2 9201 }

dpsRTUv2p8202Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 202 is set."
	::= { dpsRTUv2 8202 }

dpsRTUv2p9202Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 202 clears."
	::= { dpsRTUv2 9202 }

dpsRTUv2p8203Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 203 is set."
	::= { dpsRTUv2 8203 }

dpsRTUv2p9203Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 203 clears."
	::= { dpsRTUv2 9203 }

dpsRTUv2p8204Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 204 is set."
	::= { dpsRTUv2 8204 }

dpsRTUv2p9204Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 204 clears."
	::= { dpsRTUv2 9204 }

dpsRTUv2p8205Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 205 is set."
	::= { dpsRTUv2 8205 }

dpsRTUv2p9205Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 205 clears."
	::= { dpsRTUv2 9205 }

dpsRTUv2p8206Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 206 is set."
	::= { dpsRTUv2 8206 }

dpsRTUv2p9206Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 206 clears."
	::= { dpsRTUv2 9206 }

dpsRTUv2p8207Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 207 is set."
	::= { dpsRTUv2 8207 }

dpsRTUv2p9207Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 207 clears."
	::= { dpsRTUv2 9207 }

dpsRTUv2p8208Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 208 is set."
	::= { dpsRTUv2 8208 }

dpsRTUv2p9208Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 208 clears."
	::= { dpsRTUv2 9208 }

dpsRTUv2p8209Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 209 is set."
	::= { dpsRTUv2 8209 }

dpsRTUv2p9209Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 209 clears."
	::= { dpsRTUv2 9209 }

dpsRTUv2p8210Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 210 is set."
	::= { dpsRTUv2 8210 }

dpsRTUv2p9210Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 210 clears."
	::= { dpsRTUv2 9210 }

dpsRTUv2p8211Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 211 is set."
	::= { dpsRTUv2 8211 }

dpsRTUv2p9211Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 211 clears."
	::= { dpsRTUv2 9211 }

dpsRTUv2p8212Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 212 is set."
	::= { dpsRTUv2 8212 }

dpsRTUv2p9212Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 212 clears."
	::= { dpsRTUv2 9212 }

dpsRTUv2p8213Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 213 is set."
	::= { dpsRTUv2 8213 }

dpsRTUv2p9213Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 213 clears."
	::= { dpsRTUv2 9213 }

dpsRTUv2p8214Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 214 is set."
	::= { dpsRTUv2 8214 }

dpsRTUv2p9214Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 214 clears."
	::= { dpsRTUv2 9214 }

dpsRTUv2p8215Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 215 is set."
	::= { dpsRTUv2 8215 }

dpsRTUv2p9215Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 215 clears."
	::= { dpsRTUv2 9215 }

dpsRTUv2p8216Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 216 is set."
	::= { dpsRTUv2 8216 }

dpsRTUv2p9216Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 216 clears."
	::= { dpsRTUv2 9216 }

dpsRTUv2p8217Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 217 is set."
	::= { dpsRTUv2 8217 }

dpsRTUv2p9217Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 217 clears."
	::= { dpsRTUv2 9217 }

dpsRTUv2p8218Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 218 is set."
	::= { dpsRTUv2 8218 }

dpsRTUv2p9218Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 218 clears."
	::= { dpsRTUv2 9218 }

dpsRTUv2p8219Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 219 is set."
	::= { dpsRTUv2 8219 }

dpsRTUv2p9219Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 219 clears."
	::= { dpsRTUv2 9219 }

dpsRTUv2p8220Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 220 is set."
	::= { dpsRTUv2 8220 }

dpsRTUv2p9220Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 220 clears."
	::= { dpsRTUv2 9220 }

dpsRTUv2p8221Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 221 is set."
	::= { dpsRTUv2 8221 }

dpsRTUv2p9221Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 221 clears."
	::= { dpsRTUv2 9221 }

dpsRTUv2p8222Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 222 is set."
	::= { dpsRTUv2 8222 }

dpsRTUv2p9222Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 222 clears."
	::= { dpsRTUv2 9222 }

dpsRTUv2p8223Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 223 is set."
	::= { dpsRTUv2 8223 }

dpsRTUv2p9223Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 223 clears."
	::= { dpsRTUv2 9223 }

dpsRTUv2p8224Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 224 is set."
	::= { dpsRTUv2 8224 }

dpsRTUv2p9224Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 224 clears."
	::= { dpsRTUv2 9224 }

dpsRTUv2p8225Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 225 is set."
	::= { dpsRTUv2 8225 }

dpsRTUv2p9225Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 225 clears."
	::= { dpsRTUv2 9225 }

dpsRTUv2p8226Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 226 is set."
	::= { dpsRTUv2 8226 }

dpsRTUv2p9226Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 226 clears."
	::= { dpsRTUv2 9226 }

dpsRTUv2p8227Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 227 is set."
	::= { dpsRTUv2 8227 }

dpsRTUv2p9227Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 227 clears."
	::= { dpsRTUv2 9227 }

dpsRTUv2p8228Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 228 is set."
	::= { dpsRTUv2 8228 }

dpsRTUv2p9228Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 228 clears."
	::= { dpsRTUv2 9228 }

dpsRTUv2p8229Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 229 is set."
	::= { dpsRTUv2 8229 }

dpsRTUv2p9229Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 229 clears."
	::= { dpsRTUv2 9229 }

dpsRTUv2p8230Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 230 is set."
	::= { dpsRTUv2 8230 }

dpsRTUv2p9230Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 230 clears."
	::= { dpsRTUv2 9230 }

dpsRTUv2p8231Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 231 is set."
	::= { dpsRTUv2 8231 }

dpsRTUv2p9231Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 231 clears."
	::= { dpsRTUv2 9231 }

dpsRTUv2p8232Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 232 is set."
	::= { dpsRTUv2 8232 }

dpsRTUv2p9232Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 232 clears."
	::= { dpsRTUv2 9232 }

dpsRTUv2p8233Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 233 is set."
	::= { dpsRTUv2 8233 }

dpsRTUv2p9233Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 233 clears."
	::= { dpsRTUv2 9233 }

dpsRTUv2p8234Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 234 is set."
	::= { dpsRTUv2 8234 }

dpsRTUv2p9234Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 234 clears."
	::= { dpsRTUv2 9234 }

dpsRTUv2p8235Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 235 is set."
	::= { dpsRTUv2 8235 }

dpsRTUv2p9235Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 235 clears."
	::= { dpsRTUv2 9235 }

dpsRTUv2p8236Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 236 is set."
	::= { dpsRTUv2 8236 }

dpsRTUv2p9236Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 236 clears."
	::= { dpsRTUv2 9236 }

dpsRTUv2p8237Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 237 is set."
	::= { dpsRTUv2 8237 }

dpsRTUv2p9237Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 237 clears."
	::= { dpsRTUv2 9237 }

dpsRTUv2p8238Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 238 is set."
	::= { dpsRTUv2 8238 }

dpsRTUv2p9238Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 238 clears."
	::= { dpsRTUv2 9238 }

dpsRTUv2p8239Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 239 is set."
	::= { dpsRTUv2 8239 }

dpsRTUv2p9239Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 239 clears."
	::= { dpsRTUv2 9239 }

dpsRTUv2p8240Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 240 is set."
	::= { dpsRTUv2 8240 }

dpsRTUv2p9240Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 240 clears."
	::= { dpsRTUv2 9240 }

dpsRTUv2p8241Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 241 is set."
	::= { dpsRTUv2 8241 }

dpsRTUv2p9241Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 241 clears."
	::= { dpsRTUv2 9241 }

dpsRTUv2p8242Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 242 is set."
	::= { dpsRTUv2 8242 }

dpsRTUv2p9242Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 242 clears."
	::= { dpsRTUv2 9242 }

dpsRTUv2p8243Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 243 is set."
	::= { dpsRTUv2 8243 }

dpsRTUv2p9243Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 243 clears."
	::= { dpsRTUv2 9243 }

dpsRTUv2p8244Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 244 is set."
	::= { dpsRTUv2 8244 }

dpsRTUv2p9244Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 244 clears."
	::= { dpsRTUv2 9244 }

dpsRTUv2p8245Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 245 is set."
	::= { dpsRTUv2 8245 }

dpsRTUv2p9245Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 245 clears."
	::= { dpsRTUv2 9245 }

dpsRTUv2p8246Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 246 is set."
	::= { dpsRTUv2 8246 }

dpsRTUv2p9246Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 246 clears."
	::= { dpsRTUv2 9246 }

dpsRTUv2p8247Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 247 is set."
	::= { dpsRTUv2 8247 }

dpsRTUv2p9247Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 247 clears."
	::= { dpsRTUv2 9247 }

dpsRTUv2p8248Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 248 is set."
	::= { dpsRTUv2 8248 }

dpsRTUv2p9248Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 248 clears."
	::= { dpsRTUv2 9248 }

dpsRTUv2p8249Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 249 is set."
	::= { dpsRTUv2 8249 }

dpsRTUv2p9249Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 249 clears."
	::= { dpsRTUv2 9249 }

dpsRTUv2p8250Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 250 is set."
	::= { dpsRTUv2 8250 }

dpsRTUv2p9250Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 250 clears."
	::= { dpsRTUv2 9250 }

dpsRTUv2p8251Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 251 is set."
	::= { dpsRTUv2 8251 }

dpsRTUv2p9251Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 251 clears."
	::= { dpsRTUv2 9251 }

dpsRTUv2p8252Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 252 is set."
	::= { dpsRTUv2 8252 }

dpsRTUv2p9252Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 252 clears."
	::= { dpsRTUv2 9252 }

dpsRTUv2p8253Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 253 is set."
	::= { dpsRTUv2 8253 }

dpsRTUv2p9253Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 253 clears."
	::= { dpsRTUv2 9253 }

dpsRTUv2p8254Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 254 is set."
	::= { dpsRTUv2 8254 }

dpsRTUv2p9254Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 254 clears."
	::= { dpsRTUv2 9254 }

dpsRTUv2p8255Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 255 is set."
	::= { dpsRTUv2 8255 }

dpsRTUv2p9255Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 255 clears."
	::= { dpsRTUv2 9255 }

dpsRTUv2p8256Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 256 is set."
	::= { dpsRTUv2 8256 }

dpsRTUv2p9256Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when discrete point 256 clears."
	::= { dpsRTUv2 9256 }

dpsRTUv2p8257Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 3 minor under threshold is violated"
	::= { dpsRTUv2 8257 }

dpsRTUv2p9257Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 3 minor under threshold is restored"
	::= { dpsRTUv2 9257 }

dpsRTUv2p8258Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 3 minor over threshold is violated"
	::= { dpsRTUv2 8258 }

dpsRTUv2p9258Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 3 minor over threshold is restored"
	::= { dpsRTUv2 9258 }

dpsRTUv2p8259Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 3 major under threshold is violated"
	::= { dpsRTUv2 8259 }

dpsRTUv2p9259Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 3 major under threshold is restored"
	::= { dpsRTUv2 9259 }

dpsRTUv2p8260Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 3 major over threshold is violated"
	::= { dpsRTUv2 8260 }

dpsRTUv2p9260Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 3 major over threshold is restored"
	::= { dpsRTUv2 9260 }

dpsRTUv2p8321Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 4 minor under threshold is violated"
	::= { dpsRTUv2 8321 }

dpsRTUv2p9321Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 4 minor under threshold is restored"
	::= { dpsRTUv2 9321 }

dpsRTUv2p8322Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 4 minor over threshold is violated"
	::= { dpsRTUv2 8322 }

dpsRTUv2p9322Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 4 minor over threshold is restored"
	::= { dpsRTUv2 9322 }

dpsRTUv2p8323Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 4 major under threshold is violated"
	::= { dpsRTUv2 8323 }

dpsRTUv2p9323Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 4 major under threshold is restored"
	::= { dpsRTUv2 9323 }

dpsRTUv2p8324Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 4 major over threshold is violated"
	::= { dpsRTUv2 8324 }

dpsRTUv2p9324Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 4 major over threshold is restored"
	::= { dpsRTUv2 9324 }

dpsRTUv2p8385Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 5 minor under threshold is violated"
	::= { dpsRTUv2 8385 }

dpsRTUv2p9385Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 5 minor under threshold is restored"
	::= { dpsRTUv2 9385 }

dpsRTUv2p8386Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 5 minor over threshold is violated"
	::= { dpsRTUv2 8386 }

dpsRTUv2p9386Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 5 minor over threshold is restored"
	::= { dpsRTUv2 9386 }

dpsRTUv2p8387Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 5 major under threshold is violated"
	::= { dpsRTUv2 8387 }

dpsRTUv2p9387Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 5 major under threshold is restored"
	::= { dpsRTUv2 9387 }

dpsRTUv2p8388Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 5 major over threshold is violated"
	::= { dpsRTUv2 8388 }

dpsRTUv2p9388Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 5 major over threshold is restored"
	::= { dpsRTUv2 9388 }

dpsRTUv2p8449Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 6 minor under threshold is violated"
	::= { dpsRTUv2 8449 }

dpsRTUv2p9449Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 6 minor under threshold is restored"
	::= { dpsRTUv2 9449 }

dpsRTUv2p8450Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 6 minor over threshold is violated"
	::= { dpsRTUv2 8450 }

dpsRTUv2p9450Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 6 minor over threshold is restored"
	::= { dpsRTUv2 9450 }

dpsRTUv2p8451Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 6 major under threshold is violated"
	::= { dpsRTUv2 8451 }

dpsRTUv2p9451Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 6 major under threshold is restored"
	::= { dpsRTUv2 9451 }

dpsRTUv2p8452Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 6 major over threshold is violated"
	::= { dpsRTUv2 8452 }

dpsRTUv2p9452Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 6 major over threshold is restored"
	::= { dpsRTUv2 9452 }

dpsRTUv2p8513Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 7 minor under threshold is violated"
	::= { dpsRTUv2 8513 }

dpsRTUv2p9513Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 7 minor under threshold is restored"
	::= { dpsRTUv2 9513 }

dpsRTUv2p8514Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 7 minor over threshold is violated"
	::= { dpsRTUv2 8514 }

dpsRTUv2p9514Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 7 minor over threshold is restored"
	::= { dpsRTUv2 9514 }

dpsRTUv2p8515Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 7 major under threshold is violated"
	::= { dpsRTUv2 8515 }

dpsRTUv2p9515Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 7 major under threshold is restored"
	::= { dpsRTUv2 9515 }

dpsRTUv2p8516Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 7 major over threshold is violated"
	::= { dpsRTUv2 8516 }

dpsRTUv2p9516Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 7 major over threshold is restored"
	::= { dpsRTUv2 9516 }

dpsRTUv2p8577Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 8 minor under threshold is violated"
	::= { dpsRTUv2 8577 }

dpsRTUv2p9577Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 8 minor under threshold is restored"
	::= { dpsRTUv2 9577 }

dpsRTUv2p8578Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 8 minor over threshold is violated"
	::= { dpsRTUv2 8578 }

dpsRTUv2p9578Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 8 minor over threshold is restored"
	::= { dpsRTUv2 9578 }

dpsRTUv2p8579Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 8 major under threshold is violated"
	::= { dpsRTUv2 8579 }

dpsRTUv2p9579Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 8 major under threshold is restored"
	::= { dpsRTUv2 9579 }

dpsRTUv2p8580Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 8 major over threshold is violated"
	::= { dpsRTUv2 8580 }

dpsRTUv2p9580Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when channel 8 major over threshold is restored"
	::= { dpsRTUv2 9580 }

dpsRTUv2p8641Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when control 1 is latched."
	::= { dpsRTUv2 8641 }

dpsRTUv2p9641Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when control 1 is released."
	::= { dpsRTUv2 9641 }

dpsRTUv2p8642Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when control 2 is latched."
	::= { dpsRTUv2 8642 }

dpsRTUv2p9642Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when control 2 is released."
	::= { dpsRTUv2 9642 }

dpsRTUv2p8657Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Timed Tick: set."
	::= { dpsRTUv2 8657 }

dpsRTUv2p9657Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Timed Tick: cleared."
	::= { dpsRTUv2 9657 }

dpsRTUv2p8659Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Network Time Server: set."
	::= { dpsRTUv2 8659 }

dpsRTUv2p9659Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Network Time Server: cleared."
	::= { dpsRTUv2 9659 }

dpsRTUv2p8660Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Accumulation Event: set."
	::= { dpsRTUv2 8660 }

dpsRTUv2p9660Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Accumulation Event: cleared."
	::= { dpsRTUv2 9660 }

dpsRTUv2p8661Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Duplicate IP Address: set."
	::= { dpsRTUv2 8661 }

dpsRTUv2p9661Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Duplicate IP Address: cleared."
	::= { dpsRTUv2 9661 }

dpsRTUv2p8662Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "External Sensor Down: set."
	::= { dpsRTUv2 8662 }

dpsRTUv2p9662Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "External Sensor Down: cleared."
	::= { dpsRTUv2 9662 }

dpsRTUv2p8673Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Power Up: set."
	::= { dpsRTUv2 8673 }

dpsRTUv2p9673Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Power Up: cleared."
	::= { dpsRTUv2 9673 }

dpsRTUv2p8676Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Lost Provisioning: set."
	::= { dpsRTUv2 8676 }

dpsRTUv2p9676Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Lost Provisioning: cleared."
	::= { dpsRTUv2 9676 }

dpsRTUv2p8677Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "DCP Poller Inactive: set."
	::= { dpsRTUv2 8677 }

dpsRTUv2p9677Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "DCP Poller Inactive: cleared."
	::= { dpsRTUv2 9677 }

dpsRTUv2p8678Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "T1 WAN Not Active: set."
	::= { dpsRTUv2 8678 }

dpsRTUv2p9678Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "T1 WAN Not Active: cleared."
	::= { dpsRTUv2 9678 }

dpsRTUv2p8679Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "LAN Not Active: set."
	::= { dpsRTUv2 8679 }

dpsRTUv2p9679Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "LAN Not Active: cleared."
	::= { dpsRTUv2 9679 }

dpsRTUv2p8680Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "LAN Link Not Active: set."
	::= { dpsRTUv2 8680 }

dpsRTUv2p9680Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "LAN Link Not Active: cleared."
	::= { dpsRTUv2 9680 }

dpsRTUv2p8683Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "SNMP Trap not Sent: set."
	::= { dpsRTUv2 8683 }

dpsRTUv2p9683Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "SNMP Trap not Sent: cleared."
	::= { dpsRTUv2 9683 }

dpsRTUv2p8684Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Pager Que Overflow: set."
	::= { dpsRTUv2 8684 }

dpsRTUv2p9684Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Pager Que Overflow: cleared."
	::= { dpsRTUv2 9684 }

dpsRTUv2p8685Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Notification Failed: set."
	::= { dpsRTUv2 8685 }

dpsRTUv2p9685Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Notification Failed: cleared."
	::= { dpsRTUv2 9685 }

dpsRTUv2p8686Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Craft RcvQ full: set."
	::= { dpsRTUv2 8686 }

dpsRTUv2p9686Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Craft RcvQ full: cleared."
	::= { dpsRTUv2 9686 }

dpsRTUv2p8688Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Data 1 RcvQ full: set."
	::= { dpsRTUv2 8688 }

dpsRTUv2p9688Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Data 1 RcvQ full: cleared."
	::= { dpsRTUv2 9688 }

dpsRTUv2p8696Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "NGDdx 1 Fail: set."
	::= { dpsRTUv2 8696 }

dpsRTUv2p9696Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "NGDdx 1 Fail: cleared."
	::= { dpsRTUv2 9696 }

dpsRTUv2p8697Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "NGDdx 2 Fail: set."
	::= { dpsRTUv2 8697 }

dpsRTUv2p9697Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "NGDdx 2 Fail: cleared."
	::= { dpsRTUv2 9697 }

dpsRTUv2p8698Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "NGDdx 3 Fail: set."
	::= { dpsRTUv2 8698 }

dpsRTUv2p9698Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "NGDdx 3 Fail: cleared."
	::= { dpsRTUv2 9698 }

dpsRTUv2p8703Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Craft Timeout: set."
	::= { dpsRTUv2 8703 }

dpsRTUv2p9703Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Craft Timeout: cleared."
	::= { dpsRTUv2 9703 }

dpsRTUv2p8704Set NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Event Que Full: set."
	::= { dpsRTUv2 8704 }

dpsRTUv2p9704Clr NOTIFICATION-TYPE
	OBJECTS	 {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Event Que Full: cleared."
	::= { dpsRTUv2 9704 } 

END
