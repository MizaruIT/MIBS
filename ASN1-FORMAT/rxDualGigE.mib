-- Ericsson Television Limited Standard MIB disclaimer
-- ###################################################
-- SNMP MIBs for Ericsson Television Limited products are developed 
-- primarily for use by Ericsson Television Limited control solutions.
-- Where MIBs are provided to a third party or other non-Ericsson 
-- Television Limited person, for the purposes of their development 
-- of a non-Ericsson Television Limited control or monitoring solution, 
-- they are provided free of charge, and without obligation on the
-- part of Ericsson Television Limited to offer priority support, or
-- changes to suit the third party.

RX-DUAL-GIGE DEFINITIONS ::= BEGIN

IMPORTS
   OBJECT-TYPE 
	FROM RFC-1212
   modules 
	FROM ETV-Base-MIB;

etv-rxDualGigE OBJECT IDENTIFIER ::= { modules 1087 }

rcMLR    OBJECT-TYPE
    SYNTAX          INTEGER { initialVersion(1) }
    ACCESS          read-only
    STATUS          mandatory
    DESCRIPTION     "MDI - Media Loss Rate (MLR)"
    ::= { etv-rxDualGigE 1 }

	rcDF    OBJECT-TYPE
    SYNTAX          INTEGER { initialVersion(1) }
    ACCESS          read-only
    STATUS          mandatory
    DESCRIPTION     "MDI - Delay Factor (DF)"
    ::= { etv-rxDualGigE 2 }
END
