--
-- HUAWEI-ATM-OAM-MIB.mib
-- MIB generated by MG-SOFT Visual MIB Builder Version 2.5 Build 225
-- Thursday, April 10, 2003 at 08:03:05
--

	HUAWEI-ATM-OAM-MIB DEFINITIONS ::= BEGIN

		IMPORTS 
			AtmVpIdentifier, AtmVcIdentifier			
				FROM ATM-TC-MIB			
			huaweiUtility			
				FROM HUAWEI-MIB			
			ifIndex			
				FROM IF-MIB			
			OBJECT-TYPE, MODULE-IDENTITY, NOTIFICATION-TYPE			
				FROM SNMPv2-SMI			
			DateAndTime, RowStatus			
				FROM SNMPv2-TC;
	
	
		hwAtmOam MODULE-IDENTITY
			LAST-UPDATED "190304280900Z"
			ORGANIZATION
				"Huawei Technologies co.,Ltd."
			CONTACT-INFO
				"Kefa Road,
				Fx-Net Dep, Huawei Technologies Co.,Ltd.
				Science-Based Industrial Park, 
				Nanshan District,Shenzhen  P.R. China
				http://www.huawei.com
				Zip:518057
				"
			DESCRIPTION
				"
				huawei hwAtmOam mib.
				"
			REVISION "200211290900Z"
			DESCRIPTION
				"It initilized by FixNet Mib Group .
				"
			::= { huaweiUtility 11 }
		
	
	
--
-- Node definitions
--
	
		hwAtmOamMibObjects OBJECT IDENTIFIER ::= { hwAtmOam 1 }
		
		hwAtmOamPointTable OBJECT-TYPE
			SYNTAX SEQUENCE OF HwAtmOamPointEntry
			MAX-ACCESS not-accessible
			STATUS current
			DESCRIPTION
				"Table of OAM point.
				functions Decripted as:
				"
			::= { hwAtmOamMibObjects 1 }
		
		hwAtmOamPointEntry OBJECT-TYPE
			SYNTAX HwAtmOamPointEntry
			MAX-ACCESS not-accessible
			STATUS current
			DESCRIPTION
				"OAM point table entry."
			INDEX { ifIndex,hwAtmOamPointVPI, hwAtmOamPointVCI }
			::= { hwAtmOamPointTable 1 }
		
		HwAtmOamPointEntry ::=
			SEQUENCE { 
				hwAtmOamPointVPI
					AtmVpIdentifier,
				hwAtmOamPointVCI
					AtmVcIdentifier,
				hwAtmOamPointType
					INTEGER,
				hwAtmOamPointAdminStatus
					INTEGER,
				hwAtmOamAlarmType
					INTEGER,
				hwAtmOamCfgFlag
					INTEGER,
				hwAtmOamFmStatus
					INTEGER,
				hwAtmOamFmStatusDateTime
					DateAndTime,
				hwAtmOamPointRowStatus
					RowStatus
			 }

		hwAtmOamPointVPI OBJECT-TYPE
			SYNTAX AtmVpIdentifier
			MAX-ACCESS accessible-for-notify
			STATUS current
			DESCRIPTION
				"vpi."
			::= { hwAtmOamPointEntry 1 }
		
		hwAtmOamPointVCI OBJECT-TYPE
			SYNTAX AtmVcIdentifier
			MAX-ACCESS accessible-for-notify
			STATUS current
			DESCRIPTION
				"vci. 
				if vci = 0, means that this is a F4 point"
			::= { hwAtmOamPointEntry 2 }
		
		hwAtmOamPointType OBJECT-TYPE
			SYNTAX INTEGER
				{
				e2e(1),
				segment(2),
				e2eInter(3),
				segmentInter(4)
				}
			MAX-ACCESS read-create
			STATUS current
			DESCRIPTION
				"OAM point type. 
				
				e2e(1)          : e-t-e end point.
				segment(2)      : segment end point.
				e2e-inter(3)    : connection point within two e-t-e points.
				segment-inter(4): connection point within two segment points."
			DEFVAL { segment }
			::= { hwAtmOamPointEntry 3 }
		
		hwAtmOamPointAdminStatus OBJECT-TYPE
			SYNTAX INTEGER
				{
				up(1),
				down(2)
				}
			MAX-ACCESS read-create
			STATUS current
			DESCRIPTION
				"up(1) means enable; down(2) means disable."
			DEFVAL { up }
			::= { hwAtmOamPointEntry 4 }
		
		hwAtmOamAlarmType OBJECT-TYPE
			SYNTAX INTEGER
				{
				noAlarm(0),
				receiveAisCell(1),
				receiveRdiCell(2),
				loc(4),
				f4Ais(8),
				portAlarm(16)
				}
			MAX-ACCESS read-only
			STATUS current
			DESCRIPTION
				"OAM point alarm type.
				noAlarm(0)          : no alarm.
				receiveAisCell(0x01): received AIS cell.
				receiveRdiCell(0x02): received RDI cell.
				loc(0x04)           : lost of continuty(CC failed).
				f4Ais(0x08)         : F4 layer AIS alarm. only for F5 point.
				portAlarm(0x10)     : F1~F3 layer alarm.
				All Alarms can happen at same time which dispayed as the relate bit "
			::= { hwAtmOamPointEntry 5 }
		
		hwAtmOamCfgFlag OBJECT-TYPE
			SYNTAX INTEGER
				{
				running(1),
				recovering(2)
				}
			MAX-ACCESS read-only
			STATUS current
			DESCRIPTION
				"OAM point configure recovering flag.
				running(1)   : OAM point in running stage.
				recovering(2): OAM point in recovering stage.
				
				"
			::= { hwAtmOamPointEntry 6 }
		
		hwAtmOamFmStatus OBJECT-TYPE
			SYNTAX INTEGER
				{
				normal(1),
				ais(2),
				rdi(3)
				}
			MAX-ACCESS read-only
			STATUS current
			DESCRIPTION
				"OAM point FM status."
			::= { hwAtmOamPointEntry 7 }
		
		hwAtmOamFmStatusDateTime OBJECT-TYPE
			SYNTAX DateAndTime
			MAX-ACCESS read-only
			STATUS current
			DESCRIPTION
				"The time that the OAM point entered this FM status."
			::= { hwAtmOamPointEntry 8 }
		
		hwAtmOamPointRowStatus OBJECT-TYPE
			SYNTAX RowStatus
			MAX-ACCESS read-create
			STATUS current
			DESCRIPTION
				"OAM point table row status."
			::= { hwAtmOamPointEntry 9 }
		
		hwAtmOamCcTable OBJECT-TYPE
			SYNTAX SEQUENCE OF HwAtmOamCcEntry
			MAX-ACCESS not-accessible
			STATUS current
			DESCRIPTION
				"Table of CC end point.
				see the define  of the OAM point table .
				"
			::= { hwAtmOamMibObjects 2 }
		
		hwAtmOamCcEntry OBJECT-TYPE
			SYNTAX HwAtmOamCcEntry
			MAX-ACCESS not-accessible
			STATUS current
			DESCRIPTION
				"OAM CC end point table entry."
			INDEX { ifIndex,hwAtmOamCcVPI, hwAtmOamCcVCI }
			::= { hwAtmOamCcTable 1 }
		
		HwAtmOamCcEntry ::=
			SEQUENCE { 
				hwAtmOamCcVPI
					AtmVpIdentifier,
				hwAtmOamCcVCI
					AtmVcIdentifier,
				hwAtmOamCcDirection
					INTEGER,
				hwAtmOamConfType
					INTEGER,
				hwAtmOamCcAdminStatus
					INTEGER,
				hwAtmOamCcRowStatus
					RowStatus
			 }

		hwAtmOamCcVPI OBJECT-TYPE
			SYNTAX AtmVpIdentifier
			MAX-ACCESS not-accessible
			STATUS current
			DESCRIPTION
				"vpi."
			::= { hwAtmOamCcEntry 1 }
		
		hwAtmOamCcVCI OBJECT-TYPE
			SYNTAX AtmVcIdentifier
			MAX-ACCESS not-accessible
			STATUS current
			DESCRIPTION
				"vci.  
				if vci = 0, means that this is a F4 point"
			::= { hwAtmOamCcEntry 2 }
		
		hwAtmOamCcDirection OBJECT-TYPE
			SYNTAX INTEGER
				{
				sink(1),
				source(2),
				both(3)
				}
			MAX-ACCESS read-create
			STATUS current
			DESCRIPTION
				"OAM CC direction. "
			DEFVAL { both }
			::= { hwAtmOamCcEntry 3 }
		
		hwAtmOamConfType OBJECT-TYPE
			SYNTAX INTEGER
				{
				autoConfig(1),
				manualConfig(2)
				}
			MAX-ACCESS read-create
			STATUS current
			DESCRIPTION
				"OAM CC configure type,only valid  up or down operating . 
				autoConfig(1)  : active/deactive CC by A/D protocol.
				manualConfig(2): active/deactive CC by TMN entirely. see I.610
				"
			DEFVAL { manualConfig }
			::= { hwAtmOamCcEntry 4 }
		
		hwAtmOamCcAdminStatus OBJECT-TYPE
			SYNTAX INTEGER
				{
				up(1),
				down(2)
				}
			MAX-ACCESS read-create
			STATUS current
			DESCRIPTION
				"up(1) means enable; down(2) means disable."
			DEFVAL { up }
			::= { hwAtmOamCcEntry 5 }
		
		hwAtmOamCcRowStatus OBJECT-TYPE
			SYNTAX RowStatus
			MAX-ACCESS read-create
			STATUS current
			DESCRIPTION
				"OAM CC end point table row status."
			::= { hwAtmOamCcEntry 6 }
		
		hwAtmOamLbTable OBJECT-TYPE
			SYNTAX SEQUENCE OF HwAtmOamLbEntry
			MAX-ACCESS not-accessible
			STATUS current
			DESCRIPTION
				"Table of loopback."
			::= { hwAtmOamMibObjects 3 }
		
		hwAtmOamLbEntry OBJECT-TYPE
			SYNTAX HwAtmOamLbEntry
			MAX-ACCESS not-accessible
			STATUS current
			DESCRIPTION
				"OAM loopback table entry.
				This talbe only support 'set' operation."
			INDEX { ifIndex,hwAtmOamLbVPI, hwAtmOamLbVCI }
			::= { hwAtmOamLbTable 1 }
		
		HwAtmOamLbEntry ::=
			SEQUENCE { 
				hwAtmOamLbVPI
					AtmVpIdentifier,
				hwAtmOamLbVCI
					AtmVcIdentifier,
				hwAtmOamLbType
					INTEGER,
				hwAtmOamLbPointLLID
					OCTET STRING,
				hwAtmOamLbNumber
					INTEGER,
				hwAtmOamLbInterval
					INTEGER
			 }

		hwAtmOamLbVPI OBJECT-TYPE
			SYNTAX AtmVpIdentifier
			MAX-ACCESS accessible-for-notify
			STATUS current
			DESCRIPTION
				"vpi."
			::= { hwAtmOamLbEntry 1 }
		
		hwAtmOamLbVCI OBJECT-TYPE
			SYNTAX AtmVcIdentifier
			MAX-ACCESS accessible-for-notify
			STATUS current
			DESCRIPTION
				"vci. 
				if vci = 0, means that this is a F4 point."
			::= { hwAtmOamLbEntry 2 }
		
		hwAtmOamLbType OBJECT-TYPE
			SYNTAX INTEGER
				{
				e2e(1),
				segment(2),
				llid(3),
				no-loopback(4)
				}
			MAX-ACCESS read-create
			STATUS current
			DESCRIPTION
				"OAM loopback type. 
				e2e(1)     : end to end loopback.
				segment(2) : segment loopback.
				llid(3)    : specified llid loopback.
				no-loopback(4): stopping loopback. "
			DEFVAL { segment }
			::= { hwAtmOamLbEntry 3 }
		
		hwAtmOamLbPointLLID OBJECT-TYPE
			SYNTAX OCTET STRING (SIZE (0..16))
			MAX-ACCESS read-create
			STATUS current
			DESCRIPTION
				"Specify loopback destination LLID, which valid only hwAtmOamLbType being set llid(3) . 
				"
			::= { hwAtmOamLbEntry 4 }
		
		hwAtmOamLbNumber OBJECT-TYPE
			SYNTAX INTEGER (1..10)
			MAX-ACCESS read-create
			STATUS current
			DESCRIPTION
				"Specify the number of the cells loopbacked . 
				"
			::= { hwAtmOamLbEntry 5 }
		
		hwAtmOamLbInterval OBJECT-TYPE
			SYNTAX INTEGER (1..5)
			MAX-ACCESS read-create
			STATUS current
			DESCRIPTION
				"Specify the interval between two insert operation. "
			::= { hwAtmOamLbEntry 6 }
		
		hwAtmOamLlidTable OBJECT-TYPE
			SYNTAX SEQUENCE OF HwAtmOamLlidEntry
			MAX-ACCESS not-accessible
			STATUS current
			DESCRIPTION
				"Table of LLID."
			::= { hwAtmOamMibObjects 4 }
		
		hwAtmOamLlidEntry OBJECT-TYPE
			SYNTAX HwAtmOamLlidEntry
			MAX-ACCESS not-accessible
			STATUS current
			DESCRIPTION
				"OAM LLID table entry."
			INDEX { ifIndex }
			::= { hwAtmOamLlidTable 1 }
		
		HwAtmOamLlidEntry ::=
			SEQUENCE { 
				hwAtmOamLlidPointLLID
					OCTET STRING
			 }

		hwAtmOamLlidPointLLID OBJECT-TYPE
			SYNTAX OCTET STRING (SIZE (0..16))
			MAX-ACCESS read-write
			STATUS current
			DESCRIPTION
				"local interface LLID. "
			::= { hwAtmOamLlidEntry 1 }
		
		hwAtmOamInsertTable OBJECT-TYPE
			SYNTAX SEQUENCE OF HwAtmOamInsertEntry
			MAX-ACCESS not-accessible
			STATUS current
			DESCRIPTION
				"Table of Insert."
			::= { hwAtmOamMibObjects 5 }
		
		hwAtmOamInsertEntry OBJECT-TYPE
			SYNTAX HwAtmOamInsertEntry
			MAX-ACCESS not-accessible
			STATUS current
			DESCRIPTION
				"OAM Insert table entry.
				This talbe only support 'set' operation."
			INDEX { ifIndex,hwAtmOamInsertVPI, hwAtmOamInsertVCI }
			::= { hwAtmOamInsertTable 1 }
		
		HwAtmOamInsertEntry ::=
			SEQUENCE { 
				hwAtmOamInsertVPI
					AtmVpIdentifier,
				hwAtmOamInsertVCI
					AtmVcIdentifier,
				hwAtmOamInsertOperation
					INTEGER,
				hwAtmOamInsertSegment
					INTEGER,
				hwAtmOamInsertCellType
					INTEGER
			 }

		hwAtmOamInsertVPI OBJECT-TYPE
			SYNTAX AtmVpIdentifier
			MAX-ACCESS not-accessible
			STATUS current
			DESCRIPTION
				"vpi."
			::= { hwAtmOamInsertEntry 1 }
		
		hwAtmOamInsertVCI OBJECT-TYPE
			SYNTAX AtmVcIdentifier
			MAX-ACCESS not-accessible
			STATUS current
			DESCRIPTION
				"vci. 
				if vci = 0, means that this is a F4 point."
			::= { hwAtmOamInsertEntry 2 }
		
		hwAtmOamInsertOperation OBJECT-TYPE
			SYNTAX INTEGER
				{
				start(1),
				stop(2)
				}
			MAX-ACCESS read-create
			STATUS current
			DESCRIPTION
				"specify the operation(begin or stop) of the insertion . 
				"
			::= { hwAtmOamInsertEntry 3 }
		
		hwAtmOamInsertSegment OBJECT-TYPE
			SYNTAX INTEGER
				{
				segment(1),
				end(2)
				}
			MAX-ACCESS read-create
			STATUS current
			DESCRIPTION
				"specify the segment type. 
				"
			::= { hwAtmOamInsertEntry 4 }
		
		hwAtmOamInsertCellType OBJECT-TYPE
			SYNTAX INTEGER
				{
				ais(1),
				rdi(2),
				cc(3)
				}
			MAX-ACCESS read-create
			STATUS current
			DESCRIPTION
				"specify the type of the inserted cell . 
				"
			::= { hwAtmOamInsertEntry 5 }
		
		hwAtmOamTraps OBJECT IDENTIFIER ::= { hwAtmOam 2 }
		
		hwAtmOamTrapVarBindOids OBJECT IDENTIFIER ::= { hwAtmOamTraps 1 }
		
		hwAtmOamGeneralVarBindOids OBJECT IDENTIFIER ::= { hwAtmOamTrapVarBindOids 1 }
		
		hwAtmOamVarBindLoopbackResult OBJECT-TYPE
			SYNTAX INTEGER
				{
				success(1),
				timeout(2)
				}
			MAX-ACCESS accessible-for-notify
			STATUS current
			DESCRIPTION
				"
				Loopback result:
				success(1)          --loopback success
				timeout(2)          --not recieved loopback cell for 5 seconds after sent, time out
				
				            "
			::= { hwAtmOamGeneralVarBindOids 1 }
		
		hwAtmOamVarBindOidsReason OBJECT IDENTIFIER ::= { hwAtmOamTrapVarBindOids 2 }
		
		hwAtmOamAisReason OBJECT-TYPE
			SYNTAX INTEGER
				{
				connDelete(1),
				boardFail(2)
				}
			MAX-ACCESS accessible-for-notify
			STATUS current
			DESCRIPTION
				"  OAM operation terminate reason:
				enumFirst:  
				explain： ATM  connection be deleted
				 resolving method:None
				enumSecond:  
				 explain： Board fail
				 resolving method:None
				
				
				 OAM操作终止原因：
				enumFirst:  
				 告警原因： ATM连接被删除
				 修复建议:  无
				enumSecond: 
				 告警原因： 单板故障
				 修复建议:  无
				"
			::= { hwAtmOamVarBindOidsReason 1 }
		
		hwAtmOamOperTerminateReason OBJECT-TYPE
			SYNTAX INTEGER
				{
				connDelete(1),
				boardFail(2)
				}
			MAX-ACCESS accessible-for-notify
			STATUS current
			DESCRIPTION
				"  OAM operation terminate reason:
				enumFirst:  
				explain： ATM  connection be deleted
				 resolving method:None
				enumSecond:  
				 explain： Board fail
				 resolving method:None
				
				
				 OAM操作终止原因：
				enumFirst:  
				 告警原因： ATM连接被删除
				 修复建议:  无
				enumSecond: 
				 告警原因： 单板故障
				 修复建议:  无
				"
			::= { hwAtmOamVarBindOidsReason 2 }
		
		hwAtmOamAlarmTraps OBJECT IDENTIFIER ::= { hwAtmOamTraps 2 }
		
		hwAtmOamAlarmTrapsOids OBJECT IDENTIFIER ::= { hwAtmOamAlarmTraps 0 }
		
		hwAtmOamAlarmAis NOTIFICATION-TYPE
			OBJECTS { ifIndex, hwAtmOamPointVPI, hwAtmOamPointVCI }
			STATUS current
			DESCRIPTION
				"alarm description:AIS alarm
				explain： AIS cell recieved from upstream.
				resolving method:Check if there is some defect in the upstream
				
				
				告警描述：AIS告警
				告警原因：收到来自上游的AIS信元
				修复建议：检查上游是否出问题"
			::= { hwAtmOamAlarmTrapsOids 1 }
		
		hwAtmOamAlarmAisRestore NOTIFICATION-TYPE
			OBJECTS { ifIndex, hwAtmOamPointVPI, hwAtmOamPointVCI }
			STATUS current
			DESCRIPTION
				"alarm description:AIS alarm　restore
				explain： There is no AIS cell recieved from upstream within a time interval of 2.5 seconds, with a margin of 0.5 seconds,
				resolving method:NA.
				
				告警描述：AIS告警恢复
				告警原因：在AIS状态下，2.5秒（+/- 0.5秒）的时间后，没有能再收到AIS信元
				修复建议：无
				"
			::= { hwAtmOamAlarmTrapsOids 2 }
		
		hwAtmOamAlarmRdi NOTIFICATION-TYPE
			OBJECTS { ifIndex, hwAtmOamPointVPI, hwAtmOamPointVCI }
			STATUS current
			DESCRIPTION
				"alarm description:RDI alarm
				explain： RDI cell recieved from downstream.
				resolving method:Check if there is some defect in the downstream.
				
				
				告警描述：RDI告警
				告警原因：收到来自下游的RDI信元
				修复建议：检查下游是否出问题
				"
			::= { hwAtmOamAlarmTrapsOids 3 }
		
		hwAtmOamAlarmRdiRestore NOTIFICATION-TYPE
			OBJECTS { ifIndex, hwAtmOamPointVPI, hwAtmOamPointVCI }
			STATUS current
			DESCRIPTION
				"
				alarm description:RDI alarm　restore
				explain： There is no RDI cell recieved from downstream within a time interval of 2.5 seconds, with a margin of 0.5 seconds,
				resolving method:NA.
				
				告警描述：RDI告警恢复
				告警原因：在RDI状态下，2.5秒（+/- 0.5秒）的时间后，没有能再收到RDI信元
				修复建议：无
				
				"
			::= { hwAtmOamAlarmTrapsOids 4 }
		
		hwAtmOamAlarmLoc NOTIFICATION-TYPE
			OBJECTS { ifIndex, hwAtmOamPointVPI, hwAtmOamPointVCI }
			STATUS current
			DESCRIPTION
				"alarm description:LOC alarm
				explain： CC sink can not recieve CC cells from source within a time interval of 3.5 seconds,with a margin of 0.5 seconds;Or physical fault is detected
				resolving method:Check if there is some physical fault.check if there is some defect bettween CC source and CC sink.check if CC source is configured turely.
				
				
				告警描述：LOC告警
				告警原因：如果连续性检测功能被激活，指定的接收点收不到CC信元达3.5秒（+/- 0.5秒)；或者收到物理层故障告警
				修复建议：检查本端是否存在物理层故障；检查和CC对端之间的连接通路是否正常；如果以上都正常，则可能是对端CC没有正确启动。
				"
			::= { hwAtmOamAlarmTrapsOids 5 }
		
		hwAtmOamAlarmLocRestore NOTIFICATION-TYPE
			OBJECTS { ifIndex, hwAtmOamPointVPI, hwAtmOamPointVCI }
			STATUS current
			DESCRIPTION
				"alarm description:LOC alarm restore
				explain： CC cells can be recieved from CC source.Or physical fault is restored.
				resolving method:NA
				
				
				告警描述：LOC告警恢复
				告警原因：在LOC状态下，收到CC信元；或者物理层故障恢复
				修复建议：无
				"
			::= { hwAtmOamAlarmTrapsOids 6 }
		
		hwAtmOamAlarmLbTerminate NOTIFICATION-TYPE
			OBJECTS { ifIndex, hwAtmOamPointVPI, hwAtmOamPointVCI, hwAtmOamOperTerminateReason }
			STATUS current
			DESCRIPTION
				"alarm description:LB abort alarm
				explain：1.The corresponding connection is deleted
				         2.There is some fault in the corresponding board. 
				resolving method:Until the board changes normal, and renew configureing if necesssary
				
				
				告警描述：LB终止告警
				告警原因：1.对应的连接已经被删除
				          2.所在的单板发生故障
				修复建议：等待单板恢复正常，如果需要重新进行环回操作"
			::= { hwAtmOamAlarmTrapsOids 7 }
		
		hwAtmOamAlarmInsTerminate NOTIFICATION-TYPE
			OBJECTS { ifIndex, hwAtmOamPointVPI, hwAtmOamPointVCI, hwAtmOamOperTerminateReason }
			STATUS current
			DESCRIPTION
				"alarm description:Insertion abort alarm
				explain：1.The corresponding connection is deleted
				         2.There is some fault in the corresponding board. 
				resolving method:Until the board changes normal, and renew configureing if necesssary
				
				
				告警描述：插入终止告警
				告警原因：1.对应的连接已经被删除
				          2.所在的单板发生故障
				修复建议：等待单板恢复正常，如果需要重新进行插入操作
				"
			::= { hwAtmOamAlarmTrapsOids 8 }
		
		hwAtmOamGeneralTraps OBJECT IDENTIFIER ::= { hwAtmOamTraps 3 }
		
		hwAtmOamGeneralTrapsOids OBJECT IDENTIFIER ::= { hwAtmOamGeneralTraps 0 }
		
		hwAtmOamTrapLoopbackReport NOTIFICATION-TYPE
			OBJECTS { hwAtmOamLbPointLLID, hwAtmOamVarBindLoopbackResult, hwAtmOamLbVPI, hwAtmOamLbVCI, ifIndex
				 }
			STATUS current
			DESCRIPTION
				"General trap description:
				Used to send loopback result of LB cell, success(1) or timeout(2).
				
				一般TRAP 描述:
				用于发送环回信元的环回结果，成功(1)或超时(2)。
				"
			::= { hwAtmOamGeneralTrapsOids 1 }
		
	
	END

--
-- HUAWEI-ATM-OAM-MIB.mib
--
