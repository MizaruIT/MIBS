--
-- OPTIX-SDH-ALM-MIB.mib
-- MIB generated by MG-SOFT Visual MIB Builder Version 3.0 Build 253
-- Thursday, June 29, 2006 at 15:00:54
--

	OPTIX-SDH-ALM-MIB DEFINITIONS ::= BEGIN
 
		IMPORTS
			optixCommonSdh			
				FROM OPTIX-OID-MIB			
			SdhAlarmEventType			
				FROM OPTIX-SDH-TC-MIB			
			OBJECT-GROUP, MODULE-COMPLIANCE			
				FROM SNMPv2-CONF			
			mgmt, Gauge32, OBJECT-TYPE, MODULE-IDENTITY			
				FROM SNMPv2-SMI			
			DateAndTime			
				FROM SNMPv2-TC;
	
	
		optixAlarm MODULE-IDENTITY 
			LAST-UPDATED "200604141405Z"		-- April 14, 2006 at 14:05 GMT
			ORGANIZATION 
				"Huawei Technologies co.,Ltd."
			CONTACT-INFO 
				"R&D Building
				Huawei Technologies Co., Ltd.
				Bantian, Longgang District 
				Shenzhen, P. R. China
				http://www.huawei.com
				Zip:518129
				E-mail:support@huawei.com"
			DESCRIPTION 
				"This module MIB describes the Optix Alarm."
			REVISION "200604151200Z"		-- April 15, 2006 at 12:00 GMT
			DESCRIPTION
				"The initial revision of this MIB module."
			::= { optixCommonSdh 30 }
		
	
--
-- Type definitions
--
	
		RowStatus ::= INTEGER
			{
			active(1),
			notInService(2),
			notReady(3),
			createAndGo(4),
			createAndWait(5),
			destroy(6)
			}
		
	
--
-- Node definitions
--
	
--  Performance event
		-- 1.3.6.1.4.1.2011.2.25.3.10.30.10
		almAttribute OBJECT IDENTIFIER ::= { optixAlarm 10 }
		
--  -------------------------------------------------------------------------
-- Alarm module objects,include alarm attribute table and alarm data table
-- 
-- -------------------------------------------------------------------------
		-- 1.3.6.1.4.1.2011.2.25.3.10.30.10.10
		almAutoReportTable OBJECT-TYPE
			SYNTAX SEQUENCE OF AlmAutoReportEntry
			MAX-ACCESS not-accessible
			STATUS current
			DESCRIPTION
				"Alarm auotmatic report status table."
			::= { almAttribute 10 }
		
		-- 1.3.6.1.4.1.2011.2.25.3.10.30.10.10.1
		almAutoReportEntry OBJECT-TYPE
			SYNTAX AlmAutoReportEntry
			MAX-ACCESS not-accessible
			STATUS current
			DESCRIPTION
				"Alarm auotmatic report status entry."
			INDEX { almAutoRepBid, almAutoRepEid }
			::= { almAutoReportTable 1 }
		
		AlmAutoReportEntry ::=
			SEQUENCE { 
				almAutoRepBid
					Gauge32,
				almAutoRepEid
					SdhAlarmEventType,
				almAutoRep
					INTEGER
			 }

		-- 1.3.6.1.4.1.2011.2.25.3.10.30.10.10.1.1
		almAutoRepBid OBJECT-TYPE
			SYNTAX Gauge32
			MAX-ACCESS read-only
			STATUS current
			DESCRIPTION
				"Card ID"
			::= { almAutoReportEntry 1 }
		
		-- 1.3.6.1.4.1.2011.2.25.3.10.30.10.10.1.2
		almAutoRepEid OBJECT-TYPE
			SYNTAX SdhAlarmEventType
			MAX-ACCESS read-only
			STATUS current
			DESCRIPTION
				"Alarm ID"
			::= { almAutoReportEntry 2 }
		
		-- 1.3.6.1.4.1.2011.2.25.3.10.30.10.10.1.3
		almAutoRep OBJECT-TYPE
			SYNTAX INTEGER
				{
				disable(0),
				enable(1)
				}
			MAX-ACCESS read-write
			STATUS current
			DESCRIPTION
				"Alarm auotmatic report status."
			::= { almAutoReportEntry 3 }
		
		-- 1.3.6.1.4.1.2011.2.25.3.10.30.10.20
		almSeverityTable OBJECT-TYPE
			SYNTAX SEQUENCE OF AlmSeverityEntry
			MAX-ACCESS not-accessible
			STATUS current
			DESCRIPTION
				"Alarm severity table."
			::= { almAttribute 20 }
		
		-- 1.3.6.1.4.1.2011.2.25.3.10.30.10.20.1
		almSeverityEntry OBJECT-TYPE
			SYNTAX AlmSeverityEntry
			MAX-ACCESS not-accessible
			STATUS current
			DESCRIPTION
				"Alarm severity table."
			INDEX { almSeverityBid, almSeverityEid }
			::= { almSeverityTable 1 }
		
		AlmSeverityEntry ::=
			SEQUENCE { 
				almSeverityBid
					Gauge32,
				almSeverityEid
					SdhAlarmEventType,
				almSeverity
					INTEGER
			 }

		-- 1.3.6.1.4.1.2011.2.25.3.10.30.10.20.1.1
		almSeverityBid OBJECT-TYPE
			SYNTAX Gauge32
			MAX-ACCESS read-only
			STATUS current
			DESCRIPTION
				"Card ID"
			::= { almSeverityEntry 1 }
		
		-- 1.3.6.1.4.1.2011.2.25.3.10.30.10.20.1.2
		almSeverityEid OBJECT-TYPE
			SYNTAX SdhAlarmEventType
			MAX-ACCESS read-only
			STATUS current
			DESCRIPTION
				"Alarm ID"
			::= { almSeverityEntry 2 }
		
		-- 1.3.6.1.4.1.2011.2.25.3.10.30.10.20.1.3
		almSeverity OBJECT-TYPE
			SYNTAX INTEGER
				{
				critical(1),
				major(2),
				minor(3),
				warning(4)
				}
			MAX-ACCESS read-write
			STATUS current
			DESCRIPTION
				"Alarm severity."
			::= { almSeverityEntry 3 }
		
		-- 1.3.6.1.4.1.2011.2.25.3.10.30.10.30
		almMonStateTable OBJECT-TYPE
			SYNTAX SEQUENCE OF AlmMonStateEntry
			MAX-ACCESS not-accessible
			STATUS current
			DESCRIPTION
				"Alarm monitor status table."
			::= { almAttribute 30 }
		
		-- 1.3.6.1.4.1.2011.2.25.3.10.30.10.30.1
		almMonStateEntry OBJECT-TYPE
			SYNTAX AlmMonStateEntry
			MAX-ACCESS not-accessible
			STATUS current
			DESCRIPTION
				"Alarm monitor status entry."
			INDEX { almMonStateBid, almMonStateEid, almMonStatePort, almMonStatePath }
			::= { almMonStateTable 1 }
		
		AlmMonStateEntry ::=
			SEQUENCE { 
				almMonStateBid
					Gauge32,
				almMonStateEid
					SdhAlarmEventType,
				almMonStatePort
					Gauge32,
				almMonStatePath
					Gauge32,
				almMonState
					INTEGER
			 }

		-- 1.3.6.1.4.1.2011.2.25.3.10.30.10.30.1.1
		almMonStateBid OBJECT-TYPE
			SYNTAX Gauge32
			MAX-ACCESS read-only
			STATUS current
			DESCRIPTION
				"Card ID"
			::= { almMonStateEntry 1 }
		
		-- 1.3.6.1.4.1.2011.2.25.3.10.30.10.30.1.2
		almMonStateEid OBJECT-TYPE
			SYNTAX SdhAlarmEventType
			MAX-ACCESS read-only
			STATUS current
			DESCRIPTION
				"Alarm ID"
			::= { almMonStateEntry 2 }
		
		-- 1.3.6.1.4.1.2011.2.25.3.10.30.10.30.1.3
		almMonStatePort OBJECT-TYPE
			SYNTAX Gauge32
			MAX-ACCESS read-only
			STATUS current
			DESCRIPTION
				"Optical port No."
			::= { almMonStateEntry 3 }
		
		-- 1.3.6.1.4.1.2011.2.25.3.10.30.10.30.1.4
		almMonStatePath OBJECT-TYPE
			SYNTAX Gauge32
			MAX-ACCESS read-only
			STATUS current
			DESCRIPTION
				"Path No."
			::= { almMonStateEntry 4 }
		
		-- 1.3.6.1.4.1.2011.2.25.3.10.30.10.30.1.5
		almMonState OBJECT-TYPE
			SYNTAX INTEGER
				{
				disable(0),
				enable(1)
				}
			MAX-ACCESS read-write
			STATUS current
			DESCRIPTION
				"Alarm monitor status."
			::= { almMonStateEntry 5 }
		
--  Alarm attribute
		-- 1.3.6.1.4.1.2011.2.25.3.10.30.20
		almData OBJECT IDENTIFIER ::= { optixAlarm 20 }
		
		-- 1.3.6.1.4.1.2011.2.25.3.10.30.20.20
		almHisAlarmDataTable OBJECT-TYPE
			SYNTAX SEQUENCE OF AlmHisAlarmDataEntry
			MAX-ACCESS not-accessible
			STATUS current
			DESCRIPTION
				"Historic alarm table."
			::= { almData 20 }
		
		-- 1.3.6.1.4.1.2011.2.25.3.10.30.20.20.1
		almHisAlarmDataEntry OBJECT-TYPE
			SYNTAX AlmHisAlarmDataEntry
			MAX-ACCESS not-accessible
			STATUS current
			DESCRIPTION
				"Historic alarm Entry."
			INDEX { almHisAlarmDataNID }
			::= { almHisAlarmDataTable 1 }
		
		AlmHisAlarmDataEntry ::=
			SEQUENCE { 
				almHisAlarmDataTableStatus
					RowStatus,
				almHisAlarmDataPara
					OCTET STRING,
				almHisAlarmDataEndTime
					DateAndTime,
				almHisAlarmDataStartTime
					DateAndTime,
				almHisAlarmDataState
					INTEGER,
				almHisAlarmDataSeverity
					INTEGER,
				almHisAlarmDataEid
					SdhAlarmEventType,
				almHisAlarmDataBid
					Gauge32,
				almHisAlarmDataNID
					Gauge32
			 }

		-- 1.3.6.1.4.1.2011.2.25.3.10.30.20.20.1.9
		almHisAlarmDataTableStatus OBJECT-TYPE
			SYNTAX RowStatus
			MAX-ACCESS read-write
			STATUS current
			DESCRIPTION
				"Indicate whether this row has been deleted."
			::= { almHisAlarmDataEntry 9 }
		
		-- 1.3.6.1.4.1.2011.2.25.3.10.30.20.20.1.8
		almHisAlarmDataPara OBJECT-TYPE
			SYNTAX OCTET STRING (SIZE (5))
			MAX-ACCESS read-only
			STATUS current
			DESCRIPTION
				"Additional parameters,include optical port No,path No,etc."
			::= { almHisAlarmDataEntry 8 }
		
		-- 1.3.6.1.4.1.2011.2.25.3.10.30.20.20.1.7
		almHisAlarmDataEndTime OBJECT-TYPE
			SYNTAX DateAndTime
			MAX-ACCESS read-only
			STATUS current
			DESCRIPTION
				"Date and time when alarm cleared,has following format:
				field  octets  contents                  range
				-----  ------  --------                  -----
				  1      1-2   year                      0..65536
				  2       3    month                     1..12
				  3       4    day                       1..31
				  4       5    hour                      0..23
				  5       6    minutes                   0..59
				  6       7    seconds                   0..60
				               (use 60 for leap-second)
				  7       8    deci-seconds              0..9
				  8       9    direction from UTC        '+' / '-'
				  9      10    hours from UTC            0..11"
			::= { almHisAlarmDataEntry 7 }
		
		-- 1.3.6.1.4.1.2011.2.25.3.10.30.20.20.1.6
		almHisAlarmDataStartTime OBJECT-TYPE
			SYNTAX DateAndTime
			MAX-ACCESS read-only
			STATUS current
			DESCRIPTION
				"Date and time when alarm declared,has following format:
				field  octets  contents                  range
				-----  ------  --------                  -----
				  1      1-2   year                      0..65536
				  2       3    month                     1..12
				  3       4    day                       1..31
				  4       5    hour                      0..23
				  5       6    minutes                   0..59
				  6       7    seconds                   0..60
				               (use 60 for leap-second)
				  7       8    deci-seconds              0..9
				  8       9    direction from UTC        '+' / '-'
				  9      10    hours from UTC            0..11"
			::= { almHisAlarmDataEntry 6 }
		
		-- 1.3.6.1.4.1.2011.2.25.3.10.30.20.20.1.5
		almHisAlarmDataState OBJECT-TYPE
			SYNTAX INTEGER
				{
				almStart(1),
				almGo(2),
				almEnd(3)
				}
			MAX-ACCESS read-only
			STATUS current
			DESCRIPTION
				"Alarm state."
			::= { almHisAlarmDataEntry 5 }
		
		-- 1.3.6.1.4.1.2011.2.25.3.10.30.20.20.1.4
		almHisAlarmDataSeverity OBJECT-TYPE
			SYNTAX INTEGER
				{
				critical(1),
				major(2),
				minor(3),
				warning(4)
				}
			MAX-ACCESS read-only
			STATUS current
			DESCRIPTION
				"Alarm severity."
			::= { almHisAlarmDataEntry 4 }
		
		-- 1.3.6.1.4.1.2011.2.25.3.10.30.20.20.1.3
		almHisAlarmDataEid OBJECT-TYPE
			SYNTAX SdhAlarmEventType
			MAX-ACCESS read-only
			STATUS current
			DESCRIPTION
				"Alarm event ID."
			::= { almHisAlarmDataEntry 3 }
		
		-- 1.3.6.1.4.1.2011.2.25.3.10.30.20.20.1.2
		almHisAlarmDataBid OBJECT-TYPE
			SYNTAX Gauge32
			MAX-ACCESS read-only
			STATUS current
			DESCRIPTION
				"Card ID."
			::= { almHisAlarmDataEntry 2 }
		
		-- 1.3.6.1.4.1.2011.2.25.3.10.30.20.20.1.1
		almHisAlarmDataNID OBJECT-TYPE
			SYNTAX Gauge32
			MAX-ACCESS read-only
			STATUS current
			DESCRIPTION
				"Number ID."
			::= { almHisAlarmDataEntry 1 }
		
		-- 1.3.6.1.4.1.2011.2.25.3.10.30.20.10
		almCurAlarmDataTable OBJECT-TYPE
			SYNTAX SEQUENCE OF AlmCurAlarmDataEntry
			MAX-ACCESS not-accessible
			STATUS current
			DESCRIPTION
				"Current alarm table."
			::= { almData 10 }
		
		-- 1.3.6.1.4.1.2011.2.25.3.10.30.20.10.1
		almCurAlarmDataEntry OBJECT-TYPE
			SYNTAX AlmCurAlarmDataEntry
			MAX-ACCESS not-accessible
			STATUS current
			DESCRIPTION
				"Current alarm table."
			INDEX { almCurAlarmDataNID }
			::= { almCurAlarmDataTable 1 }
		
		AlmCurAlarmDataEntry ::=
			SEQUENCE { 
				almCurAlarmDataTableStatus
					RowStatus,
				almCurAlarmDataPara
					OCTET STRING,
				almCurAlarmDataEndTime
					DateAndTime,
				almCurAlarmDataStartTime
					DateAndTime,
				almCurAlarmDataState
					INTEGER,
				almCurAlarmDataSeverity
					INTEGER,
				almCurAlarmDataEid
					SdhAlarmEventType,
				almCurAlarmDataBid
					Gauge32,
				almCurAlarmDataNID
					Gauge32
			 }

		-- 1.3.6.1.4.1.2011.2.25.3.10.30.20.10.1.9
		almCurAlarmDataTableStatus OBJECT-TYPE
			SYNTAX RowStatus
			MAX-ACCESS read-write
			STATUS current
			DESCRIPTION
				"Indicate whether this row has been deleted."
			::= { almCurAlarmDataEntry 9 }
		
		-- 1.3.6.1.4.1.2011.2.25.3.10.30.20.10.1.8
		almCurAlarmDataPara OBJECT-TYPE
			SYNTAX OCTET STRING (SIZE (5))
			MAX-ACCESS read-only
			STATUS current
			DESCRIPTION
				"Additional parameters,include optical port No,path No,etc."
			::= { almCurAlarmDataEntry 8 }
		
		-- 1.3.6.1.4.1.2011.2.25.3.10.30.20.10.1.7
		almCurAlarmDataEndTime OBJECT-TYPE
			SYNTAX DateAndTime
			MAX-ACCESS read-only
			STATUS current
			DESCRIPTION
				"Date and time when alarm cleared,has following format:
				field  octets  contents                  range
				-----  ------  --------                  -----
				  1      1-2   year                      0..65536
				  2       3    month                     1..12
				  3       4    day                       1..31
				  4       5    hour                      0..23
				  5       6    minutes                   0..59
				  6       7    seconds                   0..60
				               (use 60 for leap-second)
				  7       8    deci-seconds              0..9
				  8       9    direction from UTC        '+' / '-'
				  9      10    hours from UTC            0..11"
			::= { almCurAlarmDataEntry 7 }
		
		-- 1.3.6.1.4.1.2011.2.25.3.10.30.20.10.1.6
		almCurAlarmDataStartTime OBJECT-TYPE
			SYNTAX DateAndTime
			MAX-ACCESS read-only
			STATUS current
			DESCRIPTION
				"Date and time when alarm declared,has following format:
				field  octets  contents                  range
				-----  ------  --------                  -----
				  1      1-2   year                      0..65536
				  2       3    month                     1..12
				  3       4    day                       1..31
				  4       5    hour                      0..23
				  5       6    minute                    0..59
				  6       7    second                    0..60
				               (use 60 for leap-second)
				  7       8    deci-second               0..9
				  8       9    direction from UTC        '+' / '-'
				  9      10    hours from UTC            0..11"
			::= { almCurAlarmDataEntry 6 }
		
		-- 1.3.6.1.4.1.2011.2.25.3.10.30.20.10.1.5
		almCurAlarmDataState OBJECT-TYPE
			SYNTAX INTEGER
				{
				almStart(1),
				almGo(2),
				almEnd(3)
				}
			MAX-ACCESS read-only
			STATUS current
			DESCRIPTION
				"Alarm state."
			::= { almCurAlarmDataEntry 5 }
		
		-- 1.3.6.1.4.1.2011.2.25.3.10.30.20.10.1.4
		almCurAlarmDataSeverity OBJECT-TYPE
			SYNTAX INTEGER
				{
				critical(1),
				major(2),
				minor(3),
				warning(4)
				}
			MAX-ACCESS read-only
			STATUS current
			DESCRIPTION
				"Alarm severity."
			::= { almCurAlarmDataEntry 4 }
		
		-- 1.3.6.1.4.1.2011.2.25.3.10.30.20.10.1.3
		almCurAlarmDataEid OBJECT-TYPE
			SYNTAX SdhAlarmEventType
			MAX-ACCESS read-only
			STATUS current
			DESCRIPTION
				"Alarm event ID."
			::= { almCurAlarmDataEntry 3 }
		
		-- 1.3.6.1.4.1.2011.2.25.3.10.30.20.10.1.2
		almCurAlarmDataBid OBJECT-TYPE
			SYNTAX Gauge32
			MAX-ACCESS read-only
			STATUS current
			DESCRIPTION
				"Card ID."
			::= { almCurAlarmDataEntry 2 }
		
		-- 1.3.6.1.4.1.2011.2.25.3.10.30.20.10.1.1
		almCurAlarmDataNID OBJECT-TYPE
			SYNTAX Gauge32
			MAX-ACCESS read-only
			STATUS current
			DESCRIPTION
				"Number ID."
			::= { almCurAlarmDataEntry 1 }
		
		-- 1.3.6.1.4.1.2011.2.25.3.10.30.50
		optixAlarmConformance OBJECT IDENTIFIER ::= { optixAlarm 50 }
		
		-- 1.3.6.1.4.1.2011.2.25.3.10.30.50.2
		optixAlarmCompliances OBJECT IDENTIFIER ::= { optixAlarmConformance 2 }
		
		-- 1.3.6.1.4.1.2011.2.25.3.10.30.50.2.1
		optixAlarmbasicCompliance MODULE-COMPLIANCE
			STATUS current
			DESCRIPTION 
				"Enter the description of the created MODULE-COMPLIANCE."
			MODULE -- this module
				MANDATORY-GROUPS { currentObjectGroup }
			::= { optixAlarmCompliances 1 }
		
		-- 1.3.6.1.4.1.2011.2.25.3.10.30.50.1
		optixAlarmGroups OBJECT IDENTIFIER ::= { optixAlarmConformance 1 }
		
		-- 1.3.6.1.4.1.2011.2.25.3.10.30.50.1.1
		currentObjectGroup OBJECT-GROUP
			OBJECTS { almAutoRepBid, almAutoRepEid, almAutoRep, almSeverityBid, almSeverityEid, 
				almSeverity, almMonStateBid, almMonStateEid, almMonStatePort, almMonStatePath, 
				almMonState, almCurAlarmDataNID, almCurAlarmDataBid, almCurAlarmDataEid, almCurAlarmDataSeverity, 
				almCurAlarmDataState, almCurAlarmDataStartTime, almCurAlarmDataEndTime, almCurAlarmDataPara, almCurAlarmDataTableStatus, 
				almHisAlarmDataNID, almHisAlarmDataBid, almHisAlarmDataEid, almHisAlarmDataSeverity, almHisAlarmDataState, 
				almHisAlarmDataStartTime, almHisAlarmDataEndTime, almHisAlarmDataPara, almHisAlarmDataTableStatus }
			STATUS current
			DESCRIPTION 
				"Enter the description of the created OBJECT-GROUP."
			::= { optixAlarmGroups 1 }
		
	
	END

--
-- OPTIX-SDH-ALM-MIB.mib
--
