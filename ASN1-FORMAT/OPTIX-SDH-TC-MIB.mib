--
-- OPTIX-SDH-TC-MIB.mib
-- MIB generated by MG-SOFT Visual MIB Builder Version 3.0 Build 253
-- Thursday, October 26, 2006 at 09:34:11
--

--  OPTIX-SDH-TC-MIB.mib
-- MIB generated by MG-SOFT Visual MIB Builder Version 3.0 Build 253
-- Saturday, April 15, 2006 at 14:32:18
-- 

	OPTIX-SDH-TC-MIB DEFINITIONS ::= BEGIN
 
		IMPORTS
			optixCommon			
				FROM OPTIX-OID-MIB			
			MODULE-IDENTITY			
				FROM SNMPv2-SMI			
			TEXTUAL-CONVENTION			
				FROM SNMPv2-TC;
	
	
		optixsdhTCMIB MODULE-IDENTITY 
			LAST-UPDATED "200604141608Z"		-- April 14, 2006 at 16:08 GMT
			ORGANIZATION 
				"Huawei Technologies Co.,Ltd."
			CONTACT-INFO 
				"R&D Building
				Huawei Technologies Co., Ltd.
				Bantian, Longgang District 
				Shenzhen, P. R. China
				http://www.huawei.com
				Zip:518129
				E-mail:support@huawei.com
				"
			DESCRIPTION 
				"This module describes rules of Huawei transmit 
				platform self-defined types."
			REVISION "200604151156Z"		-- April 15, 2006 at 11:56 GMT
			DESCRIPTION
				"The initial revision of this MIB module."
			::= { optixCommon 98 }
		
	
-- -------------------------------------------------------------------------
--  Performance monitor event type
-- -------------------------------------------------------------------------
		SdhPerformanceEventType ::= TEXTUAL-CONVENTION
			STATUS current
			DESCRIPTION 
				"Performance ID."
			SYNTAX INTEGER
				{
				rsBackgroundBlockError(1),
				rsErroredSecond(2),
				rsSeverelyErroredSecond(3),
				rsOutOfFrame(4),
				rsOutOfFrameSecond(5),
				rsUnavailableSecond(6),
				rsConsecutiveSeverelyErroredSecond(7),
				rsFc(8),
				rsEsb(9),
				msBackgroundBlockError(16),
				msErroredSecond(17),
				msSeverelyErroredSecond(18),
				msFarEndBackgroundBlockError(19),
				msFarEndErroredSecond(20),
				msFarEndSeverelyErroredSecond(21),
				msUnavailableSecond(22),
				msConsecutiveSeverelyErroredSecond(23),
				msFarEndConsecutiveSeverelyErroredSecond(24),
				msEsb(25),
				msFc(26),
				msFefc(27),
				msFeesb(28),
				msEsa(29),
				msFeesa(30),
				msCv(31),
				msFecv(32),
				msFarEndUnavailableSecond(33),
				fbCodeErr(41),
				auPointerJustificationCountHIGH(42),
				auPointerJustificationCountLOW(43),
				auPointerJustificationCountNEW(44),
				tcBackgroundBlockError(45),
				tcFarEndBackgroundBlockError(46),
				tcOutgoingBackgroundBlockError(47),
				hpBackgroundBlockError(48),
				hpErroredSecond(49),
				hpSeverelyErroredSecond(50),
				hpFarEndBackgroundBlockError(51),
				hpFarEndErroredSecond(52),
				hpFarEndSeverelyErroredSecond(53),
				hpUnavailableSecond(54),
				hpConsecutiveSeverelyErroredSecond(55),
				hpFarEndConsecutiveSeverelyErroredSecond(56),
				hpEsb(57),
				hpFc(58),
				hpFefc(59),
				hpFeesb(60),
				hpEsa(61),
				hpFeesa(62),
				hpCv(63),
				hpFecv(64),
				hpFarEndUnavailableSecond(76),
				temperatureOfErbiumDopedFiberBOXMAX(65),
				temperatureOfErbiumDopedFiberBOXMIN(66),
				temperatureOfErbiumDopedFiberBOXCurrent(67),
				lineOutputPowerMax(68),
				lineOutputPowerMin(69),
				lineOutputPowerCurrent(70),
				msProtectionSwitchCount(74),
				msProtectionSwitchDuration(75),
				vc3BackgroundBlockError(80),
				vc3ErroredSecond(81),
				vc3ServerlyErroredSecond(82),
				vc3FarEndBackgroundBlockError(83),
				vc3FarEndErroredSecond(84),
				vc3FarEndServerlyErroredSecond(85),
				vc3UnavailableSecond(86),
				vc3ConsecutivServerlyEeeoredSecond(87),
				vc3FarEndConsecutivServerlyEeeoredSecond(88),
				vc3FarEndUnavailableSecond(89),
				ospiTransmissionLaserBiasMaximum(96),
				ospiTransmissionLaserBiasMinmum(97),
				ospiTransmissionLaserBiasCurrent(98),
				ospiCoolingMaximum(99),
				ospiCoolingMinimum(100),
				ospiCoolingCurrent(101),
				ospiTransmissionPowerLevelMaximum(102),
				ospiTransmissionPowerLevelMinimum(103),
				ospiTransmissionPowerLevelCurrent(104),
				ospiReceivingPowerLevelMaximum(105),
				ospiReceivingPowerLevelMinimum(106),
				ospiReceivingPowerLevelCurrent(107),
				ospiTemperatureMaximum(108),
				ospiTemperatureMinimum(109),
				ospiTemperatureCurrent(110),
				workingCurrentValueMaximum(112),
				workingCurrentValueMinimum(113),
				workingCurrentValueValueCurrent(114),
				coolingCurrentValueMaximum(115),
				coolingCurrentValueMinimum(116),
				coolingCurrentValueCurrent(117),
				backCurrentValueMaximum(118),
				backCurrentValueMinimum(119),
				backCurrentValueCurrent(120),
				edfaTransmissionPowerLevelMaximum(121),
				edfaTransmissionPowerLevelMinimum(122),
				edfaTransmissionPowerLevelCurrent(123),
				edfaReceivingPowerLevelMaximum(124),
				edfaReceivingPowerLevelMinimum(125),
				edfaReceivingPowerLevelCurrent(126),
				workingCurrentSetupMaximum(127),
				workingCurrentSetupMinimum(128),
				workingCurrentSetupCurrent(129),
				edfaTemperatureMaximum(130),
				edfaTemperatureMinimum(131),
				edfaTemperatureCurrent(132),
				fecCorrected0BitCount(133),
				fecCorrected1BitCount(134),
				fecCorrectedByteCount(135),
				fecUnCorrectedBlockCount(136),
				emuVolMax(138),
				emuVolMin(139),
				emuVolAvg(140),
				emuTmpCur(141),
				lpFarEndUnavailableSecond(142),
				lpBackgroundBlockError(144),
				lpErroredSecond(145),
				lpSeverelyErroredSecond(146),
				lpFarEndBackgroundBlockError(147),
				lpFarEndErroredSecond(148),
				lpFarEndSeverelyErroredSecond(149),
				lpUnavailableSecond(150),
				lpConsecutiveSeverelyErroredSecond(151),
				lpFarEndConsecutiveSeverelyErroredSecond(152),
				lpEsb(153),
				lpFc(154),
				lpFefc(155),
				lpFeesb(156),
				lpEsa(157),
				lpFeesa(158),
				lpCv(159),
				tuPointerJustificationCountHIGH(170),
				tuPointerJustificationCountLOW(171),
				tuPointerJustificationCountNEW(172),
				lpProtectionSwitchCount(176),
				lpProtectionSwitchDuration(177),
				dslCrcErrors(178),
				dslLOWS(179),
				dslErrorsSeconds(180),
				dslsevereErrorsSeconds(181),
				dslUnuseAccessSeconds(182),
				dslCurrentLoopPathAttenuation(183),
				dslCurrentSigalNoiseRations(184),
				crc4Err(185),
				ddnCrc4Err(186),
				beforeFECCorrectErrorRatio(252),
				afterFECCorrectErrorRatio(253),
				boardTemperatureMaximum(188),
				boardTemperatureMinimum(189),
				boardTemperatureCurrent(190),
				pmuTemperatureMaximum(192),
				pmuTemperatureMinimum(193),
				pmuTemperatureAverage(194),
				pmuTemperatureCurrent(195),
				w32LaserOutputOfPowerMaximum(198),
				w32LaserOutputOfPowerMinimum(199),
				w32LaserOutputOfPowerCurrent(200),
				w32LaserInputOfPowerMaximum(201),
				w32LaserInputOfPowerMinimum(202),
				w32LaserInputOfPowerCurrent(203),
				w32LaserWorkingTemperatureMaximum(204),
				w32LaserWorkingTemperatureMinimum(205),
				w32LaserWorkingTemperatureCurrent(206),
				w32LaserBiasMaximum(207),
				w32LaserBiasMinimum(208),
				w32LaserBiasCurrent(209),
				w32SumLaserInputOfPowerMaximum(210),
				w32SumLaserInputOfPowerMinimum(211),
				w32SumLaserInputOfPowerCurrent(212),
				w32SumLaserOutputOfPowerMaximum(213),
				w32SumLaserOutputOfPowerMinimum(214),
				w32SumLaserOutputOfPowerCurrent(215),
				w32PumpWorkingTemperatureMaximum(216),
				w32PumpWorkingTemperatureMinimum(217),
				w32PumpWorkingTemperatureCurrent(218),
				w32PumpBiasMaximum(219),
				w32PumpBiasMinimum(220),
				w32PumpBiasCurrent(221),
				w32EnvironmentTemperatureMaximum(222),
				w32EnvironmentTemperatureMinimum(223),
				w32EnvironmentTemperatureCurrent(224),
				w32LaserCoolingMaximum(225),
				w32LaserCoolingMinimum(226),
				w32LaserCoolingCurrent(227),
				w32PerChannelLaserWaveLengthMaximum(228),
				w32PerChannelLaserWaveLengthMinimum(229),
				w32PerChannelLaserWaveLengthCurrent(230),
				w32PerChannelLaserWaveLengthOffsetMaximum(231),
				w32PerChannelLaserWaveLengthOffsetMinimum(232),
				w32PerChannelLaserWaveLengthOffsetCurrent(233),
				w32PerChannelLaserPowerMaximum(234),
				w32PerChannelLaserPowerMinimum(235),
				w32PerChannelLaserPowerCurrent(236),
				w32PerChannelLaserRateOfSingnalAndNoiseMaximum(237),
				w32PerChannelLaserRateOfSingnalAndNoiseMinimum(238),
				w32PerChannelLaserRateOfSingnalAndNoiseCurrent(239),
				w32CRC4BackgroundBlockError(240),
				w32CRC4ErroredSecond(241),
				w32CRC4SeverelyErroredSecond(242),
				w32CRC4FarEndBackgroundBlockError(243),
				w32CRC4FarEndErroredSecond(244),
				w32CRC4FarEndSeverelyErroredSecond(245),
				w32CRC4UnavailableSecond(246),
				w32CRC4ConsecutiveSeverelyErroredSecond(247),
				w32CRC4FarEndConsecutiveSeverelyErroredSecond(248),
				w32IntegrateCircuitTemperatureMaximum(249),
				w32IntegrateCircuitTemperatureMinimum(250),
				w32IntegrateCircuitTemperatureCurrent(251),
				w32CRC4FarEndUnavailableSecond(254),
				e3LCV(37),
				e3LES(38),
				e3LSES(39),
				e3LLOSS(40),
				e1LCV(12),
				e1LES(13),
				e1LSES(14),
				e1LLOSS(15),
				t3LCV(160),
				t3LES(161),
				t3LSES(162),
				t3LLOSS(163),
				t1LCV(164),
				t1LES(165),
				t1LSES(166),
				t1LLOSS(167),
				opticalTransportUnitSMBIP8(4170),
				opticalDataUnitPMBIP8(4171),
				maxModuleCoolCurrent(4172),
				minModuleCoolCurrent(4173),
				currentModuleCoolCurrent(4174),
				maxReceiveSignalLevel(8606),
				minReceiveSignalLevel(8607),
				currentReceiveSignalLevel(8608),
				maxTransmissionSignalLevel(8609),
				minTransmissionSignalLevel(8610),
				currentTransmissionSignalLevel(8611),
				crc6Err(8587),
				opticalOutputPowerReturnLossMaximum(8612),
				opticalOutputPowerReturnLossMinimum(8613),
				opticalOutputPowerReturnLosscurrentm(8614),
				otu1iaes(14336),--OTU1_IAES
				otu1biaes(14337),
				otu1bbe(14338),
				otu1es(14339),
				otu1ses(14340),
				otu1uas(14341),
				otu1sesr(14342),
				otu1bber(14343),
				otu1febbe(14344),
				otu1fees(14345),
				otu1feses(14346),
				otu1feuas(14347),
				otu1fesesr(14348),
				otu1febber(14349),
				otu5giaes(14350),
				otu5gbiaes(14351),
				otu5gbbe(14352),
				otu5ges(14353),
				otu5gses(14354),
				otu5guas(14355),
				otu5gsesr(14356),
				otu5gbber(14357),
				otu5gfebbe(14358),
				otu5gfees(14359),
				otu5gfeses(14360),
				otu5gfeuas(14361),
				otu5gfesesr(14362),
				otu5gfebber(14363),
				otu2iaes(14364),
				otu2biaes(14365),
				otu2bbe(14366),
				otu2es(14367),
				otu2ses(14368),
				otu2uas(14369),
				otu2sesr(14370),
				otu2bber(14371),
				otu2febbe(14372),
				otu2fees(14373),
				otu2feses(14374),
				otu2feuas(14375),
				otu2fesesr(14376),
				otu2febber(14377),
				otu3iaes(14378),
				otu3biaes(14379),
				otu3bbe(14380),
				otu3es(14381),
				otu3ses(14382),
				otu3uas(14383),
				otu3sesr(14384),
				otu3bber(14385),
				otu3febbe(14386),
				otu3fees(14387),
				otu3feses(14388),
				otu3feuas(14389),
				otu3fesesr(14390),
				otu3febber(14391),
				odu1pmbbe(14392),
				odu1pmes(14393),
				odu1pmses(14394),
				odu1pmuas(14395),
				odu1pmsesr(14396),
				odu1pmbber(14397),
				odu1pmfebbe(14398),
				odu1pmfees(14399),
				odu1pmfeses(14400),
				odu1pmfeuas(14401),
				odu1pmfesesr(14402),
				odu1pmfebber(14403),
				odu5gpmbbe(14404),
				odu5gpmes(14405),
				odu5gpmses(14406),
				odu5gpmuas(14407),
				odu5gpmsesr(14408),
				odu5gpmbber(14409),
				odu5gpmfebbe(14410),
				odu5gpmfees(14411),
				odu5gpmfeses(14412),
				odu5gpmfeuas(14413),
				odu5gpmfesesr(14414),
				odu5gpmfebber(14415),
				odu2pmbbe(14416),
				odu2pmes(14417),
				odu2pmses(14418),
				odu2pmuas(14419),
				odu2pmsesr(14420),
				odu2pmbber(14421),
				odu2pmfebbe(14422),
				odu2pmfees(14423),
				odu2pmfeses(14424),
				odu2pmfeuas(14425),
				odu2pmfesesr(14426),
				odu2pmfebber(14427),
				odu3pmbbe(14428),
				odu3pmes(14429),
				odu3pmses(14430),
				odu3pmuas(14431),
				odu3pmsesr(14432),
				odu3pmbber(14433),
				odu3pmfebbe(14434),
				odu3pmfees(14435),
				odu3pmfeses(14436),
				odu3pmfeuas(14437),
				odu3pmfesesr(14438),
				odu3pmfebber(14439),
				odu1tcm1iaes(14440),
				odu1tcm2iaes(14441),
				odu1tcm3iaes(14442),
				odu1tcm4iaes(14443),
				odu1tcm5iaes(14444),
				odu1tcm6iaes(14445),
				odu1tcm1biaes(14446),
				odu1tcm2biaes(14447),
				odu1tcm3biaes(14448),
				odu1tcm4biaes(14449),
				odu1tcm5biaes(14450),
				odu1tcm6biaes(14451),
				odu1tcm1bbe(14452),
				odu1tcm1es(14453),
				odu1tcm1ses(14454),
				odu1tcm1uas(14455),
				odu1tcm1sesr(14456),
				odu1tcm1bber(14457),
				odu1tcm2bbe(14458),
				odu1tcm2es(14459),
				odu1tcm2ses(14460),
				odu1tcm2uas(14461),
				odu1tcm2sesr(14462),
				odu1tcm2bber(14463),
				odu1tcm3bbe(14464),
				odu1tcm3es(14465),
				odu1tcm3ses(14466),
				odu1tcm3uas(14467),
				odu1tcm3sesr(14468),
				odu1tcm3bber(14469),
				odu1tcm4bbe(14470),
				odu1tcm4es(14471),
				odu1tcm4ses(14472),
				odu1tcm4uas(14473),
				odu1tcm4sesr(14474),
				odu1tcm4bber(14475),
				odu1tcm5bbe(14476),
				odu1tcm5es(14477),
				odu1tcm5ses(14478),
				odu1tcm5uas(14479),
				odu1tcm5sesr(14480),
				odu1tcm5bber(14481),
				odu1tcm6bbe(14482),
				odu1tcm6es(14483),
				odu1tcm6ses(14484),
				odu1tcm6uas(14485),
				odu1tcm6sesr(14486),
				odu1tcm6bber(14487),
				odu1tcm1febbe(14488),
				odu1tcm1fees(14489),
				odu1tcm1feses(14490),
				odu1tcm1feuas(14491),
				odu1tcm1fesesr(14492),
				odu1tcm1febber(14493),
				odu1tcm2febbe(14494),
				odu1tcm2fees(14495),
				odu1tcm2feses(14496),
				odu1tcm2feuas(14497),
				odu1tcm2fesesr(14498),
				odu1tcm2febber(14499),
				odu1tcm3febbe(14500),
				odu1tcm3fees(14501),
				odu1tcm3feses(14502),
				odu1tcm3feuas(14503),
				odu1tcm3fesesr(14504),
				odu1tcm3febber(14505),
				odu1tcm4febbe(14506),
				odu1tcm4fees(14507),
				odu1tcm4feses(14508),
				odu1tcm4feuas(14509),
				odu1tcm4fesesr(14510),
				odu1tcm4febber(14511),
				odu1tcm5febbe(14512),
				odu1tcm5fees(14513),
				odu1tcm5feses(14514),
				odu1tcm5feuas(14515),
				odu1tcm5fesesr(14516),
				odu1tcm5febber(14517),
				odu1tcm6febbe(14518),
				odu1tcm6fees(14519),
				odu1tcm6feses(14520),
				odu1tcm6feuas(14521),
				odu1tcm6fesesr(14522),
				odu1tcm6febber(14523),
				odu5gtcm1iaes(14524),
				odu5gtcm2iaes(14525),
				odu5gtcm3iaes(14526),
				odu5gtcm4iaes(14527),
				odu5gtcm5iaes(14528),
				odu5gtcm6iaes(14529),
				odu5gtcm1biaes(14530),
				odu5gtcm2biaes(14531),
				odu5gtcm3biaes(14532),
				odu5gtcm4biaes(14533),
				odu5gtcm5biaes(14534),
				odu5gtcm6biaes(14535),
				odu5gtcm1bbe(14536),
				odu5gtcm1es(14537),
				odu5gtcm1ses(14538),
				odu5gtcm1uas(14539),
				odu5gtcm1sesr(14540),
				odu5gtcm1bber(14541),
				odu5gtcm2bbe(14542),
				odu5gtcm2es(14543),
				odu5gtcm2ses(14544),
				odu5gtcm2uas(14545),
				odu5gtcm2sesr(14546),
				odu5gtcm2bber(14547),
				odu5gtcm3bbe(14548),
				odu5gtcm3es(14549),
				odu5gtcm3ses(14550),
				odu5gtcm3uas(14551),
				odu5gtcm3sesr(14552),
				odu5gtcm3bber(14553),
				odu5gtcm4bbe(14554),
				odu5gtcm4es(14555),
				odu5gtcm4ses(14556),
				odu5gtcm4uas(14557),
				odu5gtcm4sesr(14558),
				odu5gtcm4bber(14559),
				odu5gtcm5bbe(14560),
				odu5gtcm5es(14561),
				odu5gtcm5ses(14562),
				odu5gtcm5uas(14563),
				odu5gtcm5sesr(14564),
				odu5gtcm5bber(14565),
				odu5gtcm6bbe(14566),
				odu5gtcm6es(14567),
				odu5gtcm6ses(14568),
				odu5gtcm6uas(14569),
				odu5gtcm6sesr(14570),
				odu5gtcm6bber(14571),
				odu5gtcm1febbe(14572),
				odu5gtcm1fees(14573),
				odu5gtcm1feses(14574),
				odu5gtcm1feuas(14575),
				odu5gtcm1fesesr(14576),
				odu5gtcm1febber(14577),
				odu5gtcm2febbe(14578),
				odu5gtcm2fees(14579),
				odu5gtcm2feses(14580),
				odu5gtcm2feuas(14581),
				odu5gtcm2fesesr(14582),
				odu5gtcm2febber(14583),
				odu5gtcm3febbe(14584),
				odu5gtcm3fees(14585),
				odu5gtcm3feses(14586),
				odu5gtcm3feuas(14587),
				odu5gtcm3fesesr(14588),
				odu5gtcm3febber(14589),
				odu5gtcm4febbe(14590),
				odu5gtcm4fees(14591),
				odu5gtcm4feses(14592),
				odu5gtcm4feuas(14593),
				odu5gtcm4fesesr(14594),
				odu5gtcm4febber(14595),
				odu5gtcm5febbe(14596),
				odu5gtcm5fees(14597),
				odu5gtcm5feses(14598),
				odu5gtcm5feuas(14599),
				odu5gtcm5fesesr(14600),
				odu5gtcm5febber(14601),
				odu5gtcm6febbe(14602),
				odu5gtcm6fees(14603),
				odu5gtcm6feses(14604),
				odu5gtcm6feuas(14605),
				odu5gtcm6fesesr(14606),
				odu5gtcm6febber(14607),
				odu2tcm1iaes(14608),
				odu2tcm2iaes(14609),
				odu2tcm3iaes(14610),
				odu2tcm4iaes(14611),
				odu2tcm5iaes(14612),
				odu2tcm6iaes(14613),
				odu2tcm1biaes(14614),
				odu2tcm2biaes(14615),
				odu2tcm3biaes(14616),
				odu2tcm4biaes(14617),
				odu2tcm5biaes(14618),
				odu2tcm6biaes(14619),
				odu2tcm1bbe(14620),
				odu2tcm1es(14621),
				odu2tcm1ses(14622),
				odu2tcm1uas(14623),
				odu2tcm1sesr(14624),
				odu2tcm1bber(14625),
				odu2tcm2bbe(14626),
				odu2tcm2es(14627),
				odu2tcm2ses(14628),
				odu2tcm2uas(14629),
				odu2tcm2sesr(14630),
				odu2tcm2bber(14631),
				odu2tcm3bbe(14632),
				odu2tcm3es(14633),
				odu2tcm3ses(14634),
				odu2tcm3uas(14635),
				odu2tcm3sesr(14636),
				odu2tcm3bber(14637),
				odu2tcm4bbe(14638),
				odu2tcm4es(14639),
				odu2tcm4ses(14640),
				odu2tcm4uas(14641),
				odu2tcm4sesr(14642),
				odu2tcm4bber(14643),
				odu2tcm5bbe(14644),
				odu2tcm5es(14645),
				odu2tcm5ses(14646),
				odu2tcm5uas(14647),
				odu2tcm5sesr(14648),
				odu2tcm5bber(14649),
				odu2tcm6bbe(14650),
				odu2tcm6es(14651),
				odu2tcm6ses(14652),
				odu2tcm6uas(14653),
				odu2tcm6sesr(14654),
				odu2tcm6bber(14655),
				odu2tcm1febbe(14656),
				odu2tcm1fees(14657),
				odu2tcm1feses(14658),
				odu2tcm1feuas(14659),
				odu2tcm1fesesr(14660),
				odu2tcm1febber(14661),
				odu2tcm2febbe(14662),
				odu2tcm2fees(14663),
				odu2tcm2feses(14664),
				odu2tcm2feuas(14665),
				odu2tcm2fesesr(14666),
				odu2tcm2febber(14667),
				odu2tcm3febbe(14668),
				odu2tcm3fees(14669),
				odu2tcm3feses(14670),
				odu2tcm3feuas(14671),
				odu2tcm3fesesr(14672),
				odu2tcm3febber(14673),
				odu2tcm4febbe(14674),
				odu2tcm4fees(14675),
				odu2tcm4feses(14676),
				odu2tcm4feuas(14677),
				odu2tcm4fesesr(14678),
				odu2tcm4febber(14679),
				odu2tcm5febbe(14680),
				odu2tcm5fees(14681),
				odu2tcm5feses(14682),
				odu2tcm5feuas(14683),
				odu2tcm5fesesr(14684),
				odu2tcm5febber(14685),
				odu2tcm6febbe(14686),
				odu2tcm6fees(14687),
				odu2tcm6feses(14688),
				odu2tcm6feuas(14689),
				odu2tcm6fesesr(14690),
				odu2tcm6febber(14691),
				odu3tcm1iaes(14692),
				odu3tcm2iaes(14693),
				odu3tcm3iaes(14694),
				odu3tcm4iaes(14695),
				odu3tcm5iaes(14696),
				odu3tcm6iaes(14697),
				odu3tcm1biaes(14698),
				odu3tcm2biaes(14699),
				odu3tcm3biaes(14700),
				odu3tcm4biaes(14701),
				odu3tcm5biaes(14702),
				odu3tcm6biaes(14703),
				odu3tcm1bbe(14704),
				odu3tcm1es(14705),
				odu3tcm1ses(14706),
				odu3tcm1uas(14707),
				odu3tcm1sesr(14708),
				odu3tcm1bber(14709),
				odu3tcm2bbe(14710),
				odu3tcm2es(14711),
				odu3tcm2ses(14712),
				odu3tcm2uas(14713),
				odu3tcm2sesr(14714),
				odu3tcm2bber(14715),
				odu3tcm3bbe(14716),
				odu3tcm3es(14717),
				odu3tcm3ses(14718),
				odu3tcm3uas(14719),
				odu3tcm3sesr(14720),
				odu3tcm3bber(14721),
				odu3tcm4bbe(14722),
				odu3tcm4es(14723),
				odu3tcm4ses(14724),
				odu3tcm4uas(14725),
				odu3tcm4sesr(14726),
				odu3tcm4bber(14727),
				odu3tcm5bbe(14728),
				odu3tcm5es(14729),
				odu3tcm5ses(14730),
				odu3tcm5uas(14731),
				odu3tcm5sesr(14732),
				odu3tcm5bber(14733),
				odu3tcm6bbe(14734),
				odu3tcm6es(14735),
				odu3tcm6ses(14736),
				odu3tcm6uas(14737),
				odu3tcm6sesr(14738),
				odu3tcm6bber(14739),
				odu3tcm1febbe(14740),
				odu3tcm1fees(14741),
				odu3tcm1feses(14742),
				odu3tcm1feuas(14743),
				odu3tcm1fesesr(14744),
				odu3tcm1febber(14745),
				odu3tcm2febbe(14746),
				odu3tcm2fees(14747),
				odu3tcm2feses(14748),
				odu3tcm2feuas(14749),
				odu3tcm2fesesr(14750),
				odu3tcm2febber(14751),
				odu3tcm3febbe(14752),
				odu3tcm3fees(14753),
				odu3tcm3feses(14754),
				odu3tcm3feuas(14755),
				odu3tcm3fesesr(14756),
				odu3tcm3febber(14757),
				odu3tcm4febbe(14758),
				odu3tcm4fees(14759),
				odu3tcm4feses(14760),
				odu3tcm4feuas(14761),
				odu3tcm4fesesr(14762),
				odu3tcm4febber(14763),
				odu3tcm5febbe(14764),
				odu3tcm5fees(14765),
				odu3tcm5feses(14766),
				odu3tcm5feuas(14767),
				odu3tcm5fesesr(14768),
				odu3tcm5febber(14769),
				odu3tcm6febbe(14770),
				odu3tcm6fees(14771),
				odu3tcm6feses(14772),
				odu3tcm6feuas(14773),
				odu3tcm6fesesr(14774),
				odu3tcm6febber(14775),
				ds3PbitNearEndBackgroundBlockErrorCounts(14776), --DS3_PNBBE
				ds3PbitNearEndErroredSecondCounts(14777),
				ds3PbitNearEndSeverelyErroredSecondCounts(14778),
				ds3PbitNearEndContinuousSeverelyErroredSecondCounts(14779),
				ds3PbitNearEndUnavailableSecondCounts(14780),
				ds3CPbitNearEndBackgroundBlockErrorCounts(14781),
				ds3CPbitNearEndErroredSecondCounts(14782),
				ds3CPbitSeverelyErroredSecondCounts(14783),
				ds3CPbitNearEndContinuousSeverelyErroredSecondCounts(14784),
				ds3CPbitNearEndUnavailableSecondCounts(14785),
				ds3CPbitFarEndBackgroundBlockErrorCounts(14786),
				ds3CPbitFarEndErroredSecondCounts(14787),
				ds3CPbitFarEndSeverelyErroredSecondCounts(14788),
				ds3CPbitFarEndContinuousSeverelyErroredSecondCounts(14789),
				ds3CPbitFarEndUnavailableSecondCounts(14790),
				ds3FrameAlignErrorSecondCounts(14791),
				otuSmIncomingAlignmentErroredSecond(14792),--OTU_IAES
				otuSmBackwardIncomingAlignmentErroredSecond(14793),--OTU_BIAES
				otuSmBackgroundBlockError(14794),--OTU_BBE
				otuSmErroredSecond(14795),--OTU_ES
				otuSmSeverelyErroredSecond(14796),--OTU_SES
				otuSmUnavailableSeconds(14797),--OTU_UAS
				otuSmSeverelyErroredSecondRatio(14798),--OTU_SESR
				otuSmBackgroundBlockErrorRatio(14799),--OTU_BBER
				otuSmFarBackgroundBlockError(14800),--OTU_FEBBE 
				otuSmFarErroredSecond(14801),--OTU_FEES 
				otuSmFarSeverelyErroredSecond(14802),--OTU_FESES
				otuSmFarUnavailableSeconds(14803),--OTU_FEUAS
				otuSmFarSeverelyErroredSecondRatio(14804),--OTU_FESESR
				otuSmFarBackgroundBlockErrorRatio(14805),--OTU_FEBBER 
				oduPmBackgroundBlockError(14806),--ODU_PM_BBE
				oduPmErroredSecond(14807),--ODU_PM_ES
				oduPmSeverelyErroredSecond(14808),--ODU_PM_SES
				oduPmUnavailableSeconds(14809),--ODU_PM_UAS
				oduPmSeverelyErroredSecondRatio(14810),--ODU_PM_SESR
				oduPmBackgroundBlockErrorRatio(14811),--ODU_PM_BBER 
				oduPmFarBackgroundBlockError(14812),--ODU_PM_FEBBE
				oduPmFarErroredSecond(14813),--ODU_PM_FEES
				oduPmFarSeverelyErroredSecond(14814),--ODU_PM_FESES
				oduPmFarUnavailableSeconds(14815),--ODU_PM_FEUAS
				oduPmFarSeverelyErroredSecondRatio(14816),--ODU_PM_FESESR
				oduPmFarBackgroundBlockErrorRatio(14817),--ODU_PM_FEBBER
				oduTcm1IncomingAlignmentErroredSecond(14818),--ODU_TCM1_IAES
				oduTcm2IncomingAlignmentErroredSecond(14819),--ODU_TCM2_IAES
				oduTcm3IncomingAlignmentErroredSecond(14820),--ODU_TCM3_IAES
				oduTcm4IncomingAlignmentErroredSecond(14821),--ODU_TCM4_IAES
				oduTcm5IncomingAlignmentErroredSecond(14822),--ODU_TCM5_IAES
				oduTcm6IncomingAlignmentErroredSecond(14823),--ODU_TCM6_IAES
				oduTcm1BackwardIncomingAlignmentErroredSecond(14824),--ODU_TCM1_BIAES
				oduTcm2BackwardIncomingAlignmentErroredSecond(14825),--ODU_TCM2_BIAES 
				oduTcm3BackwardIncomingAlignmentErroredSecond(14826),--ODU_TCM3_BIAES
				oduTcm4BackwardIncomingAlignmentErroredSecond(14827),--ODU_TCM4_BIAES
				oduTcm5BackwardIncomingAlignmentErroredSecond(14828),--ODU_TCM5_BIAES 
				oduTcm6BackwardIncomingAlignmentErroredSecond(14829),-- ODU_TCM6_BIAES
				oduTcm1BackgroundBlockError(14830),--ODU_TCM1_BBE 
				oduTcm1ErroredSecond(14831),--ODU_TCM1_ES
				oduTcm1SeverelyErroredSecond(14832),--ODU_TCM1_SES
				oduTcm1UnavailableSeconds(14833),--ODU_TCM1_UAS
				oduTcm1SeverelyErroredSecondRatio(14834),--ODU_TCM1_SESR
				oduTcm1BackgroundBlockErrorRatio(14835),--ODU_TCM1_BBER
				oduTcm2BackgroundBlockError(14836),--ODU_TCM2_BBE
				oduTcm2ErroredSecond(14837),--ODU_TCM2_ES
				oduTcm2SeverelyErroredSecond(14838),--ODU_TCM2_SES
				oduTcm2UnavailableSeconds(14839),--ODU_TCM2_UAS
				oduTcm2SeverelyErroredSecondRatio(14840),--ODU_TCM2_SESR
				oduTcm2BackgroundBlockErrorRatio(14841),--ODU_TCM2_BBER
				oduTcm3BackgroundBlockError(14842),--ODU_TCM3_BBE
				oduTcm3ErroredSecond(14843),--ODU_TCM3_ES
				oduTcm3SeverelyErroredSecond(14844),--ODU_TCM3_SES
				oduTcm3UnavailableSeconds(14845),--ODU_TCM3_UAS
				oduTcm3SeverelyErroredSecondRatio(14846),--ODU_TCM3_SESR
				oduTcm3BackgroundBlockErrorRatio(14847),--ODU_TCM3_BBER 
				oduTcm4BackgroundBlockError(14848),--ODU_TCM4_BBE
				oduTcm4ErroredSecond(14849),--ODU_TCM4_ES
				oduTcm4SeverelyErroredSecond(14850),--ODU_TCM4_SES
				oduTcm4UnavailableSeconds(14851),--ODU_TCM4_UAS
				oduTcm4SeverelyErroredSecondRatio(14852),--ODU_TCM4_SESR
				oduTcm4BackgroundBlockErrorRatio(14853),--ODU_TCM4_BBER
				oduTcm5BackgroundBlockError(14854),--ODU_TCM5_BBE
				oduTcm5ErroredSecond(14855),--ODU_TCM5_ES 
				oduTcm5SeverelyErroredSecond(14856),--ODU_TCM5_SES
				oduTcm5UnavailableSeconds(14857),--ODU_TCM5_UAS
				oduTcm5SeverelyErroredSecondRatio(14858),--ODU_TCM5_SESR
				oduTcm5BackgroundBlockErrorRatio(14859),--ODU_TCM5_BBER
				oduTcm6BackgroundBlockError(14860),--ODU_TCM6_BBE
				oduTcm6ErroredSecond(14861),--ODU_TCM6_ES
				oduTcm6SeverelyErroredSecond(14862),--ODU_TCM6_SES
				oduTcm6UnavailableSeconds(14863),--ODU_TCM6_UAS
				oduTcm6SeverelyErroredSecondRatio(14864),--ODU_TCM6_SESR
				oduTcm6BackgroundBlockErrorRatio(14865),--ODU_TCM6_BBER
				oduTcm1FarBackgroundBlockError(14866),--ODU_TCM1_FEBBE
				oduTcm1FarErroredSecond(14867),--ODU_TCM1_FEES  
				oduTcm1FarSeverelyErroredSecond(14868),--ODU_TCM1_FESES
				oduTcm1FarUnavailableSeconds(14869),--ODU_TCM1_FEUAS
				oduTcm1FarSeverelyErroredSecondRatio(14870),--ODU_TCM1_FESESR
				oduTcm1FarBackgroundBlockErrorRatio(14871),--ODU_TCM1_FEBBER  
				oduTcm2FarBackgroundBlockError(14872),--ODU_TCM2_FEBBE                                        
				oduTcm2FarErroredSecond(14873),--ODU_TCM2_FEES                                                
				oduTcm2FarSeverelyErroredSecond(14874),--ODU_TCM2_FESES                                       
				oduTcm2FarUnavailableSeconds(14875),--ODU_TCM2_FEUAS                                          
				oduTcm2FarSeverelyErroredSecondRatio(14876),--ODU_TCM2_FESESR                                 
				oduTcm2FarBackgroundBlockErrorRatio(14877),--ODU_TCM2_FEBBER                                  
				oduTcm3FarBackgroundBlockError(14878),--ODU_TCM3_FEBBE                                        
				oduTcm3FarErroredSecond(14879),--ODU_TCM3_FEES                                                
				oduTcm3FarSeverelyErroredSecond(14880),--ODU_TCM3_FESES                                       
				oduTcm3FarUnavailableSeconds(14881),--ODU_TCM3_FEUAS                                          
				oduTcm3FarSeverelyErroredSecondRatio(14882),--ODU_TCM3_FESESR                                 
				oduTcm3FarBackgroundBlockErrorRatio(14883),--ODU_TCM3_FEBBER                                  
				oduTcm4FarBackgroundBlockError(14884),--ODU_TCM4_FEBBE                                        
				oduTcm4FarErroredSecond(14885),--ODU_TCM4_FEES                                                
				oduTcm4FarSeverelyErroredSecond(14886),--ODU_TCM4_FESES                                       
				oduTcm4FarUnavailableSeconds(14887),--ODU_TCM4_FEUAS                                          
				oduTcm4FarSeverelyErroredSecondRatio(14888),--ODU_TCM4_FESESR                                 
				oduTcm4FarBackgroundBlockErrorRatio(14889),--ODU_TCM4_FEBBER                                  
				oduTcm5FarBackgroundBlockError(14890),--ODU_TCM5_FEBBE                                        
				oduTcm5FarErroredSecond(14891),--ODU_TCM5_FEES                                                
				oduTcm5FarSeverelyErroredSecond(14892),--ODU_TCM5_FESES                                       
				oduTcm5FarUnavailableSeconds(14893),--ODU_TCM5_FEUAS                                          
				oduTcm5FarSeverelyErroredSecondRatio(14894),--ODU_TCM5_FESESR                                 
				oduTcm5FarBackgroundBlockErrorRatio(14895),--ODU_TCM5_FEBBER                                  
				oduTcm6FarBackgroundBlockError(14896),--ODU_TCM6_FEBBE                                        
				oduTcm6FarErroredSecond(14897),--ODU_TCM6_FEES                                                
				oduTcm6FarSeverelyErroredSecond(14898),--ODU_TCM6_FESES                                       
				oduTcm6FarUnavailableSeconds(14899),--ODU_TCM6_FEUAS                                          
				oduTcm6FarSeverelyErroredSecondRatio(14900),--ODU_TCM6_FESESR                                 
				oduTcm6FarBackgroundBlockErrorRatio(14901),--ODU_TCM6_FEBBER                                  
				theDispersionCompensationMaximumValue(14902),--TDCMAX                                         
				theDispersionCompensationMinimumValue(14903),--TDCMIN                                         
				theDispersionCompensationCurrentValue(14904),--TDCCUR                                         
				cpServiceCreationRequests(14905),--CP_SER_REQ_ALL                                             
				cpServiceCreationSuccesses(14906),--CP_SER_REQ_OK                                             
				cpServiceCreationFailures(14907),--CP_SER_REQ_FAIL                                            
				cpServiceInterruptionCount(14908),--CP_SER_INT_COUNT                                          
				cpServiceInterruptionTime(14909),--CP_SER_INT_TIME                                            
				cpServiceSLAdegradationCount(14910),--CP_SER_DEG_COUNT                                        
				cpServiceSLAdegradationTime(14911),--CP_SER_DEG_TIME                                          
				cpServiceRerouteSuccesses(14912),--CP_SER_RER_OK                                              
				cpServiceRerouteFailures(14913),--CP_SER_RER_FAIL                                             
				cpServiceRerouteTime(14914),--CP_SER_RER_TIME                                                 
				cpTELinkDownCount(14915),--CP_TEL_DOWN_COUNT                                                  
				cpTELinkDownTime(14916),--CP_TEL_DOWN_TIME                                                    
				cpControlChannelDownCount(14917),--CP_CC_DOWN_COUNT                                           
				cpControlChannelDownTime(14918),--CP_CC_DOWN_TIME  
				cpuUsageMaximum(14919),--CPUUSAGEMAX
				cpuUsageMinimum(14920),--CPUUSAGEMIN
				cpuUsageCurrent(14921),--CPUUSAGECUR
				memoryUsageMaximum(14922),--MEMUSAGEMAX
				memoryUsageMinimum(14923),--MEMUSAGEMIN
				memoryUsageCurrent(14924),--MEMUSAGECUR
				theValueOfQData(14925),--Q_VALUE_EER
				fecBefCorerFloat(14926),--FEC_BEF_CORER_FLOAT
				fecAftCorerFloat(14927),--FEC_AFT_CORER_FLOAT 
				cesBBE(14928),--CES_BBE                          
				cesES(14929),--CES_ES 
				cesSES(14930),--CES_SES
				cesCSES(14931),--CES_CSES
				cesUAS(14932),--CES_UAS
				mplsTunnelLS(14933),--MPLS_TUNNEL_LS
				mplsTunnelSLS(14934),--MPLS_TUNNEL_SLS
				mplsTunnelCSLS(14935),--MPLS_TUNNEL_CSLS
				mplsTunnelUAS(14936),--MPLS_TUNNEL_UAS
				ethCfmLS(14937),--ETH_CFM_LS
				ethCfmSLS(14938),--ETH_CFM_SLS   
				ethCfmCSLS(14939),--ETH_CFM_CSLS
				ethCfmUAS(14940),--ETH_CFM_UAS
				intermediateFrequencyBBackgroundBlockError(14941),--IF_BBE
				intermediateFrequencyErroredSecond(14942),--IF_BBE
				intermediateFrequencySeverelyErroredSecond(14943),--IF_SES
				intermediateFrequencyUnavailableSecond(14944),--IF_UAS
				intermediateFrequencyConsecutiveSeverelyErroredSecond(14945),--IF_CSES
				probopMax(14946),--PROBOPMAX
				probopMin(14947),--PROBOPMIN
				probopCur(14948),--PROBOPCUR
				loadopMax(14949),--LOADOPMAX
				loadopMin(14950),--LOADOPMIN
				loadopCur(14951),--LOADOPCUR
				probtemMax(14952),--PROBTEMMAX
				probtemMin(14953),--PROBTEMMIN
				probtemCur(14954),--PROBTEMCUR
				loadtemMax(14955),--LOADTEMMAX
				loadtemMin(14956),--LOADTEMMIN
				loadtemCur(14957),--LOADTEMCUR
				probcoolMax(14958),--PROBCOOLMAX
				probcoolMin(14959),--PROBCOOLLMIN
				probcoolCur(14960),--PROBCOOLCUR 
				loadcoolMax(14961),--LOADCOOLMAX
				loadcoolMin(14962),--LOADCOOLMIN
				loadcoolCur(14963),--LOADCOOLCUR
				probbcMax(14964),--PROBBCMAX
				probbcMin(14965),--PROBBCLMIN
				probbcCur(14966),--PROBBCLCUR 
				loadbcMax(14967),--LOADBCMAX
				loadbcMin(14968),--LOADBCMIN
				loadbcCur(14969),--LOADBCCUR 
				apdvolMax(14970),--APDVOLMAX
				apdvolMin(14971),--APDVOLMIN
				apdvolCur(14972),--APDVOLCUR                 
				inopMax(14973),--INOPMAX
				inopMin(14974),--INOPMIN
				inopCur(14975),--INOPCUR 
				apdtemMax(14976),--APDTEMMAX
				apdtemMin(14977),--APDTEMMIN
				apdtemCur(14978),--APDTEMCUR
				cpwServiceCreationRequests(14979),--CPW_SER_REQ_ALL
				cpwServiceCreationSuccesses(14980),--CPW_SER_REQ_OK
				cpwServiceCreationFailures(14981),--CPW_SER_REQ_FAIL
				cpwServiceInterruptionCount(14982),--CPW_SER_INT_COUNT
				cpwServiceInterruptionTime(14983),--CPW_SER_INT_TIME
				cpwServiceSlaDegradeCount(14984),--CPW_SER_DEG_COUNT
				cpwServiceSlaDegradeTime(14985),--CPW_SER_DEG_TIME
				cpwServiceRerouteSuccesses(14986),--CPW_SER_RER_OK
				cpwServiceRerouteFailures(14987),--CPW_SER_RER_FAIL
				cpwServiceRerouteTime(14988),--CPW_SER_RER_TIME
				cpwControlChannelDownCount(14989),--CPW_CC_DOWN_COUNT
				cpwControlChannelDownTime(14990),--CPW_CC_DOWN_TIME
				maximumValueOfBoardTemperature(14991),--BDTEMPMAX
				minimumValueOfBoardTemperature(14992),--BDTEMPMIN
				currentValueOfBoardTemperature(14993),--BDTEMPCUR
				apdcoolMax(14994),--APDCOOLMAX
				apdcoolMin(14995),--APDCOOLMIN
				apdcoolCur(14996),--APDCOOLCUR
				evoatemMax(14997),--EVOATEMMAX
				evoatemMin(14998),--EVOATEMMIN
				evoatemCur(14999),--EVOATEMCUR 
				evoacoolMax(15000),--EVOACOOLMAX
				evoacoolMin(15001),--EVOACOOLMIN
				evoacoolCur(15002),--EVOACOOLCUR 
				wltemMax(15003),--WLTEMMAX
				wltemMin(15004),--WLTEMMIN
				wltemCur(15005),--WLTEMCUR       
				averageReceiveSignalLevel(15043),--RSL_AVG
				averageTransmissionSignalLevel(15047),--TSL_AVG
				positiveATPCAdjust(15041),--ATPC_P_ADJUST
				negativeATPCAdjust(15042),--ATPC_N_ADJUST
				transmissionSignalLevelBeyondHighThreshold(15050),--TLHTT
				transmissionSignalLevelBeyondLowThreshold(15051),--TLLTT
				receiveSignalLevelUnderHighThreshold(15052),--RLHTT
				receiveSignalLevelUnderLowThreshold(15053),--RLLTT
				qpskWorkSecond(15033),--QPSKWS
				qam16WorkSecond(15034),--QAMWS16
				qam32WorkSecond(15035),--QAMWS32
				qam64WorkSecond(15036),--QAMWS64
				qam128WorkSecond(15037),--QAMWS128
				qam256WorkSecond(15038),--QAMWS256
				adaptiveModulationUpAdjustCounts(15049),--FB_AMDCNT
				adaptiveModulationDownAdjustCounts(15048)--FB_AMUCNT
                		}
			
		
--  -------------------------------------------------------------------------
-- Alarm event type
-- -------------------------------------------------------------------------
		SdhAlarmEventType ::= TEXTUAL-CONVENTION
			STATUS current
			DESCRIPTION 
				"Alarm ID."
			SYNTAX INTEGER
				{
				receiveLossOfSignal(1),
				transmitLossOfSignal(2),
				receiveLossOfClock(3),
				transmitLossOfClock(4),
				receiveOutOfFrame(5),
				noBoardSoftware(6),
				configuredWaveLevelNotComplying(7),
				receiveLossOfFrame(8),
				transmissionFailure(9),
				regeneratorSectionPerformanceOverThreshold(10),
				regeneratorSectionUnavailableTimeEvent(11),
				regeneratorSectionB1ExcessiveErrors(12),
				receiveReferenceLossOfClock(13),
				transmitReferenceLossOfClock(14),
				workingTemperatureOverThreshold(15),
				highOrderPathPerformanceOverThreshold(16),
				highOrderPathUnavailableTimeEvent(17),
				lossOfDownlinkJ1Signal(18),
				lossOfMultiplexSectionNodeInformation(19),
				highOrderPathTraceIndentifierLossOfLock(20),
				workingCurrentLockFailed(21),
				workingCurrentOverThreshold(22),
				coolingCurrentOverThreshold(23),
				inputPowerFailed(24),
				inputPowerAbnormal(25),
				outputPowerAbnormal(26),
				outputPowerFailed(27),
				opticalModuleWorkingTemperatureOverThreshold(28),
				laserTemperatureTooHigh(29),
				laserTemperatureTooLow(30),
				inputPowerTooHigh(31),
				inputPowerTooLow(32),
				multiplexSectionAlarmIndicationSignal(33),
				multiplexSectionRemoteDefectIndication(34),
				multiplexSectionB2ExcessiveErrors(35),
				multiplexSectionB2SignalDegrade(36),
				multiplexSectionRemoteErrorIndication(37),
				multiplexSectionPerformanceOverThreshold(38),
				multiplexSectionUnavailableTimeEvent(39),
				k1k2BytesReceivingFailed(40),
				automaticProtectionSwitchIndication(41),
				automaticProtectionSwitchFailed(42),
				inputOpticalFailed(43),
				receiveSynchronousLoss(44),
				laserPowerAlarm(45),
				receiveSideSlidingFrame(46),
				transmitSideSlidingFrame(47),
				lowOrderPathRemoteFailureIndication(48),
				lowOrderPathPerformanceOverThreshold(49),
				lowOrderPathUnavailableTimeEvent(50),
				tuStructureError(51),
				laserDrivingCurrentOverride(52),
				crc4MultiframeErrorCodeCountOverThreshold(53),
				receiveRemoteAlarm(54),
				laserOutputPowerTooLow(55),
				laserWillBeOutOfWork(56),
				laserNotInstalled(57),
				setoverCurrentOfLaserOverThreshold(58),
				currentOfLaserBackAgainstLightOverThreshold(59),
				coolingCurrentOfLaserOverThreshold(60),
				lossOfInputSingal(61),
				lossOfOutputSingal(62),
				outputPowerTooHigh(63),
				outputPowerTooLow(64),
				highOrderPathAlarmIndicationSignal(65),
				auLossOfPointer(66),
				multiplexSectionAdaptionPerformanceOverThreshold(67),
				workingTemperatureOfPumpLaserOverThreshold(68),
				setoverCurrentOfPumpLaserOverThreshold(69),
				highOrderPathB3SignalDegrade(70),
				highOrderPathB3ExcessiveErrors(71),
				auAlarmIndicationSignal(72),
				fifoOverflowOnHPReceiveSide(73),
				fifoOverflowOnHPTransmitSide(74),
				highOrderPathUnequipped(75),
				highOrderPathTraceIdentifierMismatch(76),
				highOrderPathSignalLabelMismatch(77),
				highOrderPathRemoteDefectIndication(78),
				highOrderPathRemoteErrorIndication(79),
				mailCommunicationError(80),
				highOrderPathLossOfMultiframe(81),
				tuLossOfPointer(82),
				tuAlarmIndicationSignal(83),
				highOrderPathAdaptionPerformanceOverThreshold(84),
				laserFallToSearchingState(85),
				laserSearchingStepOverThreshold(86),
				j0TraceIdentifierMismatch(87),
				fifoOverflowOnReceiveSideOfLowerOrderPath(88),
				fifoOverflowOnTransmitSideOfLowerOrderPath(89),
				lowOrderPathUnequipped(90),
				lowOrderPathTraceIdentifierMismatch(91),
				lowOrderPathSignalLabelMismatch(92),
				lowOrderPathRemoteDefectIndication(93),
				lowOrderPathRemoteErrorIndication(94),
				lowOrderPathAlarmIndicationSignal(95),
				noInputOfDIN(96),
				lossOfSystemFrameSFP(97),
				anotherBoardStateVariation(98),
				readOrWriteSingleChipRegisterFailed(99),
				lossOfTimingInput(100),
				synchronousSourceDegrade(101),
				overheadProcessingRAMLossOfClock(102),
				alarmSerialPortTransmitClockLoss(103),
				interface2MLossOfExternalClock(104),
				interface2MLossOfTransmitClock(105),
				interface2MLossOfDigitalSignal(106),
				interface2MLossOfAnalogSignal(107),
				interface2MTransmitDrivingEquipmentError(108),
				ramReadOrWriteError(109),
				configurationDataLoss(110),
				synchronousSourceLevelLoss(111),
				wayOfSTMConfigurationError(112),
				boardBufferAreaError(113),
				externalSynchronousSourceJitterOverflow(114),
				fanFailed(115),
				busDroppingLossOfClock(116),
				line2MLossOfSignal(117),
				upSignal2MAlarmIndicationSignal(118),
				boardNotInPositionAlarm(119),
				protectionSwitchIndication(120),
				wrongBoardType(121),
				dspLoadFailure(122),
				boardSoftwareVersionMismatch(123),
				fInterfaceCommunicationsFailed(124),
				powerFailure(125),
				otherAlarmsOfSL4(127),
				dropBusJ1LockLost(128),
				rLop(129),
				upSignalAlarmIndication(130),
				pSlError(131),
				c2Eq0(132),
				rRDI(133),
				lossOfPDHInterfaceSignal(134),
				lossOfPDHInterfaceInputSignalClock(135),
				tOVFL(136),
				pdhInterfaceSignalAlarmIndicationSignal(137),
				e3RAMLOC(138),
				addToBusLossOfClock(139),
				addingSignalJ1Lost(140),
				receivedSignalError(141),
				tug3New(142),
				memoryError(143),
				adding140MSignalAlarmIndicationSignal(144),
				dropping140MSignalAlarmIndicationSignal(145),
				gainLow(146),
				configurationVerify(147),
				firstTransmitFIFOOverflow(148),
				receivedNewPointer(149),
				pathMonitorFail(150),
				mspProtocolError(151),
				mspControlerIsStopedManully(152),
				droppingLossOfPointer(154),
				externalLossOfSignal(155),
				transmitFIFOOverflow(156),
				receiveFIFOOverflow(157),
				configurationOverflow(158),
				receiveFIFOReset(159),
				transmitFIFOReset(160),
				lossOfVoltageControlledCrystalClock(161),
				lossOfTransmitPhaselockRingClock(162),
				lossOfReceivePhaselockRingClock(163),
				p1Alarm(164),
				p2Alarm(165),
				temperatureOverThreshold(166),
				humidityOverThreshold(167),
				powerAlarmMinor(168),
				powerAlarmMajor(169),
				digitalJitterFIFOOverflow(170),
				lossOfT1Synchronization(171),
				t1ReceiveSideFIFOOverflow(172),
				t1TransmitSideFIFOOverflow(173),
				relayAlarm(174),
				regeneratorSectionB1SignalDegrade(175),
				b1ErrorCodeOverThresholdPerSecond(176),
				masterSlaveSwitch(177),
				exerciseSwitchFailed(178),
				opmFailed(179),
				k1k2Mismatch(180),
				k2Mismatch(181),
				bipSignalDegrade(182),
				bipExcssiveErrors(183),
				lossOfExternalSynchronousSource(184),
				databaseError(185),
				mutLOS(186),
				chanLOS(187),
				chanADD(188),
				transmitorDegrade(189),
				noBoardPara(190),
				eEPROMError(191),
				coolingCurrentOfPumpLaserOverThreshold(192),
				referenceSourceChangeInS1Mode(193),
				fpgaAbnormal(194),
				reciveDataError(195),
				savingDataDifference(196),
				nestateInstall(197),
				dbmsInProtectMode(198),
				communicationFailed(199),
				securityAlarm(200),
				downSignal2MAlarmIndicationSignal(201),
				monitorFailed(202),
				apsParaError(203),
				auLOPC(204),
				auAISC(205),
				mutilFrameSequenceIndicatorDisorder(206),
				hpLOMC(207),
				mutilFrameIndicatorDisorder(208),
				n1AIS(209),
				powerDiffDefect(210),
				powerDifOver(211),
				forwardErrorCorrectionLossOfFrame(212),
				forwardErrorCorrectionOutOfFrame(213),
				almOCD(214),
				nesfLost(215),
				almLCD(216),
				almHCS(217),
				almUHCS(218),
				almCHCS(219),
				almSUBCARDABN(220),
				fuseAlarm(221),
				mdlAlarm(222),
				speedOver(223),
				crcExc(224),
				opswFail(225),
				vpAIS(226),
				vpRDI(227),
				vcAIS(228),
				vcRDI(229),
				vpLOC(230),
				ccLOC(231),
				cfgbdFail(232),
				cfgXcFatalErr(233),
				sncpFail(234),
				ethernetLOS(235),
				hardBAD(236),
				alarmPatch(239),
				pathLOOPBACKStatus(240),
				vcTrunkPathSwitch(241),
				configureParamarsNotApplyToBoard(242),
				rmonAlarm(243),
				bdbuscoreConflictAlarm(244),
				portDataFluxOverflow(245),
				codeViolationError(246),
				overflowFlagForIccOrLocc(247),
				vcDelayTLID(248),
				fanCommFail(256),
				sensorFail(257),
				hardFail(258),
				nebdXcDif(259),
				auCmm(260),
				linkErr(261),
				offlineOfWrench(262),
				outOfLock(263),
				wdmidMismatch(264),
				voltLos(265),
				lossOfClockInUpSignal(266),
				hdlcFail(267),
				almNolsrParaFile(268),
				aDCheckedFail(269),
				moduleCoolingCurrentOver(270),
				moduleTemperatureOver(271),
				otuLayerLossofFrameAlignment(272),
				otuLayerOutofMultiFrame(273),
				switchingModuleTraceIdentifierMismatch(274),
				projectManagementTraceIdentifierMismatch(275),
				switchingModuleBackwordDefectIndication(276),
				projectManagementBackwordDefectIndication(277),
				switchingModuleBackwordErrorIndication(278),
				projectManagementBackwordErrorIndication(279),
				switchingModuleImportAdjustError(280),
				projectManagementInportAdjustError(281),
				switchingModuleBIP8Over(282),
				projectManagementBIP8Over(283),
				switchingModuleSignalDegraded(284),
				projectManagementSignalDegraded(285),
				opticalTransportUnitAlarmIndicationSignal(286),
				opticalDataUnitAlarmIndicationSignal(287),
				opticalDataUnitOpenConnectionIndication(288),
				opticalDataUnitLock(289),
				pulseWidthModulateCoolingCurrentoverthresholdAlarm(291),
				digitalSignalProcessorLoadFail(292),
				moduleDriveCurrentOver(293),
				moduleDriveVoltageOver(294),
				ortSwitchSubtenancyFail(295),
				autoLaserShutdownAlarm(296),
				dropEventStatisticDataOverTheTopThreshold(297),
				dropEventStatisticDataFallUndertheBottomThreshold(298),
				receivedOctetsInBadPacketOverTheTopThreshold(299),
				receivedOctetsInBadPacketFallUnderTheBottomThreshold(300),
				sendOctetsInBadPacketOverTheTopThreshold(301),
				sendOctetsInBadPacketFallUnderTheBottomThreshold(302),
				collisionsDetectedOverTheTopThreshold(303),
				collisionsDetectedFallUnderTheBottomThreshold(304),
				alignmentErrorsOverTheTopThreshold(305),
				alignmentErrorsFallUnderTheBottomThreshold(306),
				fCSCheckSumErrorOverTheTopThreshold(307),
				fCSCheckSumErrorUnderTheBottomThreshold(308),
				collisionsDuringTheLatestTimeSlotOverTopThreshold(309),
				collisionsDuringTheLatestTimeSlotUnderBottomThreshold(310),
				excessiveCollisionsOverTheTopThreshold(311),
				excessiveCollisionsFallUnderTheBottomThreshold(312),
				packetsTransmissionDefferedOverTheTopThreshold(313),
				packetsTransmissionDefferedUnderTheBottomThreshold(314),
				theNumberOffalsecarrierEventsDetectedOverTheTopThreshold(315),
				theNumberOffalsecarrierEventsDetectedFallTheBottomThreshold(316),
				com485Break(317),
				laserTempratureOver(318),
				lossofServiceClock(319),
				physicalPathandLogicalPathVerifiedNotIdentical(320),
				thePathPriorityofBothTerminalVerifiedNotIdentical(321),
				interrackCommunicationFailed(322),
				sumInputPowertooHigh(323),
				sumInputPowertooLow(324),
				sumOutputPowertooHigh(325),
				sumOutputPowertooLow(326),
				opticalAmplifierPlusReduce(327),
				overheadSyncClockFail(328),
				mclockloss(329),
				relativeClkLos(330),
				opticalProtectionSwitchIndication(331),
				opticalProtectionSwitchFail(332),
				clockRunningModeEnterNoTrace(333),
				laserParameterMismatchAlarm(334),
				beffecExc(335),
				mspControlerIsStopedManually(336),
				edfaTemperatureOverTheThreshlod(337),
				rlofOfAddionalTransferClock(338),
				aisOfAddionalTransferClock(339),
				crcOfAddionalTransferClock(340),
				bipolarPolarityViolationofAddionalTransferClock(341),
				locofScc(342),
				inputPowerFailAlarm(343),
				outputPowerFailAlarm(344),
				powerTemperatureHigh(345),
				powerTemperatureOverThreshold(346),
				remoteLinkErrorAlarmIndication(347),
				remoteSingalDegradeAlarmIndication(348),
				remoteSingalUnequip(349),
				bdXcNotSwitch(350),
				bdVerNotMatch(351),
				lossofTamdemConnection(352),
				tandemConnectionUnequip(353),
				tandemConnectionIncomingAIS(354),
				tandemConnectionRemoteDefectIndication(355),
				tandemConnectionOutgoingDefectIndication(356),
				tandemConnectionTraceIdentifierMismatch(357),
				tandemConnectionRemoteErrorIndication(358),
				tandemConnectionOutgoingErrorIndication(359),
				tandemConnectionExcessiveError(360),
				tandemConnectiondegradedSignal(361),
				auSquelching(362),
				stgServiceMaterDiffer(363),
				laserClosedAlarm(364),
				tLosex(365),
				c2Vcais(366),
				fSelectBpchaN(367),
				c2Pdi(368),
				ohLoop(369),
				hpSdi(370),
				hpPdi(371),
				hpCdi(372),
				fSelectStg(373),
				testStatus(374),
				othHardFail(375),
				switchDisble(376),
				busErr(377),
				dccFailAlarm(378),
				tmpDiffOver(379),
				fanspeedCtr(380),
				mbusOffline(381),
				mbusSerial(382),
				powerAlm(383),
				powerSwitch(384),
				tempMajAlm(385),
				tempMinAlm(386),
				canAlarm(387),
				xcUnswitch(388),
				rs485ComPortFial(389),
				syncLockOff(390),
				syncFMSwitch(391),
				laserNotExist(392),
				laserModErr(393),
				sdhSideErrorIndication(394),
				almAu3ais(395),
				almAu3lop(396),
				almAu3tim(397),
				almAu3slm(398),
				almAu3uneq(399),
				almAu3rdi(400),
				almAu3rei(401),
				almAu3b3sd(402),
				almAu3b3Over(403),
				systemBusFailAlarm(404),
				t1AlarmIndicatorSignal(405),
				bdIdError(406),
				relayFail(407),
				phaseLockedLoopFail(408),
				chipFail(409),
				sparePathAlm(410),
				phoneHoldon(411),
				powerAbnormal(412),
				speedError(413),
				duplexError(414),
				initFailure(415),
				lSError(416),
				pauseError(417),
				comEpldFault(418),
				boardOffline(419),
				telephoneHangupForTooLongTime(420),
				fanPwrAlm(421),
				sccChangeAlarm(422),
				slaveBad(423),
				slaveWorking(424),
				powerInterfaceUnitAlarm(425),
				sncpIndicate(426),
				tpsIndicate(427),
				mainbdSubbdMismatch(428),
				voltageLow(429),
				transmitLossofFrame(430),
				transmitMultiplexSectionAlarmIndication(431),
				moduleCommunicateFailure(432),
				dgeAdjustFailure(433),
				insertionLossOver(434),
				otdrAcquireFiberCriticalAlarm(435),
				otdrAcquireFiberMajorAlarm(436),
				otdrAcquireFiberMinorAlarm(437),
				backupPowerUsed(438),
				waveLengthLockFailure(439),
				hscUnavailable(440),
				ethernetPortReceiveNoData(441),
				ethernetPortTransmitNoData(442),
				pwrLowProtected(443),
				fanFullSpeed(444),
				offlineOfRearBoard(445),
				ohErr(446),
				logFull(447),
				cpldFail(448),
				biosStatus(449),
				pwrOver(450),
				pwrLow(451),
				hdlcOff(452),
				tRsbbe(453),
				tRses(454),
				tRsses(455),
				tRscses(456),
				tRsuas(457),
				tRsofs(458),
				tRsoof(459),
				tMsbbe(460),
				tMses(461),
				tMsses(462),
				tMsuas(463),
				tMscses(464),
				tMsfebbe(465),
				tMsfees(466),
				tMsfeses(467),
				tMsfecses(468),
				tAupjcHigh(469),
				tAupjclow(470),
				tHhpbbe(471),
				tHpes(472),
				tHpses(473),
				tHpuas(474),
				tHpcses(475),
				tHpfebbe(476),
				tHpfees(477),
				tHpfeses(478),
				tHpfecses(479),
				tTupjchigh(480),
				tTupjclow(481),
				tLpbbe(482),
				tLpes(483),
				tLpses(484),
				tLpuas(485),
				tLpcses(486),
				tLpfebbe(487),
				tLpfees(488),
				tLpfeses(489),
				tLpfecses(490),
				acPowerTemp(492),
				pbuBdOffLine(493),
				backupServiceRoute(494),
				rPRprotectionstatusChangeAlarm(495),
				rprStationsExceed(496),
				rprNbInconsis(497),
				rprMisConfig(498),
				rprDuplicateMac(499),
				rprPmInconsis(500),
				mbusUpdateFail(501),
				envAircompr(502),
				envAircond(503),
				envAirdryr(504),
				envBatdschrg(505),
				envBattery(506),
				envClfan(507),
				envCpmajor(508),
				envCpminor(509),
				envEngine(510),
				envEngoprg(511),
				envExplgs(512),
				envFirdetr(513),
				envFire(514),
				envFlood(515),
				envFuse(516),
				envGen(517),
				envHiair(518),
				envHihum(519),
				envHitemp(520),
				envHiwtr(521),
				envIntruder(522),
				envLwbatvg(523),
				envLwfuel(524),
				envLwhum(525),
				envLwpres(526),
				envLwtemp(527),
				envLwwtr(528),
				envMisc(529),
				envOpendr(530),
				envPower(531),
				envPump(532),
				envPwr1(533),
				envPwr2(534),
				envPwr3(535),
				envPwr4(536),
				envRect(537),
				envRecthi(538),
				envRectlo(539),
				envSmoke(540),
				envToxicgas(541),
				envVentn(542),
				contAircond(543),
				contEngine(544),
				contFan(545),
				contGen(546),
				contHeat(547),
				contLight(548),
				contMisc(549),
				contSpklr(550),
				wKswbk(551),
				wKswpr(552),
				mAnwkswbk(553),
				mAnwkswpr(554),
				fRcdwkswbk(555),
				fRcdwkswpr(556),
				lOckoutofpr(557),
				lOckoutofwk(558),
				sWto(559),
				mAnswto(560),
				fRcdswto(561),
				fRngsync(562),
				hLdovrsync(563),
				lsrShtdn(564),
				aCLsrShtdn(565),
				lpbkterm(566),
				lpbkfACILITY(567),
				aCLPBK(568),
				protna(569),
				eSconCodeError(570),
				masterSlaveSoftwareDifferentAlarm(571),
				rPRSumA0Exceed(572),
				activatedTimeOut(573),
				fileLost(574),
				sCCChanged(575),
				masterUnitFailAlarm(576),
				squelchModeMismatch(577),
				nodeIdMismatch(578),
				ringMapModeMismatch(579),
				squelchTableModeMismatch(580),
				ringMapUndone(581),
				controlChannelDownAlarm(582),
				crc6CheckErrorsOver(583),
				bootromCheckSumAlarm(584),
				concatXcLimited(585),
				dpsBdVerDif(586),
				sysParaIsNotSameWithCFDB(587),
				systemDefaultRunningAlarm(588),
				veriftyLicenseErrorAlarm(589),
				licenseGoingtoExpireAlarm(590),
				sccSyncFail(591),
				extCommFailAlarm(592),
				linkAggregationGroupFail(593),
				chipAbnormal(597),
				eccChannelHasBIP8Errors(598),
				masterBoardAlarm(599),
				msAutoProtectSwitchIndicateExpand(600),
				vpRingGroupMismatch(601),
				vcRingGroupMismatch(602),
				xcNonDualTransmittedAlarm(603),
				clientTypeNotMatchAlarm(604),
				passThroughAlarm(605),
				laserModuleMismatch(606),
				v5VirtualContainerAlarmIndicationSignal(607),
				lossOfContinuityFailureDefect(608),
				lossOfContinuityFailure(609),
				dServerAlarm(610),
				dLOCVAlarm(611),
				dTTSIMismatchAlarm(612),
				dTTSIMismergeAlarm(613),
				dExcessAlarm(614),
				dUnknownAlarm(615),
				bdiAlarm(616),
				fdiAlarm(617),
				chipFIFOOverflow(618),
				mismatchInUnidirectionalAndBidirectionalOperationInMspLinear(619),
				patchFileNotExit(620),
				patchError(621),
				patchNotConfirm(622),
				fanTypeMismatch(623),
				rtcTimeFailAlarm(624),
				logicBoardNotInstalled(625),
				microWaveLinkIdentifierMismatch(626),
				rsSignalDegrade(627),
				rsSignalFail(628),
				intermediateFrequencyLossOfClock(629),
				intermediateFrequencyLossOfSignal(630),
				headofMicroWaveFrameUnreachable(631),
				radioLossOfFrame(632),
				radioAlarmIndication(633),
				hotStandbyBackupSwitchFail(634),
				radioTransmissionLevelTooLow(635),
				radioTransmissionLevelTooHigh(636),
				radioReceiveLevelTooHigh(637),
				radioReceiveLevelTooLow(638),
				radioTransmissionMute(639),
				configerationNotSupport(640),
				outdoorUnitFail(641),
				outdoorUnitVoltageAlarm(642),
				outdoorUnitCurrenctAlarm(643),
				waysideInterfaceLossOfSignal(644),
				portWorkingModeMismatchesTheServices(645),
				vc3PathPerformanceParameterOverride(646),
				framedE1RemoteErrorIndication(647),
				almAuxiliaryPattern(648),
				almISDNLoopback(649),
				almPRBSTest(650),
				almRegMM(651),
				returnLosslow(652),
				returnLossShut(653),
				failureInTheInputOfTheOppositeEnd(654),
				e3OrDs3OutOfFrame(655),
				ds3FrameFormatMismatch(656),
				e3OrDs3SingalsRAI(657),
				attributeDifferenceBetweenWorkingAndProtectionChannel(658),
				swdlChgMngNoMatch(2561),
				swdlActivated(2562),
				swdlBdMatchHw(2563),
				swdlSlvMatchHw(2564),
				swdlSlaveMatch(2565),
				swdlBdMatch(2566),
				swdlNePkgCheck(2567),
				swdlFileExcluded(2569),
				swdlRollBackFailure(2570),
				swdlCommitFailure(2571),
				swdlInProcess(2572),
				swdlNePkgVerCheckFail(2573),
				swdlAutoSwdlDisable(2574),
				dlagProtectFailure(12288),
				tributaryProtectionSwitchingFails(12289),
				twoOrMoreFansFail(12290),
				p2pEthernetOAMLoopAlarm(12291),
				p2pEthernetOAMRemoteSD(12292),
				p2pEthernetOAMRemoteCriticalFault(12293),
				p2pEthernetOAMDiscoveryFail(12294),
				t1DownstreamSignalAlarmIndication(12295),
				ethernetContinuityCheckMessageLoss(12296),
				ethernetMaintenanceIdentifyConflict(12297),
				continuityCheckMessageLoss(12298),
				maintenanceIdentifyConflict(12299),
				linkPathStateThroughRemoteFailIndication(12300),
				ethernetPortInFlowOver(12301),
				subrackIdConflictr(12302),
				subrackIdNotMismatch(12303),
				subrackFormingLoop(12304),
				criticalRelayAlarm(12305),
				majorRelayAlarm(12306),
				minorRelayAlarm(12307),
				ignoreRelayAlarm(12308),
				fanFault(12309),
				configureDataOfNeSoftwareIsOutOfRange(12310),
				lossOfOTU1Frame(12311),
				otu1AlarmIndicationSignal(12312),
				lossOfOTU1Multiframe(12313),
				otu1TraceIdentifierMismatch(12314),
				otu1SignalDegrade(12315),
				otu1BackwardAlarmIndication(12316),
				lossOfOTU5GFrame(12317),
				otu5GAlarmIndicationsignal(12318),
				lossOfOTU5GMultiframe(12319),
				otu5GTraceIdentifierMismatch(12320),
				otu5GSignalDegrade(12321),
				otu5GBackwardAlarmIndication(12322),
				lossOfOTU2Frame(12323),
				otu2AlarmIndicationSignal(12324),
				lossOfOTU2Multiframe(12325),
				otu2TraceIdentifierMismatch(12326),
				otu2SignalDegrade(12327),
				otu2BbackwardAlarmIndication(12328),
				lossOfOTU3Frame(12329),
				otu3AlarmIndicationSignal(12330),
				lossOfOTU3Multiframe(12331),
				otu3TraceIdentifierMismatch(12332),
				otu3SignalDegrade(12333),
				otu3BackwardAlarmIndication(12334),
				odu1PMTraceIdentifierMmismatch(12335),
				odu1PMSignalDegradeAlarm(12336),
				odu1PMBackwardDefectIndication(12337),
				odu1PMLockedDefect(12338),
				odu1PMOpenConnectionIndication(12339),
				odu1PMAlarmIndicationSignal(12340),
				odu1PMLossOfFrameAndMultiFrame(12341),
				odu5GPMTraceIdentifierMismatch(12342),
				odu5GPMSignalDegradeAlarm(12343),
				odu5GPMBackwardDefectIndication(12344),
				odu5GPMLockedDefect(12345),
				odu5GPMOpenConnectionIndication(12346),
				odu5GPMAlarmIndicationSignal(12347),
				odu5GPMLossOfFrameAndMultiFrame(12348),
				odu2PMTraceIdentifierMismatch(12349),
				odu2PMSignalDegradeAlarm(12350),
				odu2PMBackwardDefectIndication(12351),
				odu2PMLockedDefect(12352),
				odu2PMOpenConnectionIndication(12353),
				odu2PMAlarmIndicationSignal(12354),
				odu2PMLossOfFrameAndMultiFrame(12355),
				odu3PMTraceIdentifierMismatch(12356),
				odu3PMSignalDegradeAlarm(12357),
				odu3PMBackwardDefectIndication(12358),
				odu3PMLockedDefect(12359),
				odu3PMOpenConnectionIndication(12360),
				odu3PMAlarmIndicationSignal(12361),
				odu3PMLossOfFrameAndMultiFrame(12362),
				odu1TCM1TraceIdentifierMismatch(12363),
				odu1TCM2TraceIdentifierMismatch(12364),
				odu1TCM3TraceIdentifierMismatch(12365),
				odu1TCM4TraceIdentifierMismatch(12366),
				odu1TCM5TraceIdentifierMismatch(12367),
				odu1TCM6TraceIdentifierMismatch(12368),
				odu1TCM1SignalDegrade(12369),
				odu1TCM2SignalDegrade(12370),
				odu1TCM3SignalDegrade(12371),
				odu1TCM4SignalDegrade(12372),
				odu1TCM5SignalDegrade(12373),
				odu1TCM6SignalDegrade(12374),
				odu1TCM1BackwardDefectIndication(12375),
				odu1TCM2BackwardDefectIndication(12376),
				odu1TCM3BackwardDefectIndication(12377),
				odu1TCM4BackwardDefectIndication(12378),
				odu1TCM5BackwardDefectIndication(12379),
				odu1TCM6BackwardDefectIndication(12380),
				odu1TCM1AlarmIndicationSignal(12381),
				odu1TCM2AlarmIndicationSignal(12382),
				odu1TCM3AlarmIndicationSignal(12383),
				odu1TCM4AlarmIndicationSignal(12384),
				odu1TCM5AlarmIndicationSignal(12385),
				odu1TCM6AlarmIndicationSignal(12386),
				odu1TCM1OpenConnectionIndication(12387),
				odu1TCM2OpenConnectionIndication(12388),
				odu1TCM3OpenConnectionIndication(12389),
				odu1TCM4OpenConnectionIndication(12390),
				odu1TCM5OpenConnectionIndication(12391),
				odu1TCM6OpenConnectionIndication(12392),
				odu1TCM1LockedDefect(12393),
				odu1TCM2LockedDefect(12394),
				odu1TCM3LockedDefect(12395),
				odu1TCM4LockedDefect(12396),
				odu1TCM5LockedDefect(12397),
				odu1TCM6LockedDefect(12398),
				odu1TCM1LossOfTandemConnection(12399),
				odu1TCM2LossOfTandemConnection(12400),
				odu1TCM3LossOfTandemConnection(12401),
				odu1TCM4LossOfTandemConnection(12402),
				odu1TCM5LossOfTandemConnection(12403),
				odu1TCM6LossOfTandemConnection(12404),
				odu5GTCM1TraceIdentifierMismatch(12405),
				odu5GTCM2TraceIdentifierMismatch(12406),
				odu5GTCM3TraceIdentifierMismatch(12407),
				odu5GTCM4TraceIdentifierMismatch(12408),
				odu5GTCM5TraceIdentifierMismatch(12409),
				odu5GTCM6TraceIdentifierMismatch(12410),
				odu5GTCM1SignalDegrade(12411),
				odu5GTCM2SignalDegrade(12412),
				odu5GTCM3SignalDegrade(12413),
				odu5GTCM4SignalDegrade(12414),
				odu5GTCM5SignalDegrade(12415),
				odu5GTCM6SignalDegrade(12416),
				odu5GTCM1BackwardDefectIndication(12417),
				odu5GTCM2BackwardDefectIndication(12418),
				odu5GTCM3BackwardDefectIndication(12419),
				odu5GTCM4BackwardDefectIndication(12420),
				odu5GTCM5BackwardDefectIndication(12421),
				odu5GTCM6BackwardDefectIndication(12422),
				odu5GTCM1AlarmIndicationSignal(12423),
				odu5GTCM2AlarmIndicationSignal(12424),
				odu5GTCM3AlarmIndicationSignal(12425),
				odu5GTCM4AlarmIndicationSignal(12426),
				odu5GTCM5AlarmIndicationSignal(12427),
				odu5GTCM6AlarmIndicationSignal(12428),
				odu5GTCM1OpenConnectionIndication(12429),
				odu5GTCM2OpenConnectionIndication(12430),
				odu5GTCM3OpenConnectionIndication(12431),
				odu5GTCM4OpenConnectionIndication(12432),
				odu5GTCM5OpenConnectionIndication(12433),
				odu5GTCM6OpenConnectionIndication(12434),
				odu5GTCM1LockedDefect(12435),
				odu5GTCM2LockedDefect(12436),
				odu5GTCM3LockedDefect(12437),
				odu5GTCM4LockedDefect(12438),
				odu5GTCM5LockedDefect(12439),
				odu5GTCM6LockedDefect(12440),
				odu5GTCM1LossOfTandemConnection(12441),
				odu5GTCM2LossOfTandemConnection(12442),
				odu5GTCM3LossOfTandemConnection(12443),
				odu5GTCM4LossOfTandemConnection(12444),
				odu5GTCM5LossOfTandemConnection(12445),
				odu5GTCM6LossOfTandemConnection(12446),
				odu2TCM1TraceIdentifierMismatch(12447),
				odu2TCM2TraceIdentifierMismatch(12448),
				odu2TCM3TraceIdentifierMismatch(12449),
				odu2TCM4TraceIdentifierMismatch(12450),
				odu2TCM5TraceIdentifierMismatch(12451),
				odu2TCM6TraceIdentifierMismatch(12452),
				odu2TCM1SignalDegrade(12453),
				odu2TCM2SignalDegrade(12454),
				odu2TCM3SignalDegrade(12455),
				odu2TCM4SignalDegrade(12456),
				odu2TCM5SignalDegrade(12457),
				odu2TCM6SignalDegrade(12458),
				odu2TCM1BackwardDefectIndication(12459),
				odu2TCM2BackwardDefectIndication(12460),
				odu2TCM3BackwardDefectIndication(12461),
				odu2TCM4BackwardDefectIndication(12462),
				odu2TCM5BackwardDefectIndication(12463),
				odu2TCM6BackwardDefectIndication(12464),
				odu2TCM1AlarmIndicationSignal(12465),
				odu2TCM2AlarmIndicationSignal(12466),
				odu2TCM3AlarmIndicationSignal(12467),
				odu2TCM4AlarmIndicationSignal(12468),
				odu2TCM5AlarmIndicationSignal(12469),
				odu2TCM6AlarmIndicationSignal(12470),
				odu2TCM1OpenConnectionIndication(12471),
				odu2TCM2OpenConnectionIndication(12472),
				odu2TCM3OpenConnectionIndication(12473),
				odu2TCM4OpenConnectionIndication(12474),
				odu2TCM5OpenConnectionIndication(12475),
				odu2TCM6OpenConnectionIndication(12476),
				odu2TCM1LockedDefect(12477),
				odu2TCM2LockedDefect(12478),
				odu2TCM3LockedDefect(12479),
				odu2TCM4LockedDefect(12480),
				odu2TCM5LockedDefect(12481),
				odu2TCM6LockedDefect(12482),
				odu2TCM1LossOfTandemConnection(12483),
				odu2TCM2LossOfTandemConnection(12484),
				odu2TCM3LossOfTandemConnection(12485),
				odu2TCM4LossOfTandemConnection(12486),
				odu2TCM5LossOfTandemConnection(12487),
				odu2TCM6LossOfTandemConnection(12488),
				odu3TCM1TraceIdentifierMismatch(12489),
				odu3TCM2TraceIdentifierMismatch(12490),
				odu3TCM3TraceIdentifierMismatch(12491),
				odu3TCM4TraceIdentifierMismatch(12492),
				odu3TCM5TraceIdentifierMismatch(12493),
				odu3TCM6TraceIdentifierMismatch(12494),
				odu3TCM1SignalDegrade(12495),
				odu3TCM2SignalDegrade(12496),
				odu3TCM3SignalDegrade(12497),
				odu3TCM4SignalDegrade(12498),
				odu3TCM5SignalDegrade(12499),
				odu3TCM6SignalDegrade(12500),
				odu3TCM1BackwardDefectIndication(12501),
				odu3TCM2BackwardDefectIndication(12502),
				odu3TCM3BackwardDefectIndication(12503),
				odu3TCM4BackwardDefectIndication(12504),
				odu3TCM5BackwardDefectIndication(12505),
				odu3TCM6BackwardDefectIndication(12506),
				odu3TCM1AlarmIndicationSignal(12507),
				odu3TCM2AlarmIndicationSignal(12508),
				odu3TCM3AlarmIndicationSignal(12509),
				odu3TCM4AlarmIndicationSignal(12510),
				odu3TCM5AlarmIndicationSignal(12511),
				odu3TCM6AlarmIndicationSignal(12512),
				odu3TCM1OpenConnectionIndication(12513),
				odu3TCM2OpenConnectionIndication(12514),
				odu3TCM3OpenConnectionIndication(12515),
				odu3TCM4OpenConnectionIndication(12516),
				odu3TCM5OpenConnectionIndication(12517),
				odu3TCM6OpenConnectionIndication(12518),
				odu3TCM1LockedDefect(12519),
				odu3TCM2LockedDefect(12520),
				odu3TCM3LockedDefect(12521),
				odu3TCM4LockedDefect(12522),
				odu3TCM5LockedDefect(12523),
				odu3TCM6LockedDefect(12524),
				odu3TCM1LossOfTandemConnection(12525),
				odu3TCM2LossOfTandemConnection(12526),
				odu3TCM3LossOfTandemConnection(12527),
				odu3TCM4LossOfTandemConnection(12528),
				odu3TCM5LossOfTandemConnection(12529),
				odu3TCM6LossOfTandemConnection(12530),
				oPU1payloadLabelMismatch(12531),
				oPU5GPayloadLabelMismatch(12532),
				oPU2PayloadLabelMismatch(12533),
				oPU2MultiplexStructureIdentifierMismatch(12534),
				oPU3PayloadLabelMismatch(12535),
				oPU3MultiplexStructureIdentifierMismatch(12536),
				opticalLineProtectionSwitching(12537),
				interOTU1P1OpticalChannelProtectionSwitching(12538),
				intraOTU1P1OpticalChannelProtectionSwitching(12539),
				clientside1P1OpticalChannelProtectionSwitching(12540),
				oduSNCPProtectionSwitching(12541),
				subWavelengthSncpProtectionSwitching(12542),
				vlanSncpProtectionSwitching(12543),
				remoteFault(12544),
				localFault(12545),
				neSoftEditionDifferAlarm(12546),
				masterSlaveMismatch(12547),
				otu1ExcessiveBIP8Errors(12548),
				odu1PMSectionExcessiveBIP8Errors(12549),
				odu1TCM1SectionExcessiveBIP8Errors(12550),
				odu1TCM2SectionExcessiveBIP8Errors(12551),
				odu1TCM3SectionExcessiveBIP8Errors(12552),
				odu1TCM4SectionExcessiveBIP8Errors(12553),
				odu1TCM5SectionExcessiveBIP8Errors(12554),
				odu1TCM6SectionExcessiveBIP8Errors(12555),
				otu5GExcessiveBIP8Errors(12556),
				odu5GPMSectionExcessiveBIP8Errors(12557),
				odu5GTCM1SectionExcessiveBIP8Errors(12558),
				odu5GTCM2SectionExcessiveBIP8Errors(12559),
				odu5GTCM3SectionExcessiveBIP8Errors(12560),
				odu5GTCM4SectionExcessiveBIP8Errors(12561),
				odu5GTCM5SectionExcessiveBIP8Errors(12562),
				odu5GTCM6SectionExcessiveBIP8Errors(12563),
				otu2ExcessiveBIP8Errors(12564),
				odu2PMSectionExcessiveBIP8Errors(12565),
				odu2TCM1SectionExcessiveBIP8Errors(12566),
				odu2TCM2SectionExcessiveBIP8Errors(12567),
				odu2TCM3SectionExcessiveBIP8Errors(12568),
				odu2TCM4SectionExcessiveBIP8Errors(12569),
				odu2TCM5SectionExcessiveBIP8Errors(12570),
				odu2TCM6SectionExcessiveBIP8Errors(12571),
				otu3ExcessiveBIP8Errors(12572),
				odu3PMSectionExcessiveBIP8Errors(12573),
				odu3TCM1SectionExcessiveBIP8Errors(12574),
				odu3TCM2SectionExcessiveBIP8Errors(12575),
				odu3TCM3SectionExcessiveBIP8Errors(12576),
				odu3TCM4SectionExcessiveBIP8Errors(12577),
				odu3TCM5SectionExcessiveBIP8Errors(12578),
				odu3TCM6SectionExcessiveBIP8Errors(12579),
				hardwareFault(12580),
				noELabel(12581),
				lptSwitchingOccurred(12582),
				ethernet8B10BOdingDecodingError(12583),
				voaAdjustmentFailure(12584),
				opticalModuleAdjustmentFailure(12585),
				tcpConnectionBetweenNEAndSyslogServerIsBroken(12586),
				microWaveRemoteDefectIndication(12587),
				microWaveFECUncorrectable(12588),
				abnormalIFPowerReceivedByODU(12589),
				xcsProtectionSwitchingIndication(12590),
				hsbSwitchingIndication(12591),
				hsmSwitchingIndication(12592),
				wrongDeviceType(12593),
				ds3FrameIdle(12594),
				clientside1p1ProtectionCannotStart(12595),
				opticalCrossPowerAdjustFailIndicatio(12596), 
				theLaserIsEnabledForcibly(12597),					
				cfCardOffline(12598),--CFCARD_OFFLINE
				cfCardFailed(12599),--CFCARD_FAILED
				cfCardWriteAndReadDisable(12600),--CFCARD_W_R_DISABLED
				powerIsOverflow(12601),--NE_POWER_OVER
				boardWorksAtLowpower(12602),--BD_AT_LOWPOWER
				fcSyncLos(12603),--FC_SYNC_LOS
				fcLinkError(12604),--FC_LINK_ERR
				fc8b10bErrorOver(12605),--FC_8B10BERR_OVER   
				updatingTheOpticalModuleMicroProgramOrParameterTableFails(12606),--MODULEFILE_UPDATE_FAIL
				intelligentPowerAdjustmentStarted(12607),--IPA_START
				cpServiceProtectionAbilityDegradedAlarm(12608),--CP_1P1SER_PRO_DEG
				cpServiceInterruptedAlarm(12609),--CP_SER_INTERRUPT
				cpTeLinkDegradeAlarm(12610),--CP_TEL_DEGRADED
				cpOchStateMismatchAtTwoEndsofLinkAlarm(12611),--CP_TE_OCH_MIS
				cpLspAbnormallyDownGradedAlarm(12612),--CP_LSP_ABN_DGD
				cpLspAbnormallyDeletedAlarm(12613),--CP_LSP_ABN_DEL
				soSKMismatch(12614),--SO_SK_MISMATCH
				trailTraceIdentifierMismatchatOTSLayer(12615),--OTS_TIM
				lossOfSignalAtOTSLayer(12616),--OTS_LOS
				lossOfSignalPayloadAtOTSLayer(12617),--OTS_LOS_P
				lossOfSignalOverheadAtOTSLayer(12618),--OTS_LOS_O
				backwardDefectIndicatorAtOTSLayer(12619),--OTS_BDI
				backwardDefectIndicatorPayloadAtOTSLayer(12620),--OTS_BDI_P
				backwardDefectindicatorOverheadAtOTSLayer(12621),--OTS_BDI_O
				lossOfOosOTMoverheadSignal(12622),--OOS_LOST
				lossOfSignalPayloadAtOMSLayer(12623),--OMS_LOS_P
				serverSignalFailAtOMSLayer(12624),--OMS_SSF
				serverSignalFailPayloadAtOMSLayer(12625),--OMS_SSF_P
				serverSignalFailOverheadAtOMSLayer(12626),--OMS_SSF_O
				forwardDefectIndicatorAtOMSLayer(12627),--OMS_FDI
				forwardDefectIndicatorPayloadAtOMSLayer(12628),--OMS_FDI_P
				forwardDefectIndicatorOverheadAtOMSLayer(12629),--OMS_FDI_O
				backwardDefectIndicatorAtOMSLayer(12630),--OMS_BDI
				backwardDefectIndicatorPayloadAtOMSLayer(12631),--OMS_BDI_P
				backwarddefectindicatorOverheadAtOMSLayer(12632),--OMS_BDI_O
				lossofSignalPayloadAtOChLayer(12633),--OCH_LOS_P
				openConnectionIndicationAtOChLayer(12634),--OCH_OCI
				serverSignalFailAtOChlayer(12635),--OCH_SSF
				serverSignalFailPayloadAtOChLayer(12636),--OCH_SSF_P
				serverSignalFailOverheadAtOChLayer(12637),--OCH_SSF_O
				forwardDefectIndicatorAtOChLayer(12638),--OCH_FDI
				forwardDefectIndicatorPayloadAtOChLayer(12639),--OCH_FDI_P
				forwardDefectIndicatorOverheadAtOChLayer(12640),--OCH_FDI_O
				odukSpringProtectionSwitching(12641),--ODUKSP_PS
				opticalWaveShareProtectionSwitching(12642),--OWSP_PS
				lossOfPseudoRandomBinarySequenceSignal(12643),--PRBS_LSS
				databaseRestorationFailure(12644),--DB_RESTORE_FAIL
				oduTCM1MonitoringSectionTraceIdentifierMismatch(12645),--ODU_TCM1_TIM
				oduTCM1MonitoringSectionBackwardDefectIndication(12646),--ODU_TCM1_BDI
				oduTCM1MonitoringSectionBackwardErrorIndication(12647),--ODU_TCM1_BEI
				oduTCM1MonitoringSectionAlarmIndicationSignal(12648),--ODU_TCM1_AIS
				oduTCM1MonitoringSectionLockout(12649),--ODU_TCM1_LCK
				oduTCM1MonitoringSectionOpenConnectionIndicationO(12650),--DU_TCM1_OCI
				oduTCM1MonitoringSectionLossOfTandemConnection(12651),--ODU_TCM1_LTC
				oduTCM1MonitoringSectionSignalDegradeInTheBurstMode(12652),--ODU_TCM1_DEG
				oduTCM1MonitoringSectionSignalDegradeInThePoissonMode(12653),--ODU_TCM1_SD
				oduTCM1MonitoringSectionExcessiveErrorInThePoissonMode(12654),--ODU_TCM1_EXC
				oduTCM1MonitoringSectionServerSignalFailure(12655),--ODU_TCM1_SSF
				oduTCM2MonitoringSectionTraceIdentifierMismatch(12656),--ODU_TCM2_TIM
				oduTCM2MonitoringSectionBackwardDefectIndication(12657),--ODU_TCM2_BDI
				oduTCM2MonitoringSectionBackwardErrorIndication(12658),--ODU_TCM2_BEI
				oduTCM2MonitoringSectionAlarmIndicationSignal(12659),--ODU_TCM2_AIS
				oduTCM2MonitoringSectionLockout(12660),--ODU_TCM2_LCK
				oduTCM2MonitoringSectionOpenConnectionIndication(12661),--ODU_TCM2_OCI
				oduTCM2MonitoringSectionLossOfTandemConnection(12662),--ODU_TCM2_LTC
				oduTCM2MonitoringSectionSignalDegradeInTheBurstMode(12663),--ODU_TCM2_DEG
				oduTCM2MonitoringSectionSignalDegradeInThePoissonMode(12664),--ODU_TCM2_SD
				oduTCM2MonitoringSectionExcessiveErrorInThePoissonMode(12665),--ODU_TCM2_EXC
				oduTCM2MonitoringSectionServerSignalFailure(12666),--ODU_TCM2_SSF
				oduTCM3MonitoringSectionTraceIdentifierMismatch(12667),--ODU_TCM3_TIM
				oduTCM3MonitoringSectionBackwardDefectIndication(12668),--ODU_TCM3_BDI
				oduTCM3MonitoringSectionBackwardErrorIndication(12669),--ODU_TCM3_BEI
				oduTCM3MonitoringSectionAlarmIndicationSignal(12670),--ODU_TCM3_AIS
				oduTCM3MonitoringSectionLockout(12671),--ODU_TCM3_LCK
				oduTCM3MonitoringSectionOpenConnectionIndication(12672),--ODU_TCM3_OCI
				oduTCM3MonitoringSectionLossOfTandemConnection(12673),--ODU_TCM3_LTC
				oduTCM3MonitoringSectionSignalDegradeInTheBurstMode(12674),--ODU_TCM3_DEG
				oduTCM3MonitoringSectionSignalDegradeInThePoissonMode(12675),--ODU_TCM3_SD
				oduTCM3MonitoringSectionExcessiveErrorInThePoissonMode(12676),--ODU_TCM3_EXC
				oduTCM3MonitoringSectionServerSignalFailure(12677),--ODU_TCM3_SSF
				oduTCM4MonitoringSectionTraceIdentifierMismatch(12678),--ODU_TCM4_TIM
				oduTCM4MonitoringSectionBackwardDefectIndication(12679),--ODU_TCM4_BDI
				oduTCM4MonitoringSectionBackwardErrorIndication(12680),--ODU_TCM4_BEI
				oduTCM4MonitoringSectionAlarmIndicationSignal(12681),--ODU_TCM4_AIS
				oduTCM4MonitoringSectionLockout(12682),--ODU_TCM4_LCK
				oduTCM4MonitoringSectionOpenConnectionIndication(12683),--ODU_TCM4_OCI
				oduTCM4MonitoringSectionLossOfTandemConnection(12684),--ODU_TCM4_LTC
				oduTCM4MonitoringSectionSignalDegradeInTheBurstMode(12685),--ODU_TCM4_DEG
				oduTCM4MonitoringSectionSignalDegradeInThePoissonMode(12686),--ODU_TCM4_SD
				oduTCM4MonitoringSectionExcessiveErrorInThePoissonMode(12687),--ODU_TCM4_EXC
				oduTCM4MonitoringSectionServerSignalFailure(12688),--ODU_TCM4_SSF
				oduTCM5MonitoringSectionTraceIdentifierMismatch(12689),--ODU_TCM5_TIM
				oduTCM5MonitoringSectionBackwardDefectIndication(12690),--ODU_TCM5_BDI
				oduTCM5MonitoringSectionBackwardErrorIndication(12691),--ODU_TCM5_BEI
				oduTCM5MonitoringSectionAlarmIndicationSignal(12692),--ODU_TCM5_AIS
				oduTCM5MonitoringSectionLockout(12693),--ODU_TCM5_LCK
				oduTCM5MonitoringSectionOpenConnectionIndication(12694),--ODU_TCM5_OCI
				oduTCM5MonitoringSectionLossOfTandemConnection(12695),--ODU_TCM5_LTC
				oduTCM5MonitoringSectionSignalDegradeInTheBurstMode(12696),--ODU_TCM5_DEG
				oduTCM5MonitoringSectionSignalDegradeInThePoissonMode(12697),--ODU_TCM5_SD
				oduTCM5MonitoringSectionExcessiveErrorInThePoissonMode(12698),--ODU_TCM5_EXC
				oduTCM5MonitoringSectionServerSignalFailure(12699),--ODU_TCM5_SSF
				oduTCM6MonitoringSectionTraceIdentifierMismatch(12700),--ODU_TCM6_TIM
				oduTCM6MonitoringSectionBackwardDefectIndication(12701),--ODU_TCM6_BDI
				oduTCM6MonitoringSectionBackwardErrorIndication(12702),--ODU_TCM6_BEI
				oduTCM6MonitoringSectionAlarmIndicationSignal(12703),--ODU_TCM6_AIS
				oduTCM6MonitoringSectionLockout(12704),--ODU_TCM6_LCK
				oduTCM6MonitoringSectionOpenConnectionIndication(12705),--ODU_TCM6_OCI
				oduTCM6MonitoringSectionLossOfTandemConnection(12706),--ODU_TCM6_LTC
				oduTCM6MonitoringSectionSignalDegradeInTheBurstMode(12707),--ODU_TCM6_DEG
				oduTCM6MonitoringSectionSignalDegradeInThePoissonMode(12708),--ODU_TCM6_SD
				oduTCM6MonitoringSectionExcessiveErrorInThePoissonMode(12709),--ODU_TCM6_EXC
				oduTCM6MonitoringSectionServerSignalFailure(12710),--ODU_TCM6_SSF
				otu1ServerSignalFail(12711),--OTU1_SSF
				odu1PMServerSignalFail(12712),--ODU1_PM_SSF
				odu1TCM1ServerSignalFail(12713),--ODU1_TCM1_SSF
				odu1TCM2ServerSignalFail(12714),--ODU1_TCM2_SSF
				odu1TCM3ServerSignalFail(12715),--ODU1_TCM3_SSF
				odu1TCM4ServerSignalFail(12716),--ODU1_TCM4_SSF
				odu1TCM5ServerSignalFail(12717),--ODU1_TCM5_SSF    
				odu1TCM6ServerSignalFail(12718),--ODU1_TCM6_SSF
				otu5GServerSignalFail(12719),--OTU5G_SSF
				odu5GPMServerSignalFail(12720),--ODU5G_PM_SSF
				odu5GTCM1ServerSignalFail(12721),--ODU5G_TCM1_SSF
				odu5GTCM2ServerSignalFail(12722),--ODU5G_TCM2_SSF
				odu5GTCM3ServerSignalFail(12723),--ODU5G_TCM3_SSF
				odu5GTCM4ServerSignalFail(12724),--ODU5G_TCM4_SSF
				odu5GTCM5ServerSignalFail(12725),--ODU5G_TCM5_SSF    
				odu5GTCM6ServerSignalFail(12726),--ODU5G_TCM6_SSF               
				otu2ServerSignalFail(12727),--OTU2_SSF
				odu2PMServerSignalFail(12728),--ODU2_PM_SSF
				odu2TCM1ServerSignalFail(12729),--ODU2_TCM1_SSF
				odu2TCM2ServerSignalFail(12730),--ODU2_TCM2_SSF
				odu2TCM3ServerSignalFail(12731),--ODU2_TCM3_SSF
				odu2TCM4ServerSignalFail(12732),--ODU2_TCM4_SSF
				odu2TCM5ServerSignalFail(12733),--ODU2_TCM5_SSF    
				odu2TCM6ServerSignalFail(12734),--ODU2_TCM6_SSF
				otu3ServerSignalFail(12735),--OTU3_SSF
				odu3PMServerSignalFail(12736),--ODU3_PM_SSF
				odu3TCM1ServerSignalFail(12737),--ODU3_TCM1_SSF
				odu3TCM2ServerSignalFail(12738),--ODU3_TCM2_SSF
				odu3TCM3ServerSignalFail(12739),--ODU3_TCM3_SSF
				odu3TCM4ServerSignalFail(12740),--ODU3_TCM4_SSF
				odu3TCM5ServerSignalFail(12741),--ODU3_TCM5_SSF    
				odu3TCM6ServerSignalFail(12742),--ODU3_TCM6_SSF
				opu1VirtualConcatenatedPayloadTypeMismatch(12743),--OPU1_VCAT_VcPLM
				opu1SequenceIndicatorMismatch(12744),--OPU1_VCAT_SQM
				dispersionCompensationMarginisInsufficient(12745),--DCM_INSUFF
				odu2Sequenceindicatormismatch(12746),--ODU2_VCAT_SQM
				odu2MultiframeAlignmentSignalDelayout(12747),--ODU2_VCAT_LOA
				odu2DefectPayLoadMismatch(12748),--ODU2_PLM
				odu2DefectVirtualConcatenatedPayLoadMismatch(12749),--ODU2_VCAT_VcPLM
				cpNodeIDError(12750),--CP_NODE_ID_ERR
				cpNodeIDConflict(12751),--CP_NODE_ID_CONFLICT
				cpServiceInterrupted(12752),--CP_SER_INT
				cpServiceSLADegraded(12753),--CP_SER_SLA_DEG
				cpAssociatedServiceSynchronizationFailure(12754),--CP_ASER_SYNC_FAIL
				cpLSPInterrupted(12755),--CP_LSP_INT
				cpLSPSignalingException(12756),--CP_LSP_SIG_EXCEPT
				cpControlChannelDown(12757),--CP_CC_DOWN
				cpTELinkDown(12758),--CP_TEL_DOWN
				cpTELinkDegraded(12759),--CP_TEL_DEG
				cpTELinkMSPConfigMismatch(12760),--CP_TEL_MSP_MIS
				cpTELinkPathStateMismatch(12761),--CP_TEL_PATH_MIS
				cpRSVPNeighborDown(12762),--CP_RSVP_NB_DOWN
				cpRSVPNeighborAuthenticationError(12763),--CP_RSVP_AUTH_ERR
				cpOSPFControlLinkDown(12764),--CP_OSPF_CL_DOWN
				cpOSPFNeighborAuthenticationError(12765),--CP_OSPF_AUTH_ERR
				cpOSPFNeighborDown(12766),--CP_OSPF_NB_DOWN
				ethernetOAMSelfLoopAlarm(12767),--ETHOAM_SELF_LOOP
				ethernetOAMVCTRUNKSelfLoopAlarm(12768),--ETHOAM_VCG_SELF_LOOP
				lagPortAggregationFailure(12769),--LAG_PORT_FAIL
				lagVCTRUNKAggregationFailure(12770),--LAG_VC_PORT_FAIL
				waveLenOver(12771),--WAVELEN_OVER
				cableMisconnected(12772),--CABLE_MISCONN
				laserInvalid(12773),--LSR_INVALID 
				tunableFilterModuleSelfTestFail(12774),--TF_CHECK_FAIL
				patchPackageDeactivationTimeout(12775),--PATCH_DEACT_TIMEOUT
				patchPackageActivationTimeout(12776), --PATCH_ACT_TIMEOUT 
				cfCardCapacityFullyUsed(12777),-- CFCARD_FULL
				theQValueIsHigherThanTheThreshold(12778),--Q_VALUE_EXC
				onlyOnePumpCardIsWorking(12779),--ONE_PUMP_WORK
				pumpLaserConnectionLoss(12780),--PUMP_LINK_ULLAGE_HIGH
				laserWillAging(12781),--LSR_WILL_AGING   
				aserFailure(12782), --LSR_WILL_INVALIDATE
				pumpLaserBackFacetCurrentThresholdCrossing(12783),--PUMP_BCK_ALM
				thePumpCardIsOffline(12784),--PUMP_OFFLINE
				inputLightBeing(12785), --INPUT_LINGHT_BEING In the ASE mode, if there is input light, the ASE function is turned off
				noTrafficAtEthernetPort(12786),--ETH_NO_FLOW
				noTrafficAtVctrunkPort(12787),--VCTRUNK_NO_FLOW
				workingModeMismatchAtRemoteFePort(12788),--PORTMODE_MISMATCH
				theDccChannelResourceIsInsufficient(12789),--DCC_CHAN_LACK
				patchPackageFileError(12790),--PATCH_PKGERR
				neIpConflict(12791),-- NEIP_CONFLICT
				stateOfAutoSynchronizationDisabled(12792),--SYNC_DISABLE
				alarmOfLinkDown(12793),--ETH_LINK_DOWN			                                                                                                            
				macFcsExcess(12794),--MAC_FCS_EXC an alarm indicating that the number of FCS errors received over the Ethernet interface crosses the threshold
				macFcsSD(12795),-- MAC_FCS_SD an alarm indicating that FCS errors received over the Ethernet interface crosses the lower(degraded) threshold
				cesLossPacketsExcess(12796),--CES_LOSPKT_EXC
				cesMisorderDroppedPacketsExcess(12797),--CES_MISORDERPKT_EXC
				cesStrayDroppedPacketsExcess(12798),--CES_STRAYPKT_EXC
				cesMalformedPacketsExcessAlarm(12799),--CES_MALPKT_EXC
				cesJitterBufferUnderrunAlarm(12800),--CES_JTRUDR_EXC
				cesJitterBufferOverrunAlarm(12801),-- CES_JTROVR_EXC
				cesReceiveRemoteAlarm(12802),--CES_RDI
				mpDown(12803),--MP_DOWN  ML PPP down
				mpDelay(12804),--MP_DELAY   
				pppLcpFail(12805),-- LCP fail alarm
				pppNcpFail(12806),--PPP_NCP_FAIL  
				macFdbOfElanUsedUp(12807),--FDBSIZEALM_ELAN
				vpLostOfContinuityCheck(12808),--VP_LOC
				vcLostOfContinuityCheck(12809),--VC_LOC 
				alarmOfStpBpduGuard(12810),--STP_BPDU_GUARD_ALM 
				alarmOfStpRootGuard(12811),--STP_ROOT_GUARD_ALM  
				alarmOfStpLoopGuard(12812),--STP_LOOP_GUARD_ALM
				alarmOfBridgeLoseRootRole(12813),--STP_ROOTBRIDGE_LOST_ALM 
				mplsTunnelLossOfConnectivityVerificationDefect(12814),--MPLS_TUNNEL_LOCV
				mplsTunnelReceivingExcessRateOfCV(12815),--MPLS_TUNNEL_Excess
				mplsTunnelTrailTerminationSourceIdentifierMismatchDefect(12816),--MPLS_TUNNEL_MISMATCH
				mplsTunnelTrailTerminationSourceIdentifierMismergeDefect(12817),--MPLS_TUNNEL_MISMERGE
				mplsTunnelUnknownDefectInTheMplsNetwork(12818),--MPLS_TUNNEL_UNKNOWN 
				mplsTunnelBackwardDefectIndicator(12819),--MPLS_TUNNEL_BDI
				mplsTunnelForwardDefectIndicator(12820),--MPLS_TUNNEL_FDI
				mplsTunnelSignalDegrade(12821),-- MPLS_TUNNEL_SD
				mplsTunnelSignalFail(12822),--MPLS_TUNNEL_SF
				ethCfmCrossConnect(12823),--ETH_CFM_MISMERGE
				ethCfmReceivingInvalidCcms(12824),--ETH_CFM_UNEXPERI
				ethCfmLossOfContinuity(12825),--ETH_CFM_LOC   
				ethCfmRemoteDefectIndication(12826),--ETH_CFM_RDI
				ethCfmDiscoveryFail(12827),--ETH_EFM_DF
				ethCfmRemoteFailureDetection(12828),--ETH_EFM_REMFAULT
				ethCfmRemoteLinkEvent(12829),--ETH_EFM_EVENT  
				ethCfmLoopback(12830),--ETH_EFM_LOOPBACK
				ethApsTypeMismatch(12831),--ETH_APS_TYPE_MISMATCH  
				ethApsPathMismatch(12832),--ETH_APS_PATH_MISMATCH 
				ethApsSwitchFail(12833),--ETH_APS_SWITCH_FAIL
				ethApsLost(12834),--ETH_APS_LOST
				arpTableFull(12835),--ARP_TABLE_FULL ARP entry used up alarm  
				lacpLagMemberInvalid(12836),--LAG_MEMBER_DOWN,LACP LAG member invalid alarm 
				lacpLagInvalid(12837),--LAG_DOWN,LACP LAG invalid alarm
				imaGroupLocalEdgeFail(12838),--IMA_GROUP_LE_DOWN
				imaGroupRemoteEdgeFail(12839),--IMA_GROUP_RE_DOWN
				pumpMismatch(12840),--PUMP_MIS_MATCH 
				sccSyncDisabled(12841),--SCC_SYNC_DISABLED
				mutLossOfTransmittedOpticalPower(12842),--MUT_TLOS
				lossOfOscInterfaceInputOpticalPower(12843),--OSC_LOS
				serviceNotOnOriginalRoute(12844),--CP_SER_NOT_OR
				alcCommunicationFail(12845),--ALC_COMM_FAIL 
				apeCommunicationFail(12846),--APE_COMM_FAIL
				apeBdNotCreate(12847),--APE_BD_UNCREATE
				ipaCommunicationFail(12848),--IPA_COMM_FAIL
				ipaRamaParaError(12849),--IPA_RAMANPARA_ERR  
				lineBoardLowOrderPathLoopbackAlarm(12850),--LP_LOOP   
				boardTypeConflict(12851),--BOARD_TYPE_CONFLICT
				pwConnectionInterrupted(12852),--PW_DOWN
				pwLostPacketsOverTheThreshold(12853),--PW_DROPPKT_EXC  
				pwTrafficOverTheThreshold(12854),--PW_EXC_TRAFFIC    
				tdcWaveLengthMismatch(12855),--TDC_WAVELEN_MISMATCH
				timeSlotConfigurationMismatch(12856),--TS_CFG_MISMATCH   
				startupFailureOfTheAsonClock(12857),--ITG_CLOCK_FAIL  
				inputPowerWarning(12858),--IN_PWR_WARNING
				theSynchronizationDataPortCanNotBeUsed(12859),--F1PORT_FAILED
				theCapacityExceedsTheLimitationSpecifiedByTheLicense(12860),--LCS_LIMITED
				lossOfLicenseFile(12861),--LICENSE_LOST
				lossOfXpicSignal(12862),--XPIC_LOS
				openCircuitOfIfCable(12863),--IF_CABLE_OPEN
				theIfModeIsNotSupported(12864),--IF_MODE_UNSUPPORTED
				protectionSwitchingIndication(12865),--NP1_SW_INDI
				automaticProtectionSwitchingFailureIndication(12866),--NP1_SW_FAIL
				apsProtocolManuallyStopped(12867),--NP1_MANUAL_STOP
				portModuleTypeMismatch(12868),--MOD_TYPE_MISMATCH
				microwaveProtectionSwitchingAlarm(12869),--RPS_INDI
				microwaveLinkExcessiveErrors(12870),--MW_BER_EXC
				microwaveLinkSignalDegraded(12871),--MW_BER_SD
				patchInconsistencyAfterTheSccBoardIsReplaced(12872),--PATCH_CHGSCC_NOTMATCH
				repeaterCriticalAlarm(12873),--REPEATER_CRITICAL
				repeaterMajorAlarm(12874),--REPEATER_MAJOR
				repeaterMinorAlarm(12875),--REPEATER_MINOR
				pumpFailureAlarm(12876),--PUMP_FALL
				probePowerAndLoadingPowerMismatch(12877),--PWR_MISMATCH
				apdTemperatureOverUpperThreshold(12878),--APD_TEM_HIGH
				apdTemperatureBelowLowerThreshold(12879),--APD_TEM_LOW
				apdCoolingCurrentOverThreshold(12880),--APD_COOL_ALM
				powerLockingFailure(12881),--OAU_LOCPWR_FAIL
				probeInputPowerTooHigh(12882),--PROB_INPWR_HIGH
				probeInputPowerTooLow(12883),--PROB_INPWR_LOW
				alarmStorm(12884),--STORM_CUR_QUENUM_OVER
				cpwOspfControlLinkDown(12885),--CPW_OSPF_CL_DOWN
				cpwOspfNeighborAuthenticationError(12886),--CPW_OSPF_AUTH_ERR
				cpwOspfNeighborDown(12887),--CPW_OSPF_NB_DOWN
				cpwRsvpNeighborAuthenticationError(12888),--CPW_RSVP_AUTH_ERR
				cpwRsvpNeighborDown(12889),--CPW_RSVP_NB_DOWN
				cpwControlChannelDown(12890),--CPW_CC_DOWN
				cpwNodeIdConflict(12891),--CPW_NODE_ID_CONFLICT
				cpwNodeIdError(12892),--CPW_NODE_ID_ERR
				cpwLspSignalingException(12893),--CPW_LSP_SIG_EXCEPT
				cpwOchServiceInterrupted(12894),--CPW_OCH_SER_INT
				cpwOdu2ServiceInterrupted(12895),--CPW_ODU2_SER_INT
				cpwOdu1ServiceInterrupted(12896),--CPW_ODU1_SER_INT
				cpwClientServiceInterrupted(12897),--CPW_CLNT_SER_INT
				cpwOchServiceSlaDegraded(12898),--CPW_OCH_SER_SLADEG
				cpwOdu2ServiceSlaDegraded(12899),--CPW_ODU2_SER_SLADEG
				cpwOdu1ServiceSlaDegraded(12900),--CPW_ODU1_SER_SLADEG     
				cpwClientServiceSlaDegraded(12901),--CPW_CLNT_SER_SLADEG
				cpwOchAssociatedServiceSynchronizationFailure(12902),--CPW_OCH_SER_SYNFAIL
				cpwOdu2AssociatedServiceSynchronizationFailure(12903),--CPW_ODU2_SER_SYNFAIL
				cpwOdu1AssociatedServiceSynchronizationFailure(12904),--CPW_ODU1_SER_SYNFAIL
				cpwClientAssociatedServiceSynchronizationFailure(12905),--CPW_CLNT_SER_SYNFAIL
				cpwOchServiceNotOnOriginalRoute(12906),--CPW_OCH_SER_NOTOR  
				cpwOdu2ServiceNotOnOriginalRoute(12907),--CPW_ODU2_SER_NOTOR
				cpwOdu1ServiceNotOnOriginalRoute(12908),--CPW_ODU1_SER_NOTOR
				cpwClientServiceNotOnOriginalRoute(12909),--CPW_CLNT_SER_NOTOR 
				cpwOchTeLinkDown(12910),--CPW_OCH_TEL_DOWN
				cpwOdu2TeLinkDown(12911),--CPW_ODU2_TEL_DOWN
				cpwOdu1TeLinkDown(12912),--CPW_ODU1_TEL_DOWN
				cpwClinetTeLinkDown(12913),--CPW_CLNT_TEL_DOWN 
				cpwOchTeLinkDegraded(12914),--CPW_OCH_TEL_DEG
				cpwOdu2TeLinkDegraded(12915),--CPW_ODU2_TEL_DEG
				cpwOdu1TeLinkDegraded(12916),--CPW_ODU1_TEL_DEG
				cpwClientTeLinkDegraded(12917),--CPW_CLNT_TEL_DEG
				cpwOchTeLinkPathStateMismatch(12918),--CPW_OCH_TEL_PATHMIS
				cpwOdu2TeLinkPathStateMismatch(12919),--CPW_ODU2_TEL_PATHMIS
				cpwOdu1TeLinkPathStateMismatch(12920),--CPW_ODU1_TEL_PATHMIS
				cpwClientTeLinkPathStateMismatch(12921),--CPW_CLNT_TEL_PATHMIS
				cpwOdukSpringConfigurationMismatchonOdu2TeLink(12922),--CPW_ODU2_TEL_ODURMIS
				cpwOdukSpringConfigurationMismatchonOdu1TeLink(12923),--CPW_ODU1_TEL_ODURMIS
				cpwAsonServiceCrossConnectionException(12924),--CPW_SER_XC_EXCEPT
				imaE1DelayAlarm(12925),--IMAE1_DELAY
				lanLossOfCarrierSignal(12926),--LAN_LOC
				bfdStateDown(12927),--BFD_DOWN
				linkDownAutomaticLinkDownOfEthernetPort(12928),--ETH_AUTO_LINK_DOWN
				nullSendingEnable(12929),--NULL_SEND
				dropEventsOver(63489),
				dropEventsUnder(63490),
				inBadOctsOver(63491),
				inBadOctsUnder(63492),
				outBadOctsOver(63493),
				outBadOctsUnder(63494),
				collisionsOver(63495),
				collisionsUnder(63496),
				alignmentErrorsOver(63497),
				alignmentErrorsUnder(63498),
				fcsErrorsOver(63499),
				fcsErrorsUnder(63500),
				lateCollisionsOver(63501),
				lateCollisionsUnder(63502),
				excessiveCollisionsOver(63503),
				excessiveCollisionsUnder(63504),
				deferredTransmissionsOver(63505),
				deferredTransmissionsUnder(63506),
				carrierSenseErrorsOver(63507),
				carrierSenseErrorsUnder(63508),
				laserShut(63509),
				rprAlmHostFifoOverflow(63510),
				rprAlmHostParityError(63511),
				rprAlmHostTxError(63512),
				rprAlmHostRuntPack(63513),
				rprAlmHostGiantPack(63514),
				rprAlmHostEmptyPack(63515),
				rprAlmHostProtocolError(63516),
				rprAlmFramerParityEerror(63517),
				rprAlmFramerRxError(63518),
				rprAlmFramerProtocolError(63519),
				rprAlmFramerRuntPack(63520),
				rprAlmFramerCrcError(63521),
				rprAlmFramerParityError(63522),
				rprAlmMateTransError(63523),
				rprAlmMateOosError(63524),
				rprAlmMateOverflowError(63525),
				rprAlmMateShortError(63526),
				rprAlmRppSaRefuse(63527),
				rprAlmRppTtlZero(63528),
				rprAlmRppRuntUseagePack(63529),
				rprAlmRppRidError(63530),
				rprAlmRppTopoError(63531),
				rprAlmRppWpsError(63532),
				rprAlmTbDropped(63533),
				rprAlmTbHighOverflow(63534),
				rprAlmTbLowOverflow(63535),
				rprAlmWpsProctect(63536),
				hardNonSupport(63537),
				vcDelayTooLong(63538),
				beffecSD(63540),
				tpsAlarm(63541),
				dslCpeFailure(63542),
				dslSingalNoiseRationOver(63543),
				dslLoopPathAttenuationOver(63544),
				dslErrorSecondsOver(63545),
				dslSevereErrorSecondsOver(63546),
				dslUnuseAccessSecondsOver(63547),
				dslCrcErrorTimeOver(63548),
				dslLoswTimeOver(63549),
				ddnPortLoopAlarm(63550),
				ddnPortSignalLossAlarm(63551),
				crc4CheckErrorsOver(63552),
				ddnCrc4CheckErrorsOver(63553),
				lossOfFrameAlignment(63554),
				ddnFramedE1LFA(63555),
				framedE1RemoteFrameAlignment(63556),
				ddnFramedE1LMFA(63557),
				framedE1LossOfMulitframeAlignment(63558),
				pumpLifeAlarm(63559),
				pumpInvalidAlarm(63560),
				linkStatus(63561),
				framedE1LMFA(63562),
				framedE1RemoteMulitframeAlignment(63563),
				framedE1RMFA(63564),
				timeSlot16AIS(63565),
				ddnTs16AIS(63566),
				ddnPortAIS(63567),
				requestToSend(63568),
				dataTerminalReady(63569),
				dataSetReady(63570),
				clearToSend(63571),
				digitalCarriorDetector(63572),
				protocolMM(63573),
				multiPathLoop(63574),
				fcsERR(63575),
				lossOfE1ClockLIUtoMapper(63576),
				b3EexVC3(63577),
				b3ExcVC4(63578),
				b3sdVC3(63579),
				b3SdVC4(63580),
				illMFIvc12(63584),
				illMFIvc3(63585),
				illMfiVC4(63586),
				illSQvc12(63587),
				illSQvc3(63588),
				illSqVC4(63589),
				lpRDIvc12(63590),
				lpRDIvc3(63591),
				lpREIvc12(63592),
				lpREIvc3(63593),
				lpSLMvc12(63594),
				lpSLMvc3(63595),
				lpTIMvc12(63596),
				lpTIMvc3(63597),
				lpUNEQvc12(63598),
				lpUNEQvc3(63599),
				tuAISvc12(63600),
				tuAISvc3(63601),
				tuLOPvc12(63602),
				tuLOPvc3(63603),
				remoteSingalUnequipEx(63604),
				remoteSingalDegradeAlarmIndicationEx(63605),
				lcasBandDecreasedAlarm(63606),
				backupPowerNeed(63607),
				imaFgStartup(63608),
				imaNgCfgAbort(63609),
				imaFgCfgAbort(63610),
				imaNgInsffcntLinks(63611),
				imaFgLinks(63612),
				imaFgBlocked(63613),
				imaLostOfFrame(63614),
				imaLinkOutofDelaySynchronization(63615),
				imaRemoteEndFailureIndication(63616),
				imaRemoteEndTransmitFailure(63617),
				imaRemoteEndReceiveFailure(63618),
				imaLinkLCD(63619),
				e1LOFA(63620),
				e1LMFA(63621),
				e1RAI(63622),
				e1AIS(63623),
				clockAbnormal(63624),
				neIdConflict(63625),
				eccBdtypeMismatch(63626),
				sncpCondi(63627),
				orderwirePhoneNotHungUp(63628),
				portModuleOffline(63629),
				noDataReceived(63630),
				noDataTransmited(63631),
				ethernetPortReceiverLossOfData(63633),
				ethernetPortTransmitterLossOfData(63634),
				thunderAlarm(63635),
				pduIsOffline(63636),
				someOfPowerSuppliesHasBeenTurnOff(63637),
				gfpLossOfFrameDelineation(63638),
				gfpLossOfClientSignal(63639),
				gfpLossOfClientCharacterSynchronization(63640),
				passThroughReport(63641),
				vpgMmEx(63642),
				vcgMmEx(63643),
				laserModError(63644),
				slaveBoardWorking(63645),
				lcasFailureOfProtocol(63646),
				lcasPlct(63647),
				lacsTlct(63648),
				lcasPlcr(63649),
				lacsTlcr(63650),
				lacsFopt(63651),
				lacsFopr(63652), 
				portLoopBackAlarm(63653),--PORT_LPBK 
				esnFailed(63654),--ESN_FAILED
				esnInvalid(63655),--ESN_INVALID
				lptFunctionFailure(63656),--LPT_INEFFECT
				gfpUserPayloadMismatch(63657),--GFP_UPM
				gfpExtensionHeaderMismatch(63658),--GFP_EXM                
				portLoopbackIp(63659),--PORT_LPBK_IP
				xcsInconsistent(63660),--XCS_INCONSIST
				e1ldaVctrunkBandwidthLost(63661),--E1LDA_BAND_LOST
				e1ldaVctrunkBloked(63662),--E1LDA_VCTRUNK_BLOCKED
				protectConnectionError(12974),--PROT_CONN_ERR
				receiveSignalLevelFadingMarginInsufficient(12989),--RADIO_FADING_MARGIN_INSUFF
				receiveSignalLevelUnderThreshold(13069),--RADIO_RSL_BEYONDTH
				adaptiveModulationDownShift(13050),--AM_DOWNSHIFT
				mwCfgMismatch(13183),--MW_CFG_MISMATCH
				pgPrtDegraded(13382),--PG_PRT_DEGRADED
				pgLinkFail(13383) --PG_LINK_FAIL
				
				}
	
--
-- Node definitions
--
	
	
	END
--
