--
-- File Name : A10-AX-TRAPS-V1.txt
--
-- Copyright(C) 2005-2011, A10 Networks Inc. All rights reserved.
-- Software for all A10 products contain trade secrets and confidential
-- information of A10 Networks and its subsidiaries and may not be disclosed,
-- copied, reproduced or distributed to anyone outside of A10 Networks
-- without prior written consent of A10 Networks, Inc.
--
-- Description:     This is the A10 AX SNMP Trap v1 file.
--
-- History:
--
--
--

A10-AX-TRAPS DEFINITIONS ::= BEGIN
--================================================================
-- A10-AX-TRAPS 
--	Management MIB for AX SNMP v1 traps
--================================================================
  IMPORTS

    DisplayString, PhysAddress, DateAndTime
      FROM SNMPv2-TC

	InetAddressType
	  FROM INET-ADDRESS-MIB

    axNotification, axLogging
      FROM A10-AX-MIB

    OBJECT-TYPE, Counter32, Integer32, Unsigned32, OBJECT-IDENTITY
      FROM SNMPv2-SMI;

--================================================================
-- axNotification 
--================================================================

    axNotificationObjects        OBJECT IDENTIFIER ::= { axNotification 1 }
    axNotifications              OBJECT IDENTIFIER ::= { axNotification 2 }

--================================================================
-- axNotificationObjects 
--================================================================

    axSystemNotifications        OBJECT IDENTIFIER ::= { axNotifications 1 }
    axAppNotifications           OBJECT IDENTIFIER ::= { axNotifications 2 }
    axNetworkNotifications       OBJECT IDENTIFIER ::= { axNotifications 3 }
    axGslbNotifications          OBJECT IDENTIFIER ::= { axNotifications 5 }
    axSlbNotifications           OBJECT IDENTIFIER ::= { axNotifications 6 }

--================================================================
-- axNotifications
--================================================================

axNotificationMsg OBJECT-TYPE
        SYNTAX        DisplayString 
        MAX-ACCESS    read-only
        STATUS        current
        DESCRIPTION   "The information about the related notification."
        ::= { axNotificationObjects 1 }

axNotificationSLBServer OBJECT-TYPE
        SYNTAX        DisplayString 
        MAX-ACCESS    read-only
        STATUS        current
        DESCRIPTION   "The address or host name of the server."
        ::= { axNotificationObjects 2 }

axNotificationSLBPort OBJECT-TYPE
        SYNTAX        INTEGER 
        MAX-ACCESS    read-only
        STATUS        current
        DESCRIPTION   "The service port."
        ::= { axNotificationObjects 3 }

axNotificationSLBCurConns OBJECT-TYPE
        SYNTAX        Counter32 
        MAX-ACCESS    read-only
        STATUS        current
        DESCRIPTION   "The current total of connections."
        ::= { axNotificationObjects 4 }

axNotificationVirtualServer OBJECT-TYPE
        SYNTAX        DisplayString 
        MAX-ACCESS    read-only
        STATUS        current
        DESCRIPTION   "The address or host name of the virtual server."
        ::= { axNotificationObjects 5 }

axNotificationVirtualServerPort OBJECT-TYPE
        SYNTAX        INTEGER 
        MAX-ACCESS    read-only
        STATUS        current
        DESCRIPTION   "The virtual server port."
        ::= { axNotificationObjects 6 }

axNotificationVirtualServerPortType OBJECT-TYPE
        SYNTAX INTEGER {
		firewall(1),
		tcp(2),
		udp(3),
		rtsp(8),
		ftp(9),
		mms(10),
		fastHTTP(12),
		http(14),
		https(15),
		sslProxy(16),
		smtp(17),
		sip(11),
		sips(19), 
		sip-TCP(18), 
		others(5)
	}
        MAX-ACCESS    read-only
        STATUS        current
        DESCRIPTION   "The virtual server port type."
        ::= { axNotificationObjects 7 }

axNotificationDroppedPackets OBJECT-TYPE
        SYNTAX        INTEGER 
        MAX-ACCESS    read-only
        STATUS        current
        DESCRIPTION   "The number of dropped packets when the event happened."
        ::= { axNotificationObjects 8 }

axNotificationConfiguredThreshold OBJECT-TYPE
        SYNTAX        INTEGER 
        MAX-ACCESS    read-only
        STATUS        current
        DESCRIPTION   "The configured threshold value."
        ::= { axNotificationObjects 9 }

axNotificationCurrentUsage OBJECT-TYPE
        SYNTAX        INTEGER 
        MAX-ACCESS    read-only
        STATUS        current
        DESCRIPTION   "The current usage value."
        ::= { axNotificationObjects 10 }

axNotificationConnLimit OBJECT-TYPE
        SYNTAX        INTEGER 
        MAX-ACCESS    read-only
        STATUS        current
        DESCRIPTION   "The conn-limit."
        ::= { axNotificationObjects 11 }

axNotificationTrunkID OBJECT-TYPE
        SYNTAX        INTEGER 
        MAX-ACCESS    read-only
        STATUS        current
        DESCRIPTION   "The trunk ID"
        ::= { axNotificationObjects 12 }

axNotificationPortThreshold OBJECT-TYPE
        SYNTAX        INTEGER 
        MAX-ACCESS    read-only
        STATUS        current
        DESCRIPTION   "The port threshold"
        ::= { axNotificationObjects 13 }

axNotificationCurrentUpPorts OBJECT-TYPE
        SYNTAX        INTEGER 
        MAX-ACCESS    read-only
        STATUS        current
        DESCRIPTION   "The current up ports"
        ::= { axNotificationObjects 14 }

axNotificationFanName OBJECT-TYPE
        SYNTAX        DisplayString 
        MAX-ACCESS    read-only
        STATUS        current
        DESCRIPTION   "The system fan name."
        ::= { axNotificationObjects 15 }

axNotificationPowerSupplyName OBJECT-TYPE
        SYNTAX        DisplayString 
        MAX-ACCESS    read-only
        STATUS        current
        DESCRIPTION   "The system power supply name."
        ::= { axNotificationObjects 16 }

axNotificationHAGroup OBJECT-TYPE
        SYNTAX        INTEGER 
        MAX-ACCESS    read-only
        STATUS        current
        DESCRIPTION   "The HA group ID."
        ::= { axNotificationObjects 17 }

axNotificationSLBServiceGroupName OBJECT-TYPE
        SYNTAX        DisplayString 
        MAX-ACCESS    read-only
        STATUS        current
        DESCRIPTION   "The service group name."
        ::= { axNotificationObjects 18 }

axNotificationPartitionId OBJECT-TYPE
        SYNTAX        INTEGER 
        MAX-ACCESS    read-only
        STATUS        current
        DESCRIPTION   "The application partition identifier."
        ::= { axNotificationObjects 19 }

axNotificationVrid OBJECT-TYPE
        SYNTAX        INTEGER 
        MAX-ACCESS    read-only
        STATUS        current
        DESCRIPTION   "The VRRP identifier."
        ::= { axNotificationObjects 20 }

axNotificationPartitionName OBJECT-TYPE
        SYNTAX        DisplayString
        MAX-ACCESS    read-only
        STATUS        current
        DESCRIPTION   "The application partition name."
        ::= { axNotificationObjects 21 }

axNotificationGslbSiteName OBJECT-TYPE
        SYNTAX        DisplayString
        MAX-ACCESS    read-only
        STATUS        current
        DESCRIPTION   "The GSLB site name."
        ::= { axNotificationObjects 22 }

axNotificationGslbSiteSlbDeviceName OBJECT-TYPE
        SYNTAX        DisplayString
        MAX-ACCESS    read-only
        STATUS        current
        DESCRIPTION   "The GSLB device name inside a site."
        ::= { axNotificationObjects 23 }

axNotificationGslbSiteIpServerAddr OBJECT-TYPE
        SYNTAX        DisplayString
        MAX-ACCESS    read-only
        STATUS        current
        DESCRIPTION   "The GSLB IP server address."
        ::= { axNotificationObjects 24 }

axNotificationGslbServiceIpName OBJECT-TYPE
        SYNTAX        DisplayString
        MAX-ACCESS    read-only
        STATUS        current
        DESCRIPTION   "The GSLB service IP name."
        ::= { axNotificationObjects 25 }

axNotificationGslbServiceIpAddr OBJECT-TYPE
        SYNTAX        DisplayString
        MAX-ACCESS    read-only
        STATUS        current
        DESCRIPTION   "The GSLB service IP name."
        ::= { axNotificationObjects 26 }

axNotificationGslbServiceIpPortType OBJECT-TYPE
        SYNTAX        DisplayString
        MAX-ACCESS    read-only
        STATUS        current
        DESCRIPTION   "The GSLB service IP port type."
        ::= { axNotificationObjects 27 }

axNotificationGslbZoneName OBJECT-TYPE
        SYNTAX        DisplayString
        MAX-ACCESS    read-only
        STATUS        current
        DESCRIPTION   "The GSLB zone name."
        ::= { axNotificationObjects 28 }

axNotificationGslbZoneServiceProto OBJECT-TYPE
        SYNTAX        DisplayString
        MAX-ACCESS    read-only
        STATUS        current
        DESCRIPTION   "The GSLB zone service protocol name."
        ::= { axNotificationObjects 29 }

axNotificationGslbZoneServiceName OBJECT-TYPE
        SYNTAX        DisplayString
        MAX-ACCESS    read-only
        STATUS        current
        DESCRIPTION   "The GSLB zone service name."
        ::= { axNotificationObjects 30 }

axNotificationGslbGroupName OBJECT-TYPE
        SYNTAX        DisplayString
        MAX-ACCESS    read-only
        STATUS        current
        DESCRIPTION   "The GSLB group name."
        ::= { axNotificationObjects 31 }

axNotificationGslbGroupEntity OBJECT-TYPE
        SYNTAX        DisplayString
        MAX-ACCESS    read-only
        STATUS        current
        DESCRIPTION   "The GSLB group entity (either group member or group master) IP address or local."
        ::= { axNotificationObjects 32 }


axNotificationLicensedModuleName OBJECT-TYPE
        SYNTAX        DisplayString
        MAX-ACCESS    read-only
        STATUS        current
        DESCRIPTION   "The licensed module name."
        ::= { axNotificationObjects 33 }

axNotificationShutdownReason OBJECT-TYPE
	SYNTAX INTEGER {
		tooHighSystemTemperature(1),
		insufficientPowerSupply(2)
	}
        MAX-ACCESS    read-only
        STATUS        current
        DESCRIPTION   "The reason for the system shut-down."
        ::= { axNotificationObjects 34 }

axNotificationIpAddressType OBJECT-TYPE
        SYNTAX          InetAddressType
        MAX-ACCESS    read-only
        STATUS        current
        DESCRIPTION   "The type of IP address."
        ::= { axNotificationObjects 35 }

axNotificationLicenseDisableDuration OBJECT-TYPE
        SYNTAX        Unsigned32
        MAX-ACCESS    read-only
        STATUS        current
        DESCRIPTION   "The license has been disabled for given seconds."
        ::= { axNotificationObjects 36 }

axNotificationSslServerCertificateErrCounter OBJECT-TYPE
        SYNTAX        Unsigned32
        MAX-ACCESS    read-only
        STATUS        current
        DESCRIPTION   "The counter for the SSL server certificate errors."
        ::= { axNotificationObjects 37 }

axNotificationServerSelectionFailureReason OBJECT-TYPE
        SYNTAX        DisplayString 
        MAX-ACCESS    read-only
        STATUS        current
        DESCRIPTION   "The reason of server selection failure."
        ::= { axNotificationObjects 38 }

axNotificationConnectionTypeName OBJECT-TYPE
        SYNTAX        DisplayString 
        MAX-ACCESS    read-only
        STATUS        current
        DESCRIPTION   "The name of the type."
        ::= { axNotificationObjects 39 }

axNotificationSlbObjectChange OBJECT-TYPE
        SYNTAX INTEGER {
		    create(1),
		    delete(2)
        }
        MAX-ACCESS  read-only
        STATUS      current
        DESCRIPTION "The type of create/delete."
        ::= { axNotificationObjects 40 }

axNotificationCertificateName OBJECT-TYPE
        SYNTAX      DisplayString
        MAX-ACCESS  read-only
        STATUS      current
        DESCRIPTION "The name of the certificate."
        ::= { axNotificationObjects 41 }

axNotificationDateTime OBJECT-TYPE
        SYNTAX      DateAndTime
        MAX-ACCESS  read-only
        STATUS      current
        DESCRIPTION "Time the event is going to occuer, expired."
        ::= { axNotificationObjects 42 }

axNotificationSLBServerPortType OBJECT-TYPE
        SYNTAX INTEGER {
		    tcp(2),
		    udp(3)
        }
        MAX-ACCESS  read-only
        STATUS      current
        DESCRIPTION "The server port type of create/delete."
        ::= { axNotificationObjects 43 }

axNotificationPartitionResourceName OBJECT-TYPE
        SYNTAX      DisplayString
        MAX-ACCESS  read-only
        STATUS      current
        DESCRIPTION "The partition resource name."
        ::= { axNotificationObjects 44 }

axNotificationPartitionResourceUsageLevel OBJECT-TYPE
        SYNTAX INTEGER {
                   below(1),
                   above(2)
        }
        MAX-ACCESS    read-only
        STATUS        current
        DESCRIPTION   "The partition resource usage level."
        ::= { axNotificationObjects 45 }

axNotificationTacacsServerHost OBJECT-TYPE
        SYNTAX        DisplayString
        MAX-ACCESS    read-only
        STATUS        current
        DESCRIPTION   "The TACACS server host, it could be host name, ipv4 or ipv6."
        ::= { axNotificationObjects 46 }

axNotificationUpDown OBJECT-TYPE
    SYNTAX INTEGER {
        up(1),
        down(2)
    }
    MAX-ACCESS    read-only
    STATUS        current
    DESCRIPTION   "The type of up/down."
    ::= { axNotificationObjects 47 }

axNotificationTrueFalse OBJECT-TYPE
    SYNTAX INTEGER {
        false(0),
        true(1)
    }
    MAX-ACCESS    read-only
    STATUS        current
    DESCRIPTION   "The effective of the notification."
    ::= { axNotificationObjects 48 }

axNotificationOldVcsState OBJECT-TYPE
    SYNTAX INTEGER {
		vmasterCandidate(0),
		activatingSlave(1),
		vBlade(2),
		vMaster(3),
		vMasterTakeover(4)
    }
    MAX-ACCESS    read-only
    STATUS        current
    DESCRIPTION   "The old state of VCS."
    ::= { axNotificationObjects 49 }

axNotificationNewVcsState OBJECT-TYPE
    SYNTAX INTEGER {
		vmasterCandidate(0),
		activatingSlave(1),
		vBlade(2),
		vMaster(3),
		vMasterTakeover(4)
    }
    MAX-ACCESS    read-only
    STATUS        current
    DESCRIPTION   "The new state of VCS."
    ::= { axNotificationObjects 50 }

--================================================================
-- axSystemNotifications
--================================================================

axSystemStart        TRAP-TYPE
	ENTERPRISE axSystemNotifications
	DESCRIPTION  "Notify that the system has started running."
	::= 1

axSystemShutdown     TRAP-TYPE
	ENTERPRISE axSystemNotifications
	DESCRIPTION  "Notify that the system is in the process of being shut down."
	::= 2

axSystemTempHigh      TRAP-TYPE
	ENTERPRISE axSystemNotifications
	VARIABLES     { 
			axNotificationConfiguredThreshold,
			axNotificationCurrentUsage
		      }
	DESCRIPTION  "The system tempature is high."
	::= 3

axPrimaryHardDiskFailure      TRAP-TYPE
	ENTERPRISE axSystemNotifications
	DESCRIPTION   "The primary hard disk is failed."
	::= 11

axSecondaryHardDiskFailure      TRAP-TYPE
	ENTERPRISE axSystemNotifications
	DESCRIPTION   "The secondary hard disk is failed."
	::= 12

axHardDiskUsageHigh      TRAP-TYPE
	ENTERPRISE axSystemNotifications
	DESCRIPTION   "The hard disk usage is high."
	::= 13

axMemoryUsageHigh      TRAP-TYPE
	ENTERPRISE axSystemNotifications
	DESCRIPTION  "The memory usage is high."
	::= 14

axSystemRestart      TRAP-TYPE
	ENTERPRISE axSystemNotifications
	DESCRIPTION  "Notify that the agent has been restarted."
	::= 15

axSystemDropPacketEvent   TRAP-TYPE
	ENTERPRISE axSystemNotifications
	VARIABLES     { 
			axNotificationDroppedPackets
		      }
	DESCRIPTION   "The AX experiences the packet dropped of axNotificationDroppedPackets."
	::= 16

axSystemRelieveDropPacketEvent   TRAP-TYPE
	ENTERPRISE axSystemNotifications
	VARIABLES     { 
			axNotificationDroppedPackets
		      }
	DESCRIPTION   "The AX recovers from the packet dropped before."
	::= 17

axSystemControlCpuHigh   TRAP-TYPE
	ENTERPRISE axSystemNotifications
	VARIABLES     { 
			axNotificationConfiguredThreshold,
			axNotificationCurrentUsage
		      }
	DESCRIPTION   "The AX control CPU usage is high."
	::= 18

axSystemDataCpuHigh   TRAP-TYPE
	ENTERPRISE axSystemNotifications
	VARIABLES     { 
			axNotificationConfiguredThreshold,
			axNotificationCurrentUsage
		      }
	DESCRIPTION   "The AX data CPU usage is high."
	::= 19

axSystemFanFailure   TRAP-TYPE
	ENTERPRISE axSystemNotifications
	VARIABLES     { 
			axNotificationFanName
		      }
	DESCRIPTION   "The system fan is failed."
	::= 20

axSystemPowerSupplyFailure   TRAP-TYPE
	ENTERPRISE axSystemNotifications
	VARIABLES     { 
			axNotificationPowerSupplyName
		      }
	DESCRIPTION   "The system power supply is failed."
	::= 21

axSystemLicenseRequired   TRAP-TYPE
	ENTERPRISE axSystemNotifications
	VARIABLES     { 
			axNotificationLicensedModuleName
		      }
	DESCRIPTION   "The system requires the valid license for specific module."
	::= 22

axSystemLicenseLoadSuccessful   TRAP-TYPE
	ENTERPRISE axSystemNotifications
	VARIABLES     { 
			axNotificationLicensedModuleName
		      }
	DESCRIPTION   "The system loads the license for specific module successfully."
	::= 23

axSystemLicenseExpired   TRAP-TYPE
	ENTERPRISE axSystemNotifications
	VARIABLES     { 
			axNotificationLicensedModuleName
		      }
	DESCRIPTION   "The module license is expired."
	::= 24

axSystemShutdownForReason   TRAP-TYPE
	ENTERPRISE axSystemNotifications
	VARIABLES     { 
			axNotificationShutdownReason
		      }
	DESCRIPTION   "The AX system is mandatorily shut down."
	::= 25

axFileSystemBecomeReadOnly  TRAP-TYPE
	ENTERPRISE axSystemNotifications
	DESCRIPTION   "The file system is becoming the read-only."
	::= 26

axSystemLicensedModuleDisabledForDuration   TRAP-TYPE
        ENTERPRISE axSystemNotifications
        VARIABLES     {
                        axNotificationLicensedModuleName,
                        axNotificationLicenseDisableDuration
                      }
        DESCRIPTION   "The system disables the specific licensed module for the past duration seconds."
        ::= 27

axSystemControlCpuBecomeNormal   TRAP-TYPE
	ENTERPRISE axSystemNotifications
	VARIABLES     { 
			axNotificationConfiguredThreshold,
			axNotificationCurrentUsage
		      }
	DESCRIPTION   "The AX control CPU usage is back to normal."
	::= 28 

axSystemDataCpuBecomeNormal   TRAP-TYPE
	ENTERPRISE axSystemNotifications
	VARIABLES     { 
			axNotificationConfiguredThreshold,
			axNotificationCurrentUsage
		      }
	DESCRIPTION   "The AX data CPU usage is back to normal."
	::= 29

axSystemTempBecomeNormal      TRAP-TYPE
	ENTERPRISE axSystemNotifications
	VARIABLES     { 
			axNotificationConfiguredThreshold,
			axNotificationCurrentUsage
		      }
	DESCRIPTION  "The system tempature is back to normal."
	::= 30

axHardDiskUsageBecomeNormal      TRAP-TYPE
	ENTERPRISE axSystemNotifications
	DESCRIPTION   "The hard disk usage is back to normal."
	::= 31

axMemoryUsageBecomeNormal      TRAP-TYPE
	ENTERPRISE axSystemNotifications
	DESCRIPTION  "The memory usage is back to normal."
	::= 32

axSystemFanRecover   TRAP-TYPE
	ENTERPRISE axSystemNotifications
	VARIABLES     { 
			axNotificationFanName
		      }
	DESCRIPTION   "The system fan is back to normal."
	::= 33

axSystemPowerSupplyRecover   TRAP-TYPE
	ENTERPRISE axSystemNotifications
	VARIABLES     { 
			axNotificationPowerSupplyName
		      }
	DESCRIPTION   "The system power supply is back to normal."
	::= 34

axSystemConnectionResourceHigh   TRAP-TYPE
	ENTERPRISE axSystemNotifications
	VARIABLES     { 
			axNotificationConnectionTypeName,
            axNotificationConfiguredThreshold,
            axNotificationCurrentUsage
		      }
	DESCRIPTION   "The system connection is high."
	::= 35

axSystemConnectionResourceBecomeNormal   TRAP-TYPE
	ENTERPRISE axSystemNotifications
	VARIABLES     { 
			axNotificationConnectionTypeName,
            axNotificationConfiguredThreshold,
            axNotificationCurrentUsage
		      }
	DESCRIPTION   "The system connection is back to normal."
	::= 36

axSystemSmpResourceHigh   TRAP-TYPE
	ENTERPRISE axSystemNotifications
	VARIABLES     { 
			axNotificationConnectionTypeName,
            axNotificationConfiguredThreshold,
            axNotificationCurrentUsage
		      }
	DESCRIPTION   "The SMP is high."
	::= 37

axSystemSmpResourceBecomeNormal   TRAP-TYPE
	ENTERPRISE axSystemNotifications
	VARIABLES     { 
			axNotificationConnectionTypeName,
            axNotificationConfiguredThreshold,
            axNotificationCurrentUsage
		      }
	DESCRIPTION   "The SMP is back to normal."
	::= 38

axTacacsMonitorServerUpDown   TRAP-TYPE
    ENTERPRISE axSystemNotifications
    VARIABLES     {
            axNotificationMsg,
            axNotificationTacacsServerHost,
            axNotificationUpDown
              }
    DESCRIPTION   "The AX Tacacs Monitor Server is down."
    ::= 39

axHighPrioritySyslog   TRAP-TYPE
    ENTERPRISE axSystemNotifications
    VARIABLES     {
            axNotificationMsg
              }
    DESCRIPTION   "The high severity issue such as hardware failure."
    ::=41


--================================================================
-- axAppNotifications
--================================================================

axHAStandby      TRAP-TYPE
	ENTERPRISE axAppNotifications
	VARIABLES       { axNotificationMsg, axNotificationHAGroup }
	DESCRIPTION   "The system is going into standby mode."
	::= 1

axHAActive      TRAP-TYPE
	ENTERPRISE axAppNotifications
	VARIABLES     { axNotificationMsg, axNotificationHAGroup }
	DESCRIPTION   "The system is going into active mode."
	::= 2

axServiceDown      TRAP-TYPE
	ENTERPRISE axAppNotifications
	VARIABLES     { 
		axNotificationMsg, 
		axNotificationSLBServer, 
		axNotificationSLBPort,
		axNotificationPartitionName
 	}
	DESCRIPTION   "A service is detected DOWN."
	::= 4

axServiceUp      TRAP-TYPE
	ENTERPRISE axAppNotifications
	VARIABLES     { 
		axNotificationMsg, 
		axNotificationSLBServer, 
		axNotificationSLBPort,
		axNotificationPartitionName 
	}
	DESCRIPTION   "A SLB service is up."
	::= 5

axServerDown      TRAP-TYPE
	ENTERPRISE axAppNotifications
	VARIABLES    { 
		axNotificationMsg, 
		axNotificationSLBServer,
		axNotificationPartitionName 
	}
	DESCRIPTION   "A SLB server is down."
	::= 6

axServerUp   TRAP-TYPE
	ENTERPRISE axAppNotifications
	VARIABLES     { 
		axNotificationMsg, 
		axNotificationSLBServer,
		axNotificationPartitionName 
	}
	DESCRIPTION   "A SLB server is up."
	::= 7

axServerConnLimit   TRAP-TYPE
	ENTERPRISE axAppNotifications
	VARIABLES     { 
			axNotificationMsg, 
			axNotificationSLBServer,
			axNotificationSLBCurConns,
			axNotificationPartitionName
    }
	DESCRIPTION   "A SLB server has reached the configured connection limits."
	::= 8

axServerConnResume   TRAP-TYPE
	ENTERPRISE axAppNotifications
	VARIABLES     { 
			axNotificationMsg, 
			axNotificationSLBServer,
			axNotificationSLBCurConns,
			axNotificationPartitionName
    }
	DESCRIPTION   "A SLB server has reached the configured connection-resume value."
	::= 9

axServiceConnLimit   TRAP-TYPE
	ENTERPRISE axAppNotifications
	VARIABLES     { 
			axNotificationMsg, 
			axNotificationSLBServer, 
			axNotificationSLBPort,
			axNotificationSLBCurConns,
			axNotificationPartitionName
    }
	DESCRIPTION   "A SLB service has reached the configured connection limits."
	::= 10

axServiceConnResume   TRAP-TYPE
	ENTERPRISE axAppNotifications
	VARIABLES     { 
			axNotificationMsg, 
			axNotificationSLBServer, 
			axNotificationSLBPort,
			axNotificationSLBCurConns,
			axNotificationPartitionName
    }
	DESCRIPTION   "A SLB service has reached the configured connection-resume value."
	::= 11

axVirtualServerPortDown   TRAP-TYPE
	ENTERPRISE axAppNotifications
	VARIABLES     { 
			axNotificationMsg, 
			axNotificationVirtualServer, 
			axNotificationVirtualServerPort,
			axNotificationVirtualServerPortType,
			axNotificationPartitionName
	}
	DESCRIPTION   "A SLB virtual server port is down."
	::= 12

axVirtualServerPortUp   TRAP-TYPE
	ENTERPRISE axAppNotifications
	VARIABLES     { 
			axNotificationMsg, 
			axNotificationVirtualServer, 
			axNotificationVirtualServerPort,
			axNotificationVirtualServerPortType,
			axNotificationPartitionName
    }
	DESCRIPTION   "A SLB virtual server port is up."
	::= 13

axApplicationBufferReachLimit	TRAP-TYPE
	ENTERPRISE axAppNotifications
	VARIABLES     { 
			axNotificationConfiguredThreshold,
			axNotificationCurrentUsage
		      }
	DESCRIPTION   "The AX SLB application buffer usage execeeded the configured threshold."
	::= 14

axVirtualServerPortReachConnLimit   TRAP-TYPE
	ENTERPRISE axAppNotifications
	VARIABLES     { 
			axNotificationMsg, 
			axNotificationSLBServer, 
			axNotificationSLBPort,
			axNotificationConnLimit,
			axNotificationPartitionName
    }
	DESCRIPTION   "A virtual service port has reached the configured connection limits."
	::= 15

axVirtualServerPortReachConnRateLimit   TRAP-TYPE
	ENTERPRISE axAppNotifications
	VARIABLES     { 
			axNotificationMsg, 
			axNotificationSLBServer, 
			axNotificationSLBPort,
			axNotificationConnLimit,
			axNotificationPartitionName
    }
	DESCRIPTION   "A virtual service port has reached the configured connection rate-limits."
	::= 16

axVirtualServerReachConnLimit   TRAP-TYPE
	ENTERPRISE axAppNotifications
	VARIABLES     { 
			axNotificationMsg, 
			axNotificationSLBServer, 
			axNotificationConnLimit,
			axNotificationPartitionName
    }
	DESCRIPTION   "A virtual server has reached the configured connection limits."
	::= 17

axVirtualServerReachConnRateLimit   TRAP-TYPE
	ENTERPRISE axAppNotifications
	VARIABLES     { 
			axNotificationMsg, 
			axNotificationSLBServer, 
			axNotificationConnLimit,
			axNotificationPartitionName
    }
	DESCRIPTION   "A virtual server has reached the configured connection rate-limits."
	::= 18

axServerConnRateLimit   TRAP-TYPE
	ENTERPRISE axAppNotifications
	VARIABLES     { 
			axNotificationMsg, 
			axNotificationSLBServer,
			axNotificationSLBCurConns,
			axNotificationPartitionName
    }
	DESCRIPTION   "A SLB server has reached the configured conn-rate-limits."
	::= 19

axServiceConnRateLimit   TRAP-TYPE
	ENTERPRISE axAppNotifications
	VARIABLES     { 
			axNotificationMsg, 
			axNotificationSLBServer, 
			axNotificationSLBPort,
			axNotificationSLBCurConns,
			axNotificationPartitionName
    }
	DESCRIPTION   "A SLB service group member has reached the configured conn-rate-limits."
	::= 20

axServiceGroupMemberEnabledForNewConn   TRAP-TYPE
	ENTERPRISE axAppNotifications
	VARIABLES     { 
			axNotificationMsg, 
			axNotificationSLBServer, 
			axNotificationSLBPort,
			axNotificationSLBServiceGroupName,
			axNotificationPartitionName
    }
	DESCRIPTION   "A SLB service group member is enabled to accept the new connection, when the current connections of group members exceed the conn-limit."
	::= 21

axServiceGroupMemberDisabledForNewConn   TRAP-TYPE
	ENTERPRISE axAppNotifications
	VARIABLES     { 
			axNotificationMsg, 
			axNotificationSLBServiceGroupName,
			axNotificationSLBPort,
			axNotificationPartitionName
    }
	DESCRIPTION   "A SLB service group member is disabled, when the current connections of group members are reduced to the conn-resume."
	::= 22


axVrrpActive   TRAP-TYPE
	ENTERPRISE axAppNotifications
	VARIABLES     { 
			axNotificationMsg, 
			axNotificationPartitionName,
			axNotificationVrid
		      }
	DESCRIPTION   "The vrid, axNotificationVrid, in the specific partition becomes the Active state."
	::= 23

axVrrpStandby   TRAP-TYPE
	ENTERPRISE axAppNotifications
	VARIABLES     { 
			axNotificationMsg, 
			axNotificationPartitionName,
			axNotificationVrid
		      }
	DESCRIPTION   "The vrid, axNotificationVrid, in the specific partition becomes the Standby state."
	::= 24

axSslServerCertificateErr   TRAP-TYPE 
   ENTERPRISE axAppNotifications
   VARIABLES   {
                 axNotificationMsg,
                 axNotificationSLBServer,
                 axNotificationSslServerCertificateErrCounter
               }
	DESCRIPTION   "The SSL server certificate error is detected."
	::= 25

axServerSelectionFailure   TRAP-TYPE
	ENTERPRISE axAppNotifications
	VARIABLES     { 
			axNotificationMsg, 
			axNotificationSLBServer, 
			axNotificationSLBPort,
			axNotificationServerSelectionFailureReason,
			axNotificationPartitionName
    }
	DESCRIPTION   "A SLB server has got a server selection failure."
	::= 26

axVirtualServerUp   TRAP-TYPE
	ENTERPRISE axAppNotifications
	VARIABLES     { 
			axNotificationMsg, 
			axNotificationVirtualServer,
			axNotificationPartitionName
    }
	DESCRIPTION   "A SLB virtual server is down."
	::= 27

axVirtualServerDown   TRAP-TYPE
	ENTERPRISE axAppNotifications
	VARIABLES     { 
			axNotificationMsg, 
			axNotificationVirtualServer,
			axNotificationPartitionName
    }
	DESCRIPTION   "A SLB virtual server is down."
	::= 28

axServerDisabled   TRAP-TYPE
	ENTERPRISE axAppNotifications
	VARIABLES     { 
			axNotificationMsg, 
			axNotificationSLBServer, 
			axNotificationTrueFalse,
			axNotificationPartitionName 
	}
	DESCRIPTION   "A SLB server is disabled."
	::= 29 


axServiceGroupUp TRAP-TYPE
	ENTERPRISE axAppNotifications
	VARIABLES     { 
			axNotificationMsg,
   	    	axNotificationSLBServiceGroupName,
            axNotificationSLBServerPortType,
            axNotificationPartitionName
		}
	DESCRIPTION   "A SLB service group is Up."
	::= 30

axServiceGroupDown TRAP-TYPE
	ENTERPRISE axAppNotifications
	VARIABLES     { 
			axNotificationMsg,
   	    	axNotificationSLBServiceGroupName,
            axNotificationSLBServerPortType,
            axNotificationPartitionName
		}
	DESCRIPTION   "A SLB service group is Down."
	::= 31

axServiceGroupMemberUp TRAP-TYPE
	ENTERPRISE axAppNotifications
	VARIABLES     { 
			axNotificationMsg,
   	    	axNotificationSLBServiceGroupName,
			axNotificationSLBServer,
			axNotificationSLBPort,
            axNotificationPartitionName
		}
	DESCRIPTION   "A SLB service group member is up."
	::= 32

axServiceGroupMemberDown TRAP-TYPE
	ENTERPRISE axAppNotifications
	VARIABLES     { 
			axNotificationMsg,
   	    	axNotificationSLBServiceGroupName,
			axNotificationSLBServer,
			axNotificationSLBPort,
            axNotificationPartitionName
		}
	DESCRIPTION   "A SLB service group member is down."
	::= 33

axVcsStateChange TRAP-TYPE
	ENTERPRISE axAppNotifications
	VARIABLES     { 
		axNotificationMsg,
        axNotificationOldVcsState,
        axNotificationNewVcsState
	}
	DESCRIPTION   "A SLB service group member is down."
	::= 34

axGatewayUp   TRAP-TYPE
	ENTERPRISE axAppNotifications
	VARIABLES     { 
		axNotificationMsg, 
		axNotificationSLBServer,
		axNotificationPartitionName 
	}
	DESCRIPTION   "A gateway is up."
	::=35 

axGatewayDown   TRAP-TYPE
	ENTERPRISE axAppNotifications
	VARIABLES     { 
		axNotificationMsg, 
		axNotificationSLBServer,
		axNotificationPartitionName 
	}
	DESCRIPTION   "A gateway is down."
	::=36 

 
--================================================================

--================================================================
-- axNetworkNotifications
--================================================================

axNetworkTrunkPortsThreshold      TRAP-TYPE
	ENTERPRISE axNetworkNotifications
	VARIABLES     { 
			axNotificationTrunkID,
			axNotificationPortThreshold,
			axNotificationCurrentUpPorts
		      }
	DESCRIPTION   "The trunk ports threshold trap."
	::= 1

--==================================================================
-- axSyslog trap
--==================================================================

    axSyslogTrapPrefix OBJECT-IDENTITY
        STATUS          current
        DESCRIPTION     "prefix of A10 logging traps"
        ::=  {  axLogging  100  }

    axSyslogTrap   TRAP-TYPE
 	ENTERPRISE axSyslogTrapPrefix
        VARIABLES       { axSyslogModuleName, axSyslogPriority, axSyslogMsg }
        DESCRIPTION     "the syslog messages sent through snmp trap"
        ::=  1

    axSyslogTrapObjects    OBJECT-IDENTITY
        STATUS          current
        DESCRIPTION     "Objects of AX syslog trap"
        ::=  {  axLogging  101  }

    axSyslogModuleName OBJECT-TYPE
        SYNTAX          DisplayString  ( SIZE ( 0 .. 15  ) )
        MAX-ACCESS      accessible-for-notify
        STATUS          current
        DESCRIPTION     "The module name sent the syslog message."
        ::=  {  axSyslogTrapObjects  1  }

    axSyslogPriority   OBJECT-TYPE
        SYNTAX          Integer32  ( 0 .. 7  )
        MAX-ACCESS      accessible-for-notify
        STATUS          current
        DESCRIPTION     "The syslog message priority."
        ::=  {  axSyslogTrapObjects  2  }

    axSyslogMsg    OBJECT-TYPE
        SYNTAX          OCTET STRING  ( SIZE ( 0 .. 1023  ) )
        MAX-ACCESS      accessible-for-notify
        STATUS          current
        DESCRIPTION     "The syslog message."
        ::=  {  axSyslogTrapObjects  3  }

--================================================================
-- axGslbNotifications
--================================================================

axGslbSiteAdminEnabled   TRAP-TYPE
	ENTERPRISE axGslbNotifications
	VARIABLES       { 
			axNotificationMsg, 
			axNotificationGslbSiteName, 
			axNotificationPartitionName
		      }
	DESCRIPTION   "The GSLB site is administratively enabled."
	::= 1

axGslbSiteAdminDisabled   TRAP-TYPE
	ENTERPRISE axGslbNotifications
	VARIABLES       { 
			axNotificationMsg, 
			axNotificationGslbSiteName, 
			axNotificationPartitionName
		      }
	DESCRIPTION   "The GSLB site is administratively disabled."
	::= 2

axGslbSiteOperationalStateUp   TRAP-TYPE
	ENTERPRISE axGslbNotifications
	VARIABLES       { 
			axNotificationMsg, 
			axNotificationGslbSiteName, 
			axNotificationPartitionName
		      }
	DESCRIPTION   "The GSLB site is operational up."
	::= 3

axGslbSiteOperationalStateDown   TRAP-TYPE
	ENTERPRISE axGslbNotifications
	VARIABLES       { 
			axNotificationMsg, 
			axNotificationGslbSiteName, 
			axNotificationPartitionName
		      }
	DESCRIPTION   "The GSLB site is operational down."
	::= 4

axGslbSiteSlbDeviceStateUp   TRAP-TYPE
	ENTERPRISE axGslbNotifications
	VARIABLES       { 
			axNotificationMsg, 
			axNotificationGslbSiteName, 
			axNotificationGslbSiteSlbDeviceName,
			axNotificationPartitionName
		      }
	DESCRIPTION   "The GSLB site SLB device status is changed to up."
	::= 5

axGslbSiteSlbDeviceStateDown   TRAP-TYPE
	ENTERPRISE axGslbNotifications
	VARIABLES       { 
			axNotificationMsg, 
			axNotificationGslbSiteName, 
			axNotificationGslbSiteSlbDeviceName,
			axNotificationPartitionName
		      }
	DESCRIPTION   "The GSLB site SLB device status is changed to down."
	::= 6

axGslbServiceIpAdminEnabled   TRAP-TYPE
	ENTERPRISE axGslbNotifications
	VARIABLES       { 
			axNotificationMsg, 
			axNotificationGslbServiceIpName, 
			axNotificationGslbServiceIpAddr, 
			axNotificationPartitionName
		      }
	DESCRIPTION   "The GSLB service IP is administratively enabled."
	::= 9

axGslbServiceIpAdminDisabled   TRAP-TYPE
	ENTERPRISE axGslbNotifications
	VARIABLES       { 
			axNotificationMsg, 
			axNotificationGslbServiceIpName, 
			axNotificationGslbServiceIpAddr, 
			axNotificationPartitionName
		      }
	DESCRIPTION   "The GSLB service IP is administratively disabled."
	::= 10

axGslbServiceIpOperationalStateUp   TRAP-TYPE
	ENTERPRISE axGslbNotifications
	VARIABLES       { 
			axNotificationMsg, 
			axNotificationGslbServiceIpName, 
			axNotificationGslbServiceIpAddr, 
			axNotificationPartitionName
		      }
	DESCRIPTION   "The GSLB service IP is operational up."
	::= 11

axGslbServiceIpOperationalStateDown   TRAP-TYPE
	ENTERPRISE axGslbNotifications
	VARIABLES       { 
			axNotificationMsg, 
			axNotificationGslbServiceIpName, 
			axNotificationGslbServiceIpAddr, 
			axNotificationPartitionName
		      }
	DESCRIPTION   "The GSLB service IP is operational down."
	::= 12

axGslbServiceIpPortStateUp   TRAP-TYPE
	ENTERPRISE axGslbNotifications
	VARIABLES       { 
			axNotificationMsg, 
			axNotificationGslbServiceIpName, 
			axNotificationGslbServiceIpAddr, 
			axNotificationGslbServiceIpPortType,
			axNotificationPartitionName
		      }
	DESCRIPTION   "The GSLB service IP port status is changed to up."
	::= 13

axGslbServiceIpPortStateDown   TRAP-TYPE
	ENTERPRISE axGslbNotifications
	VARIABLES       { 
			axNotificationMsg, 
			axNotificationGslbServiceIpName, 
			axNotificationGslbServiceIpAddr, 
			axNotificationGslbServiceIpPortType,
			axNotificationPartitionName
		      }
	DESCRIPTION   "The GSLB service IP port status is changed to down."
	::= 14

axGslbZoneAdminEnabled   TRAP-TYPE
	ENTERPRISE axGslbNotifications
	VARIABLES       { 
			axNotificationMsg, 
			axNotificationGslbZoneName, 
			axNotificationPartitionName
		      }
	DESCRIPTION   "The GSLB zone status is administratively enabled."
	::= 15

axGslbZoneAdminDisabled   TRAP-TYPE
	ENTERPRISE axGslbNotifications
	VARIABLES       { 
			axNotificationMsg, 
			axNotificationGslbZoneName, 
			axNotificationPartitionName
		      }
	DESCRIPTION   "The GSLB zone status is administratively disabled."
	::= 16

axGslbZoneOperationalStateUp   TRAP-TYPE
	ENTERPRISE axGslbNotifications
	VARIABLES       { 
			axNotificationMsg, 
			axNotificationGslbZoneName, 
			axNotificationPartitionName
		      }
	DESCRIPTION   "The GSLB zone is operational up."
	::= 17

axGslbZoneOperationalStateDown   TRAP-TYPE
	ENTERPRISE axGslbNotifications
	VARIABLES       { 
			axNotificationMsg, 
			axNotificationGslbZoneName,
			axNotificationPartitionName
		      }
	DESCRIPTION   "The GSLB zone is operational down."
	::= 18

axGslbZoneServiceAdminEnabled   TRAP-TYPE
	ENTERPRISE axGslbNotifications
	VARIABLES       { 
			axNotificationMsg, 
			axNotificationGslbZoneName, 
			axNotificationGslbZoneServiceProto, 
			axNotificationGslbZoneServiceName, 
			axNotificationPartitionName
		      }
	DESCRIPTION   "The GSLB zone service is administratively enabled."
	::= 19

axGslbZoneServiceAdminDisabled   TRAP-TYPE
	ENTERPRISE axGslbNotifications
	VARIABLES       { 
			axNotificationMsg, 
			axNotificationGslbZoneName, 
			axNotificationGslbZoneServiceProto, 
			axNotificationGslbZoneServiceName, 
			axNotificationPartitionName
		      }
	DESCRIPTION   "The GSLB zone service is administratively disabled."
	::= 20

axGslbZoneServiceOperationalStateUp   TRAP-TYPE
	ENTERPRISE axGslbNotifications
	VARIABLES       { 
			axNotificationMsg, 
			axNotificationGslbZoneName, 
			axNotificationGslbZoneServiceProto, 
			axNotificationGslbZoneServiceName, 
			axNotificationPartitionName
		      }
	DESCRIPTION   "The GSLB zone service is operational up."
	::= 21

axGslbZoneServiceOperationalStateDown   TRAP-TYPE
	ENTERPRISE axGslbNotifications
	VARIABLES       { 
			axNotificationMsg, 
			axNotificationGslbZoneName, 
			axNotificationGslbZoneServiceProto, 
			axNotificationGslbZoneServiceName, 
			axNotificationPartitionName
		      }
	DESCRIPTION   "The GSLB zone service is operational down."
	::= 22

axGslbGroupBecomeMaster   TRAP-TYPE
	ENTERPRISE axGslbNotifications
	VARIABLES       { 
			axNotificationMsg, 
			axNotificationGslbGroupName,
			axNotificationGslbGroupEntity
		      }
	DESCRIPTION   "The GSLB group becomes the Master."
	::= 23

axGslbGroupRemovedMaster   TRAP-TYPE
	ENTERPRISE axGslbNotifications
	VARIABLES       { 
			axNotificationMsg, 
			axNotificationGslbGroupName,
			axNotificationGslbGroupEntity
		      }
	DESCRIPTION   "The GSLB group is removed from the Master."
	::= 24

axGslbGroupMemberJoinMasterGroup   TRAP-TYPE
	ENTERPRISE axGslbNotifications
	VARIABLES       { 
			axNotificationMsg, 
			axNotificationGslbGroupName,
			axNotificationGslbGroupEntity
		      }
	DESCRIPTION   "The GSLB group member is joining a group Master."
	::= 25

axGslbGroupMemberLeaveMasterGroup   TRAP-TYPE
	ENTERPRISE axGslbNotifications
	VARIABLES       { 
			axNotificationMsg, 
			axNotificationGslbGroupName,
			axNotificationGslbGroupEntity
		      }
	DESCRIPTION   "The GSLB group is leaving a group Master."
	::= 26

axVirtualServerCreateDelete   TRAP-TYPE
	ENTERPRISE axSlbNotifications
	VARIABLES       { 
			axNotificationMsg, 
			axNotificationVirtualServer,
            axNotificationPartitionName,
            axNotificationSlbObjectChange
		      }
	DESCRIPTION   "Slb virtual server is added or deleted."
	::= 1

axVirtualServerPortCreateDelete   TRAP-TYPE
	ENTERPRISE axSlbNotifications
	VARIABLES       { 
			axNotificationMsg, 
            axNotificationVirtualServer,
            axNotificationVirtualServerPort,
            axNotificationVirtualServerPortType,
            axNotificationPartitionName,
            axNotificationSlbObjectChange
		      }
	DESCRIPTION   "Slb virtual server port is addeded or deleted."
	::= 2

axServerCreateDelete   TRAP-TYPE
	ENTERPRISE axSlbNotifications
	VARIABLES       { 
			axNotificationMsg, 
			axNotificationSLBServer,
            axNotificationPartitionName,
            axNotificationSlbObjectChange
		      }
	DESCRIPTION   "Slb server is added or deleted."
	::= 3

axServerPortCreateDelete   TRAP-TYPE
	ENTERPRISE axSlbNotifications
	VARIABLES       { 
			axNotificationMsg, 
			axNotificationSLBServer,
            axNotificationSLBPort,
            axNotificationSLBServerPortType,
            axNotificationPartitionName,
            axNotificationSlbObjectChange
		      }
	DESCRIPTION   "Slb server port is added or delete."
	::= 4

axSslCertificateCreateDelete   TRAP-TYPE
	ENTERPRISE axSlbNotifications
	VARIABLES       { 
			axNotificationMsg, 
			axNotificationCertificateName,
            axNotificationPartitionName,
            axNotificationSlbObjectChange
		      }
	DESCRIPTION   "Ssl certification is create or delete."
	::= 5

axSslCertificateExpiring   TRAP-TYPE
	ENTERPRISE axSlbNotifications
    VARIABLES       {
            axNotificationMsg,
            axNotificationCertificateName,
            axNotificationPartitionName,
--string of time that the certificate is expired or to be expired
            axNotificationDateTime     
                     }
       DESCRIPTION   "The certification is going to be expired."
       ::= 6

axPartitionResourceUsageWarning   TRAP-TYPE
       ENTERPRISE axSlbNotifications
       VARIABLES     {
                       axNotificationMsg,
                       axNotificationPartitionResourceName,
                       axNotificationPartitionResourceUsageLevel,
                        axNotificationPartitionName
                     }
       DESCRIPTION   "The partition resource usage becomes above/below the configured limitation."
       ::= 7

END
