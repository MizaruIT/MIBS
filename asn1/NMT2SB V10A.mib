--  Title:    NMT2SB_V10A.MIB
--  Version:  v1.0
--
--  Copyright @ 1997-2004 DPS Inc. All Rights Reserved
--
--  This MIB defines supplemental objects for the DPS NetMediator T2S series remotes.
--
--

DPS-MIB-NMT2SB-V10A DEFINITIONS ::= BEGIN

IMPORTS
	dpsRTU
		FROM DPS-MIB-V38;

dpsRTUp18001Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 1 is set"
	::= 18001

dpsRTUp19001Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 1 is cleared"
	::= 19001

dpsRTUp18002Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 2 is set"
	::= 18002

dpsRTUp19002Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 2 is cleared"
	::= 19002

dpsRTUp18003Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 3 is set"
	::= 18003

dpsRTUp19003Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 3 is cleared"
	::= 19003

dpsRTUp18004Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 4 is set"
	::= 18004

dpsRTUp19004Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 4 is cleared"
	::= 19004

dpsRTUp18005Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 5 is set"
	::= 18005

dpsRTUp19005Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 5 is cleared"
	::= 19005

dpsRTUp18006Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 6 is set"
	::= 18006

dpsRTUp19006Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 6 is cleared"
	::= 19006

dpsRTUp18007Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 7 is set"
	::= 18007

dpsRTUp19007Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 7 is cleared"
	::= 19007

dpsRTUp18008Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 8 is set"
	::= 18008

dpsRTUp19008Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 8 is cleared"
	::= 19008

dpsRTUp18009Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 9 is set"
	::= 18009

dpsRTUp19009Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 9 is cleared"
	::= 19009

dpsRTUp18010Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 10 is set"
	::= 18010

dpsRTUp19010Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 10 is cleared"
	::= 19010

dpsRTUp18011Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 11 is set"
	::= 18011

dpsRTUp19011Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 11 is cleared"
	::= 19011

dpsRTUp18012Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 12 is set"
	::= 18012

dpsRTUp19012Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 12 is cleared"
	::= 19012

dpsRTUp18013Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 13 is set"
	::= 18013

dpsRTUp19013Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 13 is cleared"
	::= 19013

dpsRTUp18014Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 14 is set"
	::= 18014

dpsRTUp19014Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 14 is cleared"
	::= 19014

dpsRTUp18015Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 15 is set"
	::= 18015

dpsRTUp19015Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 15 is cleared"
	::= 19015

dpsRTUp18016Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 16 is set"
	::= 18016

dpsRTUp19016Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 16 is cleared"
	::= 19016

dpsRTUp18017Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 17 is set"
	::= 18017

dpsRTUp19017Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 17 is cleared"
	::= 19017

dpsRTUp18018Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 18 is set"
	::= 18018

dpsRTUp19018Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 18 is cleared"
	::= 19018

dpsRTUp18019Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 19 is set"
	::= 18019

dpsRTUp19019Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 19 is cleared"
	::= 19019

dpsRTUp18020Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 20 is set"
	::= 18020

dpsRTUp19020Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 20 is cleared"
	::= 19020

dpsRTUp18021Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 21 is set"
	::= 18021

dpsRTUp19021Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 21 is cleared"
	::= 19021

dpsRTUp18022Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 22 is set"

	::= 18022

dpsRTUp19022Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 22 is cleared"
	::= 19022

dpsRTUp18023Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 23 is set"
	::= 18023

dpsRTUp19023Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 23 is cleared"
	::= 19023

dpsRTUp18024Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 24 is set"
	::= 18024

dpsRTUp19024Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 24 is cleared"
	::= 19024

dpsRTUp18025Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 25 is set"
	::= 18025

dpsRTUp19025Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 25 is cleared"
	::= 19025

dpsRTUp18026Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 26 is set"
	::= 18026

dpsRTUp19026Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 26 is cleared"
	::= 19026

dpsRTUp18027Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 27 is set"
	::= 18027

dpsRTUp19027Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 27 is cleared"
	::= 19027

dpsRTUp18028Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 28 is set"
	::= 18028

dpsRTUp19028Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 28 is cleared"
	::= 19028

dpsRTUp18029Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 29 is set"
	::= 18029

dpsRTUp19029Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 29 is cleared"
	::= 19029

dpsRTUp18030Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 30 is set"
	::= 18030

dpsRTUp19030Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 30 is cleared"
	::= 19030

dpsRTUp18031Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 31 is set"
	::= 18031

dpsRTUp19031Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 31 is cleared"
	::= 19031

dpsRTUp18032Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 32 is set"
	::= 18032

dpsRTUp19032Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 32 is cleared"
	::= 19032

dpsRTUp18033Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 33 is set"
	::= 18033

dpsRTUp19033Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 33 is cleared"
	::= 19033

dpsRTUp18034Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 34 is set"
	::= 18034

dpsRTUp19034Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 34 is cleared"
	::= 19034

dpsRTUp18035Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 35 is set"
	::= 18035

dpsRTUp19035Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 35 is cleared"
	::= 19035

dpsRTUp18036Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 36 is set"
	::= 18036

dpsRTUp19036Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 36 is cleared"
	::= 19036

dpsRTUp18037Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 37 is set"
	::= 18037

dpsRTUp19037Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 37 is cleared"
	::= 19037

dpsRTUp18038Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 38 is set"
	::= 18038

dpsRTUp19038Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 38 is cleared"
	::= 19038

dpsRTUp18039Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 39 is set"
	::= 18039

dpsRTUp19039Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 39 is cleared"
	::= 19039

dpsRTUp18040Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 40 is set"
	::= 18040

dpsRTUp19040Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 40 is cleared"
	::= 19040

dpsRTUp18041Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 41 is set"
	::= 18041

dpsRTUp19041Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 41 is cleared"
	::= 19041

dpsRTUp18042Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 42 is set"
	::= 18042

dpsRTUp19042Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 42 is cleared"
	::= 19042

dpsRTUp18043Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 43 is set"
	::= 18043

dpsRTUp19043Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 43 is cleared"
	::= 19043

dpsRTUp18044Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 44 is set"
	::= 18044

dpsRTUp19044Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 44 is cleared"
	::= 19044

dpsRTUp18045Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 45 is set"
	::= 18045

dpsRTUp19045Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 45 is cleared"
	::= 19045

dpsRTUp18046Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 46 is set"
	::= 18046

dpsRTUp19046Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 46 is cleared"
	::= 19046

dpsRTUp18047Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 47 is set"
	::= 18047

dpsRTUp19047Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 47 is cleared"
	::= 19047

dpsRTUp18048Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 48 is set"
	::= 18048

dpsRTUp19048Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 48 is cleared"
	::= 19048

dpsRTUp18049Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 49 is set"
	::= 18049

dpsRTUp19049Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 49 is cleared"
	::= 19049

dpsRTUp18050Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 50 is set"
	::= 18050

dpsRTUp19050Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 50 is cleared"
	::= 19050

dpsRTUp18051Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 51 is set"
	::= 18051

dpsRTUp19051Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 51 is cleared"
	::= 19051

dpsRTUp18052Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 52 is set"
	::= 18052

dpsRTUp19052Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 52 is cleared"
	::= 19052

dpsRTUp18053Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 53 is set"
	::= 18053

dpsRTUp19053Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 53 is cleared"
	::= 19053

dpsRTUp18054Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 54 is set"
	::= 18054

dpsRTUp19054Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 54 is cleared"
	::= 19054

dpsRTUp18055Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 55 is set"
	::= 18055

dpsRTUp19055Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 55 is cleared"
	::= 19055

dpsRTUp18056Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 56 is set"
	::= 18056

dpsRTUp19056Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 56 is cleared"
	::= 19056

dpsRTUp18057Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 57 is set"
	::= 18057

dpsRTUp19057Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 57 is cleared"
	::= 19057

dpsRTUp18058Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 58 is set"
	::= 18058

dpsRTUp19058Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 58 is cleared"
	::= 19058

dpsRTUp18059Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 59 is set"
	::= 18059

dpsRTUp19059Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 59 is cleared"
	::= 19059

dpsRTUp18060Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 60 is set"
	::= 18060

dpsRTUp19060Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 60 is cleared"
	::= 19060

dpsRTUp18061Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 61 is set"
	::= 18061

dpsRTUp19061Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 61 is cleared"
	::= 19061

dpsRTUp18062Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 62 is set"
	::= 18062

dpsRTUp19062Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 62 is cleared"
	::= 19062

dpsRTUp18063Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 63 is set"
	::= 18063

dpsRTUp19063Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 63 is cleared"
	::= 19063

dpsRTUp18064Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 64 is set"
	::= 18064

dpsRTUp19064Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 1 point 64 is cleared"
	::= 19064

dpsRTUp18065Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 1 is set"
	::= 18065

dpsRTUp19065Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 1 is cleared"
	::= 19065

dpsRTUp18066Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 2 is set"
	::= 18066

dpsRTUp19066Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 2 is cleared"
	::= 19066

dpsRTUp18067Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 3 is set"
	::= 18067

dpsRTUp19067Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 3 is cleared"
	::= 19067

dpsRTUp18068Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 4 is set"
	::= 18068

dpsRTUp19068Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 4 is cleared"
	::= 19068

dpsRTUp18069Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 5 is set"
	::= 18069

dpsRTUp19069Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 5 is cleared"
	::= 19069

dpsRTUp18070Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 6 is set"
	::= 18070

dpsRTUp19070Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 6 is cleared"
	::= 19070

dpsRTUp18071Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 7 is set"
	::= 18071

dpsRTUp19071Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 7 is cleared"
	::= 19071

dpsRTUp18072Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 8 is set"
	::= 18072

dpsRTUp19072Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 8 is cleared"
	::= 19072

dpsRTUp18073Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 9 is set"
	::= 18073

dpsRTUp19073Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 9 is cleared"
	::= 19073

dpsRTUp18074Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 10 is set"
	::= 18074

dpsRTUp19074Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 10 is cleared"
	::= 19074

dpsRTUp18075Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 11 is set"
	::= 18075

dpsRTUp19075Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 11 is cleared"
	::= 19075

dpsRTUp18076Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 12 is set"
	::= 18076

dpsRTUp19076Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 12 is cleared"
	::= 19076

dpsRTUp18077Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 13 is set"
	::= 18077

dpsRTUp19077Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 13 is cleared"
	::= 19077

dpsRTUp18078Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 14 is set"
	::= 18078

dpsRTUp19078Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 14 is cleared"
	::= 19078

dpsRTUp18079Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 15 is set"
	::= 18079

dpsRTUp19079Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 15 is cleared"
	::= 19079

dpsRTUp18080Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 16 is set"
	::= 18080

dpsRTUp19080Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 16 is cleared"
	::= 19080

dpsRTUp18081Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 17 is set"
	::= 18081

dpsRTUp19081Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 17 is cleared"
	::= 19081

dpsRTUp18082Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 18 is set"
	::= 18082

dpsRTUp19082Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 18 is cleared"
	::= 19082

dpsRTUp18083Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 19 is set"
	::= 18083

dpsRTUp19083Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 19 is cleared"
	::= 19083

dpsRTUp18084Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 20 is set"
	::= 18084

dpsRTUp19084Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 20 is cleared"
	::= 19084

dpsRTUp18085Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 21 is set"
	::= 18085

dpsRTUp19085Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 21 is cleared"
	::= 19085

dpsRTUp18086Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 22 is set"
	::= 18086

dpsRTUp19086Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 22 is cleared"
	::= 19086

dpsRTUp18087Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 23 is set"
	::= 18087

dpsRTUp19087Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 23 is cleared"
	::= 19087

dpsRTUp18088Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 24 is set"
	::= 18088

dpsRTUp19088Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 24 is cleared"
	::= 19088

dpsRTUp18089Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 25 is set"
	::= 18089

dpsRTUp19089Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 25 is cleared"
	::= 19089

dpsRTUp18090Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 26 is set"
	::= 18090

dpsRTUp19090Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 26 is cleared"
	::= 19090

dpsRTUp18091Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 27 is set"
	::= 18091

dpsRTUp19091Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 27 is cleared"
	::= 19091

dpsRTUp18092Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 28 is set"
	::= 18092

dpsRTUp19092Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 28 is cleared"
	::= 19092

dpsRTUp18093Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 29 is set"
	::= 18093

dpsRTUp19093Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 29 is cleared"
	::= 19093

dpsRTUp18094Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 30 is set"
	::= 18094

dpsRTUp19094Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 30 is cleared"
	::= 19094

dpsRTUp18095Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 31 is set"
	::= 18095

dpsRTUp19095Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 31 is cleared"
	::= 19095

dpsRTUp18096Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 32 is set"
	::= 18096

dpsRTUp19096Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 32 is cleared"
	::= 19096

dpsRTUp18097Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 33 is set"
	::= 18097

dpsRTUp19097Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 33 is cleared"
	::= 19097

dpsRTUp18098Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 34 is set"
	::= 18098

dpsRTUp19098Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 34 is cleared"
	::= 19098

dpsRTUp18099Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 35 is set"
	::= 18099

dpsRTUp19099Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 35 is cleared"
	::= 19099

dpsRTUp18100Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 36 is set"
	::= 18100

dpsRTUp19100Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 36 is cleared"
	::= 19100

dpsRTUp18101Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 37 is set"
	::= 18101

dpsRTUp19101Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 37 is cleared"
	::= 19101

dpsRTUp18102Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 38 is set"
	::= 18102

dpsRTUp19102Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 38 is cleared"
	::= 19102

dpsRTUp18103Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 39 is set"
	::= 18103

dpsRTUp19103Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 39 is cleared"
	::= 19103

dpsRTUp18104Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 40 is set"
	::= 18104

dpsRTUp19104Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 40 is cleared"
	::= 19104

dpsRTUp18105Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 41 is set"
	::= 18105

dpsRTUp19105Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 41 is cleared"
	::= 19105

dpsRTUp18106Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 42 is set"
	::= 18106

dpsRTUp19106Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 42 is cleared"
	::= 19106

dpsRTUp18107Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 43 is set"
	::= 18107

dpsRTUp19107Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 43 is cleared"
	::= 19107

dpsRTUp18108Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 44 is set"
	::= 18108

dpsRTUp19108Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 44 is cleared"
	::= 19108

dpsRTUp18109Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 45 is set"
	::= 18109

dpsRTUp19109Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 45 is cleared"
	::= 19109

dpsRTUp18110Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 46 is set"
	::= 18110

dpsRTUp19110Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 46 is cleared"
	::= 19110

dpsRTUp18111Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 47 is set"
	::= 18111

dpsRTUp19111Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 47 is cleared"
	::= 19111

dpsRTUp18112Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 48 is set"
	::= 18112

dpsRTUp19112Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 48 is cleared"
	::= 19112

dpsRTUp18113Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 49 is set"
	::= 18113

dpsRTUp19113Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 49 is cleared"
	::= 19113

dpsRTUp18114Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 50 is set"
	::= 18114

dpsRTUp19114Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 50 is cleared"
	::= 19114

dpsRTUp18115Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 51 is set"
	::= 18115

dpsRTUp19115Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 51 is cleared"
	::= 19115

dpsRTUp18116Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 52 is set"
	::= 18116

dpsRTUp19116Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 52 is cleared"
	::= 19116

dpsRTUp18117Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 53 is set"
	::= 18117

dpsRTUp19117Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 53 is cleared"
	::= 19117

dpsRTUp18118Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 54 is set"
	::= 18118

dpsRTUp19118Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 54 is cleared"
	::= 19118

dpsRTUp18119Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 55 is set"
	::= 18119

dpsRTUp19119Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 55 is cleared"
	::= 19119

dpsRTUp18120Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 56 is set"
	::= 18120

dpsRTUp19120Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 56 is cleared"
	::= 19120

dpsRTUp18121Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 57 is set"
	::= 18121

dpsRTUp19121Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 57 is cleared"
	::= 19121

dpsRTUp18122Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 58 is set"
	::= 18122

dpsRTUp19122Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 58 is cleared"
	::= 19122

dpsRTUp18123Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 59 is set"
	::= 18123

dpsRTUp19123Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 59 is cleared"
	::= 19123

dpsRTUp18124Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 60 is set"
	::= 18124

dpsRTUp19124Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 60 is cleared"
	::= 19124

dpsRTUp18125Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 61 is set"
	::= 18125

dpsRTUp19125Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 61 is cleared"
	::= 19125

dpsRTUp18126Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 62 is set"
	::= 18126

dpsRTUp19126Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 62 is cleared"
	::= 19126

dpsRTUp18127Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 63 is set"
	::= 18127

dpsRTUp19127Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 63 is cleared"
	::= 19127

dpsRTUp18128Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 64 is set"
	::= 18128

dpsRTUp19128Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 2 point 64 is cleared"
	::= 19128

dpsRTUp18129Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 1 is set"
	::= 18129

dpsRTUp19129Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 1 is cleared"
	::= 19129

dpsRTUp18130Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 2 is set"
	::= 18130

dpsRTUp19130Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 2 is cleared"
	::= 19130

dpsRTUp18131Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 3 is set"
	::= 18131

dpsRTUp19131Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 3 is cleared"
	::= 19131

dpsRTUp18132Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 4 is set"
	::= 18132

dpsRTUp19132Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 4 is cleared"
	::= 19132

dpsRTUp18133Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 5 is set"
	::= 18133

dpsRTUp19133Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 5 is cleared"
	::= 19133

dpsRTUp18134Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 6 is set"
	::= 18134

dpsRTUp19134Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 6 is cleared"
	::= 19134

dpsRTUp18135Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 7 is set"
	::= 18135

dpsRTUp19135Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 7 is cleared"
	::= 19135

dpsRTUp18136Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 8 is set"
	::= 18136

dpsRTUp19136Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 8 is cleared"
	::= 19136

dpsRTUp18137Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 9 is set"
	::= 18137

dpsRTUp19137Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 9 is cleared"
	::= 19137

dpsRTUp18138Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 10 is set"
	::= 18138

dpsRTUp19138Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 10 is cleared"
	::= 19138

dpsRTUp18139Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 11 is set"
	::= 18139

dpsRTUp19139Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 11 is cleared"
	::= 19139

dpsRTUp18140Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 12 is set"
	::= 18140

dpsRTUp19140Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 12 is cleared"
	::= 19140

dpsRTUp18141Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 13 is set"
	::= 18141

dpsRTUp19141Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 13 is cleared"
	::= 19141

dpsRTUp18142Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 14 is set"
	::= 18142

dpsRTUp19142Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 14 is cleared"
	::= 19142

dpsRTUp18143Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 15 is set"
	::= 18143

dpsRTUp19143Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 15 is cleared"
	::= 19143

dpsRTUp18144Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 16 is set"
	::= 18144

dpsRTUp19144Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 16 is cleared"
	::= 19144

dpsRTUp18145Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 17 is set"
	::= 18145

dpsRTUp19145Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 17 is cleared"
	::= 19145

dpsRTUp18146Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 18 is set"
	::= 18146

dpsRTUp19146Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 18 is cleared"
	::= 19146

dpsRTUp18147Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 19 is set"
	::= 18147

dpsRTUp19147Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 19 is cleared"
	::= 19147

dpsRTUp18148Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 20 is set"
	::= 18148

dpsRTUp19148Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 20 is cleared"
	::= 19148

dpsRTUp18149Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 21 is set"
	::= 18149

dpsRTUp19149Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 21 is cleared"
	::= 19149

dpsRTUp18150Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 22 is set"
	::= 18150

dpsRTUp19150Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 22 is cleared"
	::= 19150

dpsRTUp18151Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 23 is set"
	::= 18151

dpsRTUp19151Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 23 is cleared"
	::= 19151

dpsRTUp18152Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 24 is set"
	::= 18152

dpsRTUp19152Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 24 is cleared"
	::= 19152

dpsRTUp18153Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 25 is set"
	::= 18153

dpsRTUp19153Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 25 is cleared"
	::= 19153

dpsRTUp18154Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 26 is set"
	::= 18154

dpsRTUp19154Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 26 is cleared"
	::= 19154

dpsRTUp18155Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 27 is set"
	::= 18155

dpsRTUp19155Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 27 is cleared"
	::= 19155

dpsRTUp18156Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 28 is set"
	::= 18156

dpsRTUp19156Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 28 is cleared"
	::= 19156

dpsRTUp18157Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 29 is set"
	::= 18157

dpsRTUp19157Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 29 is cleared"
	::= 19157

dpsRTUp18158Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 30 is set"
	::= 18158

dpsRTUp19158Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 30 is cleared"
	::= 19158

dpsRTUp18159Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 31 is set"
	::= 18159

dpsRTUp19159Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 31 is cleared"
	::= 19159

dpsRTUp18160Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 32 is set"
	::= 18160

dpsRTUp19160Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 32 is cleared"
	::= 19160

dpsRTUp18161Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 33 is set"
	::= 18161

dpsRTUp19161Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 33 is cleared"
	::= 19161

dpsRTUp18162Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 34 is set"
	::= 18162

dpsRTUp19162Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 34 is cleared"
	::= 19162

dpsRTUp18163Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 35 is set"
	::= 18163

dpsRTUp19163Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 35 is cleared"
	::= 19163

dpsRTUp18164Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 36 is set"
	::= 18164

dpsRTUp19164Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 36 is cleared"
	::= 19164

dpsRTUp18165Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 37 is set"
	::= 18165

dpsRTUp19165Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 37 is cleared"
	::= 19165

dpsRTUp18166Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 38 is set"
	::= 18166

dpsRTUp19166Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 38 is cleared"
	::= 19166

dpsRTUp18167Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 39 is set"
	::= 18167

dpsRTUp19167Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 39 is cleared"
	::= 19167

dpsRTUp18168Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 40 is set"
	::= 18168

dpsRTUp19168Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 40 is cleared"
	::= 19168

dpsRTUp18169Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 41 is set"
	::= 18169

dpsRTUp19169Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 41 is cleared"
	::= 19169

dpsRTUp18170Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 42 is set"
	::= 18170

dpsRTUp19170Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 42 is cleared"
	::= 19170

dpsRTUp18171Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 43 is set"
	::= 18171

dpsRTUp19171Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 43 is cleared"
	::= 19171

dpsRTUp18172Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 44 is set"
	::= 18172

dpsRTUp19172Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 44 is cleared"
	::= 19172

dpsRTUp18173Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 45 is set"
	::= 18173

dpsRTUp19173Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 45 is cleared"
	::= 19173

dpsRTUp18174Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 46 is set"
	::= 18174

dpsRTUp19174Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 46 is cleared"
	::= 19174

dpsRTUp18175Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 47 is set"
	::= 18175

dpsRTUp19175Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 47 is cleared"
	::= 19175

dpsRTUp18176Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 48 is set"
	::= 18176

dpsRTUp19176Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 48 is cleared"
	::= 19176

dpsRTUp18177Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 49 is set"
	::= 18177

dpsRTUp19177Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 49 is cleared"
	::= 19177

dpsRTUp18178Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 50 is set"
	::= 18178

dpsRTUp19178Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 50 is cleared"
	::= 19178

dpsRTUp18179Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 51 is set"
	::= 18179

dpsRTUp19179Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 51 is cleared"
	::= 19179

dpsRTUp18180Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 52 is set"
	::= 18180

dpsRTUp19180Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 52 is cleared"
	::= 19180

dpsRTUp18181Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 53 is set"
	::= 18181

dpsRTUp19181Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 53 is cleared"
	::= 19181

dpsRTUp18182Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 54 is set"
	::= 18182

dpsRTUp19182Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 54 is cleared"
	::= 19182

dpsRTUp18183Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 55 is set"
	::= 18183

dpsRTUp19183Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 55 is cleared"
	::= 19183

dpsRTUp18184Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 56 is set"
	::= 18184

dpsRTUp19184Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 56 is cleared"
	::= 19184

dpsRTUp18185Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 57 is set"
	::= 18185

dpsRTUp19185Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 57 is cleared"
	::= 19185

dpsRTUp18186Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 58 is set"
	::= 18186

dpsRTUp19186Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 58 is cleared"
	::= 19186

dpsRTUp18187Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 59 is set"
	::= 18187

dpsRTUp19187Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 59 is cleared"
	::= 19187

dpsRTUp18188Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 60 is set"
	::= 18188

dpsRTUp19188Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 60 is cleared"
	::= 19188

dpsRTUp18189Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 61 is set"
	::= 18189

dpsRTUp19189Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 61 is cleared"
	::= 19189

dpsRTUp18190Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 62 is set"
	::= 18190

dpsRTUp19190Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 62 is cleared"
	::= 19190

dpsRTUp18191Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 63 is set"
	::= 18191

dpsRTUp19191Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 63 is cleared"
	::= 19191

dpsRTUp18192Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 64 is set"
	::= 18192

dpsRTUp19192Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 3 point 64 is cleared"
	::= 19192

dpsRTUp18193Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 1 is set"
	::= 18193

dpsRTUp19193Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 1 is cleared"
	::= 19193

dpsRTUp18194Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 2 is set"
	::= 18194

dpsRTUp19194Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 2 is cleared"
	::= 19194

dpsRTUp18195Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 3 is set"
	::= 18195

dpsRTUp19195Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 3 is cleared"
	::= 19195

dpsRTUp18196Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 4 is set"
	::= 18196

dpsRTUp19196Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 4 is cleared"
	::= 19196

dpsRTUp18197Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 5 is set"
	::= 18197

dpsRTUp19197Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 5 is cleared"
	::= 19197

dpsRTUp18198Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 6 is set"
	::= 18198

dpsRTUp19198Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 6 is cleared"
	::= 19198

dpsRTUp18199Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 7 is set"
	::= 18199

dpsRTUp19199Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 7 is cleared"
	::= 19199

dpsRTUp18200Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 8 is set"
	::= 18200

dpsRTUp19200Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 8 is cleared"
	::= 19200

dpsRTUp18201Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 9 is set"
	::= 18201

dpsRTUp19201Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 9 is cleared"
	::= 19201

dpsRTUp18202Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 10 is set"
	::= 18202

dpsRTUp19202Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 10 is cleared"
	::= 19202

dpsRTUp18203Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 11 is set"
	::= 18203

dpsRTUp19203Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 11 is cleared"
	::= 19203

dpsRTUp18204Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 12 is set"
	::= 18204

dpsRTUp19204Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 12 is cleared"
	::= 19204

dpsRTUp18205Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 13 is set"
	::= 18205

dpsRTUp19205Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 13 is cleared"
	::= 19205

dpsRTUp18206Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 14 is set"
	::= 18206

dpsRTUp19206Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 14 is cleared"
	::= 19206

dpsRTUp18207Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 15 is set"
	::= 18207

dpsRTUp19207Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 15 is cleared"
	::= 19207

dpsRTUp18208Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 16 is set"
	::= 18208

dpsRTUp19208Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 16 is cleared"
	::= 19208

dpsRTUp18209Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 17 is set"
	::= 18209

dpsRTUp19209Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 17 is cleared"
	::= 19209

dpsRTUp18210Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 18 is set"
	::= 18210

dpsRTUp19210Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 18 is cleared"
	::= 19210

dpsRTUp18211Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 19 is set"
	::= 18211

dpsRTUp19211Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 19 is cleared"
	::= 19211

dpsRTUp18212Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 20 is set"
	::= 18212

dpsRTUp19212Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 20 is cleared"
	::= 19212

dpsRTUp18213Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 21 is set"
	::= 18213

dpsRTUp19213Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 21 is cleared"
	::= 19213

dpsRTUp18214Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 22 is set"
	::= 18214

dpsRTUp19214Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 22 is cleared"
	::= 19214

dpsRTUp18215Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 23 is set"
	::= 18215

dpsRTUp19215Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 23 is cleared"
	::= 19215

dpsRTUp18216Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 24 is set"
	::= 18216

dpsRTUp19216Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 24 is cleared"
	::= 19216

dpsRTUp18217Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 25 is set"
	::= 18217

dpsRTUp19217Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 25 is cleared"
	::= 19217

dpsRTUp18218Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 26 is set"
	::= 18218

dpsRTUp19218Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 26 is cleared"
	::= 19218

dpsRTUp18219Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 27 is set"
	::= 18219

dpsRTUp19219Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 27 is cleared"
	::= 19219

dpsRTUp18220Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 28 is set"
	::= 18220

dpsRTUp19220Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 28 is cleared"
	::= 19220

dpsRTUp18221Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 29 is set"
	::= 18221

dpsRTUp19221Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 29 is cleared"
	::= 19221

dpsRTUp18222Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 30 is set"
	::= 18222

dpsRTUp19222Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 30 is cleared"
	::= 19222

dpsRTUp18223Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 31 is set"
	::= 18223

dpsRTUp19223Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 31 is cleared"
	::= 19223

dpsRTUp18224Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 32 is set"
	::= 18224

dpsRTUp19224Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 32 is cleared"
	::= 19224

dpsRTUp18225Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 33 is set"
	::= 18225

dpsRTUp19225Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 33 is cleared"
	::= 19225

dpsRTUp18226Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 34 is set"
	::= 18226

dpsRTUp19226Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 34 is cleared"
	::= 19226

dpsRTUp18227Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 35 is set"
	::= 18227

dpsRTUp19227Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 35 is cleared"
	::= 19227

dpsRTUp18228Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 36 is set"
	::= 18228

dpsRTUp19228Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 36 is cleared"
	::= 19228

dpsRTUp18229Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 37 is set"
	::= 18229

dpsRTUp19229Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 37 is cleared"
	::= 19229

dpsRTUp18230Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 38 is set"
	::= 18230

dpsRTUp19230Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 38 is cleared"
	::= 19230

dpsRTUp18231Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 39 is set"
	::= 18231

dpsRTUp19231Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 39 is cleared"
	::= 19231

dpsRTUp18232Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 40 is set"
	::= 18232

dpsRTUp19232Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 40 is cleared"
	::= 19232

dpsRTUp18233Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 41 is set"
	::= 18233

dpsRTUp19233Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 41 is cleared"
	::= 19233

dpsRTUp18234Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 42 is set"
	::= 18234

dpsRTUp19234Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 42 is cleared"
	::= 19234

dpsRTUp18235Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 43 is set"
	::= 18235

dpsRTUp19235Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 43 is cleared"
	::= 19235

dpsRTUp18236Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 44 is set"
	::= 18236

dpsRTUp19236Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 44 is cleared"
	::= 19236

dpsRTUp18237Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 45 is set"
	::= 18237

dpsRTUp19237Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 45 is cleared"
	::= 19237

dpsRTUp18238Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 46 is set"
	::= 18238

dpsRTUp19238Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 46 is cleared"
	::= 19238

dpsRTUp18239Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 47 is set"
	::= 18239

dpsRTUp19239Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 47 is cleared"
	::= 19239

dpsRTUp18240Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 48 is set"
	::= 18240

dpsRTUp19240Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 48 is cleared"
	::= 19240

dpsRTUp18241Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 49 is set"
	::= 18241

dpsRTUp19241Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 49 is cleared"
	::= 19241

dpsRTUp18242Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 50 is set"
	::= 18242

dpsRTUp19242Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 50 is cleared"
	::= 19242

dpsRTUp18243Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 51 is set"
	::= 18243

dpsRTUp19243Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 51 is cleared"
	::= 19243

dpsRTUp18244Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 52 is set"
	::= 18244

dpsRTUp19244Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 52 is cleared"
	::= 19244

dpsRTUp18245Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 53 is set"
	::= 18245

dpsRTUp19245Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 53 is cleared"
	::= 19245

dpsRTUp18246Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 54 is set"
	::= 18246

dpsRTUp19246Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 54 is cleared"
	::= 19246

dpsRTUp18247Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 55 is set"
	::= 18247

dpsRTUp19247Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 55 is cleared"
	::= 19247

dpsRTUp18248Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 56 is set"
	::= 18248

dpsRTUp19248Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 56 is cleared"
	::= 19248

dpsRTUp18249Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 57 is set"
	::= 18249

dpsRTUp19249Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 57 is cleared"
	::= 19249

dpsRTUp18250Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 58 is set"
	::= 18250

dpsRTUp19250Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 58 is cleared"
	::= 19250

dpsRTUp18251Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 59 is set"
	::= 18251

dpsRTUp19251Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 59 is cleared"
	::= 19251

dpsRTUp18252Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 60 is set"
	::= 18252

dpsRTUp19252Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 60 is cleared"
	::= 19252

dpsRTUp18253Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 61 is set"
	::= 18253

dpsRTUp19253Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 61 is cleared"
	::= 19253

dpsRTUp18254Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 62 is set"
	::= 18254

dpsRTUp19254Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 62 is cleared"
	::= 19254

dpsRTUp18255Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 63 is set"
	::= 18255

dpsRTUp19255Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 63 is cleared"
	::= 19255

dpsRTUp18256Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 64 is set"
	::= 18256

dpsRTUp19256Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 4 point 64 is cleared"
	::= 19256

dpsRTUp18257Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 1 is set"
	::= 18257

dpsRTUp19257Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 1 is cleared"
	::= 19257

dpsRTUp18258Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 2 is set"
	::= 18258

dpsRTUp19258Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 2 is cleared"
	::= 19258

dpsRTUp18259Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 3 is set"
	::= 18259

dpsRTUp19259Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 3 is cleared"
	::= 19259

dpsRTUp18260Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 4 is set"
	::= 18260

dpsRTUp19260Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 4 is cleared"
	::= 19260

dpsRTUp18261Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 5 is set"
	::= 18261

dpsRTUp19261Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 5 is cleared"
	::= 19261

dpsRTUp18262Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 6 is set"
	::= 18262

dpsRTUp19262Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 6 is cleared"
	::= 19262

dpsRTUp18263Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 7 is set"
	::= 18263

dpsRTUp19263Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 7 is cleared"
	::= 19263

dpsRTUp18264Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 8 is set"
	::= 18264

dpsRTUp19264Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 8 is cleared"
	::= 19264

dpsRTUp18265Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 9 is set"
	::= 18265

dpsRTUp19265Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 9 is cleared"
	::= 19265

dpsRTUp18266Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 10 is set"
	::= 18266

dpsRTUp19266Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 10 is cleared"
	::= 19266

dpsRTUp18267Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 11 is set"
	::= 18267

dpsRTUp19267Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 11 is cleared"
	::= 19267

dpsRTUp18268Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 12 is set"
	::= 18268

dpsRTUp19268Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 12 is cleared"
	::= 19268

dpsRTUp18269Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 13 is set"
	::= 18269

dpsRTUp19269Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 13 is cleared"
	::= 19269

dpsRTUp18270Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 14 is set"
	::= 18270

dpsRTUp19270Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 14 is cleared"
	::= 19270

dpsRTUp18271Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 15 is set"
	::= 18271

dpsRTUp19271Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 15 is cleared"
	::= 19271

dpsRTUp18272Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 16 is set"
	::= 18272

dpsRTUp19272Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 16 is cleared"
	::= 19272

dpsRTUp18273Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 17 is set"
	::= 18273

dpsRTUp19273Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 17 is cleared"
	::= 19273

dpsRTUp18274Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 18 is set"
	::= 18274

dpsRTUp19274Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 18 is cleared"
	::= 19274

dpsRTUp18275Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 19 is set"
	::= 18275

dpsRTUp19275Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 19 is cleared"
	::= 19275

dpsRTUp18276Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 20 is set"
	::= 18276

dpsRTUp19276Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 20 is cleared"
	::= 19276

dpsRTUp18277Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 21 is set"
	::= 18277

dpsRTUp19277Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 21 is cleared"
	::= 19277

dpsRTUp18278Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 22 is set"
	::= 18278

dpsRTUp19278Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 22 is cleared"
	::= 19278

dpsRTUp18279Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 23 is set"
	::= 18279

dpsRTUp19279Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 23 is cleared"
	::= 19279

dpsRTUp18280Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 24 is set"
	::= 18280

dpsRTUp19280Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 24 is cleared"
	::= 19280

dpsRTUp18281Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 25 is set"
	::= 18281

dpsRTUp19281Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 25 is cleared"
	::= 19281

dpsRTUp18282Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 26 is set"
	::= 18282

dpsRTUp19282Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 26 is cleared"
	::= 19282

dpsRTUp18283Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 27 is set"
	::= 18283

dpsRTUp19283Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 27 is cleared"
	::= 19283

dpsRTUp18284Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 28 is set"
	::= 18284

dpsRTUp19284Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 28 is cleared"
	::= 19284

dpsRTUp18285Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 29 is set"
	::= 18285

dpsRTUp19285Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 29 is cleared"
	::= 19285

dpsRTUp18286Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 30 is set"
	::= 18286

dpsRTUp19286Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 30 is cleared"
	::= 19286

dpsRTUp18287Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 31 is set"
	::= 18287

dpsRTUp19287Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 31 is cleared"
	::= 19287

dpsRTUp18288Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 32 is set"
	::= 18288

dpsRTUp19288Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 32 is cleared"
	::= 19288

dpsRTUp18289Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 33 is set"
	::= 18289

dpsRTUp19289Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 33 is cleared"
	::= 19289

dpsRTUp18290Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 34 is set"
	::= 18290

dpsRTUp19290Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 34 is cleared"
	::= 19290

dpsRTUp18291Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 35 is set"
	::= 18291

dpsRTUp19291Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 35 is cleared"
	::= 19291

dpsRTUp18292Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 36 is set"
	::= 18292

dpsRTUp19292Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 36 is cleared"
	::= 19292

dpsRTUp18293Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 37 is set"
	::= 18293

dpsRTUp19293Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 37 is cleared"
	::= 19293

dpsRTUp18294Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 38 is set"
	::= 18294

dpsRTUp19294Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 38 is cleared"
	::= 19294

dpsRTUp18295Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 39 is set"
	::= 18295

dpsRTUp19295Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 39 is cleared"
	::= 19295

dpsRTUp18296Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 40 is set"
	::= 18296

dpsRTUp19296Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 40 is cleared"
	::= 19296

dpsRTUp18297Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 41 is set"
	::= 18297

dpsRTUp19297Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 41 is cleared"
	::= 19297

dpsRTUp18298Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 42 is set"
	::= 18298

dpsRTUp19298Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 42 is cleared"
	::= 19298

dpsRTUp18299Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 43 is set"
	::= 18299

dpsRTUp19299Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 43 is cleared"
	::= 19299

dpsRTUp18300Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 44 is set"
	::= 18300

dpsRTUp19300Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 44 is cleared"
	::= 19300

dpsRTUp18301Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 45 is set"
	::= 18301

dpsRTUp19301Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 45 is cleared"
	::= 19301

dpsRTUp18302Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 46 is set"
	::= 18302

dpsRTUp19302Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 46 is cleared"
	::= 19302

dpsRTUp18303Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 47 is set"
	::= 18303

dpsRTUp19303Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 47 is cleared"
	::= 19303

dpsRTUp18304Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 48 is set"
	::= 18304

dpsRTUp19304Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 48 is cleared"
	::= 19304

dpsRTUp18305Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 49 is set"
	::= 18305

dpsRTUp19305Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 49 is cleared"
	::= 19305

dpsRTUp18306Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 50 is set"
	::= 18306

dpsRTUp19306Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 50 is cleared"
	::= 19306

dpsRTUp18307Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 51 is set"
	::= 18307

dpsRTUp19307Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 51 is cleared"
	::= 19307

dpsRTUp18308Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 52 is set"
	::= 18308

dpsRTUp19308Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 52 is cleared"
	::= 19308

dpsRTUp18309Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 53 is set"
	::= 18309

dpsRTUp19309Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 53 is cleared"
	::= 19309

dpsRTUp18310Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 54 is set"
	::= 18310

dpsRTUp19310Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 54 is cleared"
	::= 19310

dpsRTUp18311Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 55 is set"
	::= 18311

dpsRTUp19311Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 55 is cleared"
	::= 19311

dpsRTUp18312Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 56 is set"
	::= 18312

dpsRTUp19312Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 56 is cleared"
	::= 19312

dpsRTUp18313Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 57 is set"
	::= 18313

dpsRTUp19313Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 57 is cleared"
	::= 19313

dpsRTUp18314Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 58 is set"
	::= 18314

dpsRTUp19314Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 58 is cleared"
	::= 19314

dpsRTUp18315Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 59 is set"
	::= 18315

dpsRTUp19315Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 59 is cleared"
	::= 19315

dpsRTUp18316Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 60 is set"
	::= 18316

dpsRTUp19316Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 60 is cleared"
	::= 19316

dpsRTUp18317Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 61 is set"
	::= 18317

dpsRTUp19317Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 61 is cleared"
	::= 19317

dpsRTUp18318Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 62 is set"
	::= 18318

dpsRTUp19318Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 62 is cleared"
	::= 19318

dpsRTUp18319Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 63 is set"
	::= 18319

dpsRTUp19319Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 63 is cleared"
	::= 19319

dpsRTUp18320Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 64 is set"
	::= 18320

dpsRTUp19320Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 5 point 64 is cleared"
	::= 19320

dpsRTUp18321Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 1 is set"
	::= 18321

dpsRTUp19321Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 1 is cleared"
	::= 19321

dpsRTUp18322Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 2 is set"
	::= 18322

dpsRTUp19322Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 2 is cleared"
	::= 19322

dpsRTUp18323Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 3 is set"
	::= 18323

dpsRTUp19323Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 3 is cleared"
	::= 19323

dpsRTUp18324Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 4 is set"
	::= 18324

dpsRTUp19324Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 4 is cleared"
	::= 19324

dpsRTUp18325Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 5 is set"
	::= 18325

dpsRTUp19325Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 5 is cleared"
	::= 19325

dpsRTUp18326Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 6 is set"
	::= 18326

dpsRTUp19326Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 6 is cleared"
	::= 19326

dpsRTUp18327Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 7 is set"
	::= 18327

dpsRTUp19327Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 7 is cleared"
	::= 19327

dpsRTUp18328Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 8 is set"
	::= 18328

dpsRTUp19328Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 8 is cleared"
	::= 19328

dpsRTUp18329Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 9 is set"
	::= 18329

dpsRTUp19329Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 9 is cleared"
	::= 19329

dpsRTUp18330Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 10 is set"
	::= 18330

dpsRTUp19330Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 10 is cleared"
	::= 19330

dpsRTUp18331Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 11 is set"
	::= 18331

dpsRTUp19331Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 11 is cleared"
	::= 19331

dpsRTUp18332Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 12 is set"
	::= 18332

dpsRTUp19332Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 12 is cleared"
	::= 19332

dpsRTUp18333Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 13 is set"
	::= 18333

dpsRTUp19333Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 13 is cleared"
	::= 19333

dpsRTUp18334Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 14 is set"
	::= 18334

dpsRTUp19334Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 14 is cleared"
	::= 19334

dpsRTUp18335Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 15 is set"
	::= 18335

dpsRTUp19335Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 15 is cleared"
	::= 19335

dpsRTUp18336Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 16 is set"
	::= 18336

dpsRTUp19336Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 16 is cleared"
	::= 19336

dpsRTUp18337Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 17 is set"
	::= 18337

dpsRTUp19337Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 17 is cleared"
	::= 19337

dpsRTUp18338Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 18 is set"
	::= 18338

dpsRTUp19338Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 18 is cleared"
	::= 19338

dpsRTUp18339Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 19 is set"
	::= 18339

dpsRTUp19339Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 19 is cleared"
	::= 19339

dpsRTUp18340Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 20 is set"
	::= 18340

dpsRTUp19340Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 20 is cleared"
	::= 19340

dpsRTUp18341Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 21 is set"
	::= 18341

dpsRTUp19341Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 21 is cleared"
	::= 19341

dpsRTUp18342Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 22 is set"
	::= 18342

dpsRTUp19342Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 22 is cleared"
	::= 19342

dpsRTUp18343Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 23 is set"
	::= 18343

dpsRTUp19343Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 23 is cleared"
	::= 19343

dpsRTUp18344Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 24 is set"
	::= 18344

dpsRTUp19344Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 24 is cleared"
	::= 19344

dpsRTUp18345Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 25 is set"
	::= 18345

dpsRTUp19345Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 25 is cleared"
	::= 19345

dpsRTUp18346Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 26 is set"
	::= 18346

dpsRTUp19346Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 26 is cleared"
	::= 19346

dpsRTUp18347Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 27 is set"
	::= 18347

dpsRTUp19347Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 27 is cleared"
	::= 19347

dpsRTUp18348Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 28 is set"
	::= 18348

dpsRTUp19348Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 28 is cleared"
	::= 19348

dpsRTUp18349Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 29 is set"
	::= 18349

dpsRTUp19349Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 29 is cleared"
	::= 19349

dpsRTUp18350Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 30 is set"
	::= 18350

dpsRTUp19350Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 30 is cleared"
	::= 19350

dpsRTUp18351Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 31 is set"
	::= 18351

dpsRTUp19351Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 31 is cleared"
	::= 19351

dpsRTUp18352Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 32 is set"
	::= 18352

dpsRTUp19352Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 32 is cleared"
	::= 19352

dpsRTUp18353Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 33 is set"
	::= 18353

dpsRTUp19353Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 33 is cleared"
	::= 19353

dpsRTUp18354Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 34 is set"
	::= 18354

dpsRTUp19354Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 34 is cleared"
	::= 19354

dpsRTUp18355Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 35 is set"
	::= 18355

dpsRTUp19355Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 35 is cleared"
	::= 19355

dpsRTUp18356Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 36 is set"
	::= 18356

dpsRTUp19356Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 36 is cleared"
	::= 19356

dpsRTUp18357Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 37 is set"
	::= 18357

dpsRTUp19357Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 37 is cleared"
	::= 19357

dpsRTUp18358Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 38 is set"
	::= 18358

dpsRTUp19358Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 38 is cleared"
	::= 19358

dpsRTUp18359Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 39 is set"
	::= 18359

dpsRTUp19359Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 39 is cleared"
	::= 19359

dpsRTUp18360Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 40 is set"
	::= 18360

dpsRTUp19360Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 40 is cleared"
	::= 19360

dpsRTUp18361Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 41 is set"
	::= 18361

dpsRTUp19361Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 41 is cleared"
	::= 19361

dpsRTUp18362Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 42 is set"
	::= 18362

dpsRTUp19362Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 42 is cleared"
	::= 19362

dpsRTUp18363Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 43 is set"
	::= 18363

dpsRTUp19363Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 43 is cleared"
	::= 19363

dpsRTUp18364Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 44 is set"
	::= 18364

dpsRTUp19364Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 44 is cleared"
	::= 19364

dpsRTUp18365Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 45 is set"
	::= 18365

dpsRTUp19365Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 45 is cleared"
	::= 19365

dpsRTUp18366Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 46 is set"
	::= 18366

dpsRTUp19366Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 46 is cleared"
	::= 19366

dpsRTUp18367Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 47 is set"
	::= 18367

dpsRTUp19367Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 47 is cleared"
	::= 19367

dpsRTUp18368Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 48 is set"
	::= 18368

dpsRTUp19368Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 48 is cleared"
	::= 19368

dpsRTUp18369Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 49 is set"
	::= 18369

dpsRTUp19369Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 49 is cleared"
	::= 19369

dpsRTUp18370Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 50 is set"
	::= 18370

dpsRTUp19370Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 50 is cleared"
	::= 19370

dpsRTUp18371Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 51 is set"
	::= 18371

dpsRTUp19371Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 51 is cleared"
	::= 19371

dpsRTUp18372Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 52 is set"
	::= 18372

dpsRTUp19372Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 52 is cleared"
	::= 19372

dpsRTUp18373Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 53 is set"
	::= 18373

dpsRTUp19373Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 53 is cleared"
	::= 19373

dpsRTUp18374Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 54 is set"
	::= 18374

dpsRTUp19374Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 54 is cleared"
	::= 19374

dpsRTUp18375Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 55 is set"
	::= 18375

dpsRTUp19375Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 55 is cleared"
	::= 19375

dpsRTUp18376Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 56 is set"
	::= 18376

dpsRTUp19376Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 56 is cleared"
	::= 19376

dpsRTUp18377Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 57 is set"
	::= 18377

dpsRTUp19377Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 57 is cleared"
	::= 19377

dpsRTUp18378Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 58 is set"
	::= 18378

dpsRTUp19378Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 58 is cleared"
	::= 19378

dpsRTUp18379Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 59 is set"
	::= 18379

dpsRTUp19379Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 59 is cleared"
	::= 19379

dpsRTUp18380Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 60 is set"
	::= 18380

dpsRTUp19380Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 60 is cleared"
	::= 19380

dpsRTUp18381Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 61 is set"
	::= 18381

dpsRTUp19381Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 61 is cleared"
	::= 19381

dpsRTUp18382Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 62 is set"
	::= 18382

dpsRTUp19382Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 62 is cleared"
	::= 19382

dpsRTUp18383Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 63 is set"
	::= 18383

dpsRTUp19383Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 63 is cleared"
	::= 19383

dpsRTUp18384Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 64 is set"
	::= 18384

dpsRTUp19384Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 6 point 64 is cleared"
	::= 19384

dpsRTUp18385Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 1 is set"
	::= 18385

dpsRTUp19385Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 1 is cleared"
	::= 19385

dpsRTUp18386Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 2 is set"
	::= 18386

dpsRTUp19386Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 2 is cleared"
	::= 19386

dpsRTUp18387Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 3 is set"
	::= 18387

dpsRTUp19387Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 3 is cleared"
	::= 19387

dpsRTUp18388Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 4 is set"
	::= 18388

dpsRTUp19388Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 4 is cleared"
	::= 19388

dpsRTUp18389Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 5 is set"
	::= 18389

dpsRTUp19389Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 5 is cleared"
	::= 19389

dpsRTUp18390Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 6 is set"
	::= 18390

dpsRTUp19390Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 6 is cleared"
	::= 19390

dpsRTUp18391Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 7 is set"
	::= 18391

dpsRTUp19391Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 7 is cleared"
	::= 19391

dpsRTUp18392Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 8 is set"
	::= 18392

dpsRTUp19392Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 8 is cleared"
	::= 19392

dpsRTUp18393Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 9 is set"
	::= 18393

dpsRTUp19393Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 9 is cleared"
	::= 19393

dpsRTUp18394Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 10 is set"
	::= 18394

dpsRTUp19394Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 10 is cleared"
	::= 19394

dpsRTUp18395Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 11 is set"
	::= 18395

dpsRTUp19395Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 11 is cleared"
	::= 19395

dpsRTUp18396Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 12 is set"
	::= 18396

dpsRTUp19396Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 12 is cleared"
	::= 19396

dpsRTUp18397Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 13 is set"
	::= 18397

dpsRTUp19397Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 13 is cleared"
	::= 19397

dpsRTUp18398Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 14 is set"
	::= 18398

dpsRTUp19398Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 14 is cleared"
	::= 19398

dpsRTUp18399Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 15 is set"
	::= 18399

dpsRTUp19399Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 15 is cleared"
	::= 19399

dpsRTUp18400Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 16 is set"
	::= 18400

dpsRTUp19400Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 16 is cleared"
	::= 19400

dpsRTUp18401Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 17 is set"
	::= 18401

dpsRTUp19401Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 17 is cleared"
	::= 19401

dpsRTUp18402Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 18 is set"
	::= 18402

dpsRTUp19402Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 18 is cleared"
	::= 19402

dpsRTUp18403Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 19 is set"
	::= 18403

dpsRTUp19403Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 19 is cleared"
	::= 19403

dpsRTUp18404Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 20 is set"
	::= 18404

dpsRTUp19404Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 20 is cleared"
	::= 19404

dpsRTUp18405Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 21 is set"
	::= 18405

dpsRTUp19405Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 21 is cleared"
	::= 19405

dpsRTUp18406Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 22 is set"
	::= 18406

dpsRTUp19406Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 22 is cleared"
	::= 19406

dpsRTUp18407Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 23 is set"
	::= 18407

dpsRTUp19407Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 23 is cleared"
	::= 19407

dpsRTUp18408Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 24 is set"
	::= 18408

dpsRTUp19408Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 24 is cleared"
	::= 19408

dpsRTUp18409Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 25 is set"
	::= 18409

dpsRTUp19409Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 25 is cleared"
	::= 19409

dpsRTUp18410Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 26 is set"
	::= 18410

dpsRTUp19410Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 26 is cleared"
	::= 19410

dpsRTUp18411Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 27 is set"
	::= 18411

dpsRTUp19411Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 27 is cleared"
	::= 19411

dpsRTUp18412Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 28 is set"
	::= 18412

dpsRTUp19412Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 28 is cleared"
	::= 19412

dpsRTUp18413Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 29 is set"
	::= 18413

dpsRTUp19413Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 29 is cleared"
	::= 19413

dpsRTUp18414Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 30 is set"
	::= 18414

dpsRTUp19414Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 30 is cleared"
	::= 19414

dpsRTUp18415Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 31 is set"
	::= 18415

dpsRTUp19415Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 31 is cleared"
	::= 19415

dpsRTUp18416Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 32 is set"
	::= 18416

dpsRTUp19416Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 32 is cleared"
	::= 19416

dpsRTUp18417Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 33 is set"
	::= 18417

dpsRTUp19417Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 33 is cleared"
	::= 19417

dpsRTUp18418Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 34 is set"
	::= 18418

dpsRTUp19418Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 34 is cleared"
	::= 19418

dpsRTUp18419Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 35 is set"
	::= 18419

dpsRTUp19419Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 35 is cleared"
	::= 19419

dpsRTUp18420Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 36 is set"
	::= 18420

dpsRTUp19420Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 36 is cleared"
	::= 19420

dpsRTUp18421Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 37 is set"
	::= 18421

dpsRTUp19421Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 37 is cleared"
	::= 19421

dpsRTUp18422Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 38 is set"
	::= 18422

dpsRTUp19422Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 38 is cleared"
	::= 19422

dpsRTUp18423Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 39 is set"
	::= 18423

dpsRTUp19423Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 39 is cleared"
	::= 19423

dpsRTUp18424Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 40 is set"
	::= 18424

dpsRTUp19424Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 40 is cleared"
	::= 19424

dpsRTUp18425Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 41 is set"
	::= 18425

dpsRTUp19425Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 41 is cleared"
	::= 19425

dpsRTUp18426Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 42 is set"
	::= 18426

dpsRTUp19426Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 42 is cleared"
	::= 19426

dpsRTUp18427Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 43 is set"
	::= 18427

dpsRTUp19427Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 43 is cleared"
	::= 19427

dpsRTUp18428Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 44 is set"
	::= 18428

dpsRTUp19428Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 44 is cleared"
	::= 19428

dpsRTUp18429Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 45 is set"
	::= 18429

dpsRTUp19429Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 45 is cleared"
	::= 19429

dpsRTUp18430Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 46 is set"
	::= 18430

dpsRTUp19430Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 46 is cleared"
	::= 19430

dpsRTUp18431Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 47 is set"
	::= 18431

dpsRTUp19431Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 47 is cleared"
	::= 19431

dpsRTUp18432Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 48 is set"
	::= 18432

dpsRTUp19432Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 48 is cleared"
	::= 19432

dpsRTUp18433Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 49 is set"
	::= 18433

dpsRTUp19433Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 49 is cleared"
	::= 19433

dpsRTUp18434Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 50 is set"
	::= 18434

dpsRTUp19434Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 50 is cleared"
	::= 19434

dpsRTUp18435Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 51 is set"
	::= 18435

dpsRTUp19435Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 51 is cleared"
	::= 19435

dpsRTUp18436Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 52 is set"
	::= 18436

dpsRTUp19436Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 52 is cleared"
	::= 19436

dpsRTUp18437Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 53 is set"
	::= 18437

dpsRTUp19437Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 53 is cleared"
	::= 19437

dpsRTUp18438Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 54 is set"
	::= 18438

dpsRTUp19438Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 54 is cleared"
	::= 19438

dpsRTUp18439Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 55 is set"
	::= 18439

dpsRTUp19439Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 55 is cleared"
	::= 19439

dpsRTUp18440Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 56 is set"
	::= 18440

dpsRTUp19440Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 56 is cleared"
	::= 19440

dpsRTUp18441Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 57 is set"
	::= 18441

dpsRTUp19441Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 57 is cleared"
	::= 19441

dpsRTUp18442Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 58 is set"
	::= 18442

dpsRTUp19442Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 58 is cleared"
	::= 19442

dpsRTUp18443Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 59 is set"
	::= 18443

dpsRTUp19443Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 59 is cleared"
	::= 19443

dpsRTUp18444Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 60 is set"
	::= 18444

dpsRTUp19444Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 60 is cleared"
	::= 19444

dpsRTUp18445Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 61 is set"
	::= 18445

dpsRTUp19445Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 61 is cleared"
	::= 19445

dpsRTUp18446Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 62 is set"
	::= 18446

dpsRTUp19446Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 62 is cleared"
	::= 19446

dpsRTUp18447Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 63 is set"
	::= 18447

dpsRTUp19447Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 63 is cleared"
	::= 19447

dpsRTUp18448Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 64 is set"
	::= 18448

dpsRTUp19448Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 7 point 64 is cleared"
	::= 19448

dpsRTUp18449Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 1 is set"
	::= 18449

dpsRTUp19449Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 1 is cleared"
	::= 19449

dpsRTUp18450Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 2 is set"
	::= 18450

dpsRTUp19450Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 2 is cleared"
	::= 19450

dpsRTUp18451Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 3 is set"
	::= 18451

dpsRTUp19451Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 3 is cleared"
	::= 19451

dpsRTUp18452Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 4 is set"
	::= 18452

dpsRTUp19452Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 4 is cleared"
	::= 19452

dpsRTUp18453Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 5 is set"
	::= 18453

dpsRTUp19453Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 5 is cleared"
	::= 19453

dpsRTUp18454Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 6 is set"
	::= 18454

dpsRTUp19454Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 6 is cleared"
	::= 19454

dpsRTUp18455Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 7 is set"
	::= 18455

dpsRTUp19455Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 7 is cleared"
	::= 19455

dpsRTUp18456Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 8 is set"
	::= 18456

dpsRTUp19456Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 8 is cleared"
	::= 19456

dpsRTUp18457Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 9 is set"
	::= 18457

dpsRTUp19457Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 9 is cleared"
	::= 19457

dpsRTUp18458Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 10 is set"
	::= 18458

dpsRTUp19458Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 10 is cleared"
	::= 19458

dpsRTUp18459Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 11 is set"
	::= 18459

dpsRTUp19459Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 11 is cleared"
	::= 19459

dpsRTUp18460Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 12 is set"
	::= 18460

dpsRTUp19460Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 12 is cleared"
	::= 19460

dpsRTUp18461Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 13 is set"
	::= 18461

dpsRTUp19461Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 13 is cleared"
	::= 19461

dpsRTUp18462Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 14 is set"
	::= 18462

dpsRTUp19462Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 14 is cleared"
	::= 19462

dpsRTUp18463Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 15 is set"
	::= 18463

dpsRTUp19463Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 15 is cleared"
	::= 19463

dpsRTUp18464Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 16 is set"
	::= 18464

dpsRTUp19464Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 16 is cleared"
	::= 19464

dpsRTUp18465Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 17 is set"
	::= 18465

dpsRTUp19465Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 17 is cleared"
	::= 19465

dpsRTUp18466Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 18 is set"
	::= 18466

dpsRTUp19466Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 18 is cleared"
	::= 19466

dpsRTUp18467Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 19 is set"
	::= 18467

dpsRTUp19467Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 19 is cleared"
	::= 19467

dpsRTUp18468Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 20 is set"
	::= 18468

dpsRTUp19468Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 20 is cleared"
	::= 19468

dpsRTUp18469Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 21 is set"
	::= 18469

dpsRTUp19469Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 21 is cleared"
	::= 19469

dpsRTUp18470Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 22 is set"
	::= 18470

dpsRTUp19470Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 22 is cleared"
	::= 19470

dpsRTUp18471Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 23 is set"
	::= 18471

dpsRTUp19471Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 23 is cleared"
	::= 19471

dpsRTUp18472Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 24 is set"
	::= 18472

dpsRTUp19472Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 24 is cleared"
	::= 19472

dpsRTUp18473Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 25 is set"
	::= 18473

dpsRTUp19473Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 25 is cleared"
	::= 19473

dpsRTUp18474Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 26 is set"
	::= 18474

dpsRTUp19474Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 26 is cleared"
	::= 19474

dpsRTUp18475Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 27 is set"
	::= 18475

dpsRTUp19475Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 27 is cleared"
	::= 19475

dpsRTUp18476Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 28 is set"
	::= 18476

dpsRTUp19476Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 28 is cleared"
	::= 19476

dpsRTUp18477Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 29 is set"
	::= 18477

dpsRTUp19477Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 29 is cleared"
	::= 19477

dpsRTUp18478Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 30 is set"
	::= 18478

dpsRTUp19478Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 30 is cleared"
	::= 19478

dpsRTUp18479Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 31 is set"
	::= 18479

dpsRTUp19479Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 31 is cleared"
	::= 19479

dpsRTUp18480Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 32 is set"
	::= 18480

dpsRTUp19480Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 32 is cleared"
	::= 19480

dpsRTUp18481Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 33 is set"
	::= 18481

dpsRTUp19481Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 33 is cleared"
	::= 19481

dpsRTUp18482Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 34 is set"
	::= 18482

dpsRTUp19482Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 34 is cleared"
	::= 19482

dpsRTUp18483Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 35 is set"
	::= 18483

dpsRTUp19483Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 35 is cleared"
	::= 19483

dpsRTUp18484Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 36 is set"
	::= 18484

dpsRTUp19484Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 36 is cleared"
	::= 19484

dpsRTUp18485Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 37 is set"
	::= 18485

dpsRTUp19485Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 37 is cleared"
	::= 19485

dpsRTUp18486Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 38 is set"
	::= 18486

dpsRTUp19486Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 38 is cleared"
	::= 19486

dpsRTUp18487Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 39 is set"
	::= 18487

dpsRTUp19487Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 39 is cleared"
	::= 19487

dpsRTUp18488Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 40 is set"
	::= 18488

dpsRTUp19488Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 40 is cleared"
	::= 19488

dpsRTUp18489Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 41 is set"
	::= 18489

dpsRTUp19489Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 41 is cleared"
	::= 19489

dpsRTUp18490Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 42 is set"
	::= 18490

dpsRTUp19490Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 42 is cleared"
	::= 19490

dpsRTUp18491Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 43 is set"
	::= 18491

dpsRTUp19491Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 43 is cleared"
	::= 19491

dpsRTUp18492Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 44 is set"
	::= 18492

dpsRTUp19492Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 44 is cleared"
	::= 19492

dpsRTUp18493Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 45 is set"
	::= 18493

dpsRTUp19493Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 45 is cleared"
	::= 19493

dpsRTUp18494Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 46 is set"
	::= 18494

dpsRTUp19494Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 46 is cleared"
	::= 19494

dpsRTUp18495Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 47 is set"
	::= 18495

dpsRTUp19495Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 47 is cleared"
	::= 19495

dpsRTUp18496Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 48 is set"
	::= 18496

dpsRTUp19496Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 48 is cleared"
	::= 19496

dpsRTUp18497Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 49 is set"
	::= 18497

dpsRTUp19497Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 49 is cleared"
	::= 19497

dpsRTUp18498Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 50 is set"
	::= 18498

dpsRTUp19498Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 50 is cleared"
	::= 19498

dpsRTUp18499Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 51 is set"
	::= 18499

dpsRTUp19499Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 51 is cleared"
	::= 19499

dpsRTUp18500Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 52 is set"
	::= 18500

dpsRTUp19500Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 52 is cleared"
	::= 19500

dpsRTUp18501Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 53 is set"
	::= 18501

dpsRTUp19501Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 53 is cleared"
	::= 19501

dpsRTUp18502Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 54 is set"
	::= 18502

dpsRTUp19502Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 54 is cleared"
	::= 19502

dpsRTUp18503Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 55 is set"
	::= 18503

dpsRTUp19503Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 55 is cleared"
	::= 19503

dpsRTUp18504Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 56 is set"
	::= 18504

dpsRTUp19504Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 56 is cleared"
	::= 19504

dpsRTUp18505Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 57 is set"
	::= 18505

dpsRTUp19505Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 57 is cleared"
	::= 19505

dpsRTUp18506Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 58 is set"
	::= 18506

dpsRTUp19506Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 58 is cleared"
	::= 19506

dpsRTUp18507Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 59 is set"
	::= 18507

dpsRTUp19507Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 59 is cleared"
	::= 19507

dpsRTUp18508Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 60 is set"
	::= 18508

dpsRTUp19508Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 60 is cleared"
	::= 19508

dpsRTUp18509Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 61 is set"
	::= 18509

dpsRTUp19509Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 61 is cleared"
	::= 19509

dpsRTUp18510Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 62 is set"
	::= 18510

dpsRTUp19510Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 62 is cleared"
	::= 19510

dpsRTUp18511Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 63 is set"
	::= 18511

dpsRTUp19511Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 63 is cleared"
	::= 19511

dpsRTUp18512Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 64 is set"
	::= 18512

dpsRTUp19512Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 5 display 8 point 64 is cleared"
	::= 19512

dpsRTUp20001Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 1 is set"
	::= 20001

dpsRTUp21001Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 1 is cleared"
	::= 21001

dpsRTUp20002Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 2 is set"
	::= 20002

dpsRTUp21002Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 2 is cleared"
	::= 21002

dpsRTUp20003Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 3 is set"
	::= 20003

dpsRTUp21003Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 3 is cleared"
	::= 21003

dpsRTUp20004Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 4 is set"
	::= 20004

dpsRTUp21004Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 4 is cleared"
	::= 21004

dpsRTUp20005Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 5 is set"
	::= 20005

dpsRTUp21005Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 5 is cleared"
	::= 21005

dpsRTUp20006Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 6 is set"
	::= 20006

dpsRTUp21006Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 6 is cleared"
	::= 21006

dpsRTUp20007Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 7 is set"
	::= 20007

dpsRTUp21007Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 7 is cleared"
	::= 21007

dpsRTUp20008Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 8 is set"
	::= 20008

dpsRTUp21008Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 8 is cleared"
	::= 21008

dpsRTUp20009Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 9 is set"
	::= 20009

dpsRTUp21009Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 9 is cleared"
	::= 21009

dpsRTUp20010Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 10 is set"
	::= 20010

dpsRTUp21010Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 10 is cleared"
	::= 21010

dpsRTUp20011Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 11 is set"
	::= 20011

dpsRTUp21011Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 11 is cleared"
	::= 21011

dpsRTUp20012Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 12 is set"
	::= 20012

dpsRTUp21012Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 12 is cleared"
	::= 21012

dpsRTUp20013Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 13 is set"
	::= 20013

dpsRTUp21013Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 13 is cleared"
	::= 21013

dpsRTUp20014Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 14 is set"
	::= 20014

dpsRTUp21014Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 14 is cleared"
	::= 21014

dpsRTUp20015Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 15 is set"
	::= 20015

dpsRTUp21015Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 15 is cleared"
	::= 21015

dpsRTUp20016Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 16 is set"
	::= 20016

dpsRTUp21016Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 16 is cleared"
	::= 21016

dpsRTUp20017Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 17 is set"
	::= 20017

dpsRTUp21017Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 17 is cleared"
	::= 21017

dpsRTUp20018Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 18 is set"
	::= 20018

dpsRTUp21018Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 18 is cleared"
	::= 21018

dpsRTUp20019Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 19 is set"
	::= 20019

dpsRTUp21019Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 19 is cleared"
	::= 21019

dpsRTUp20020Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 20 is set"
	::= 20020

dpsRTUp21020Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 20 is cleared"
	::= 21020

dpsRTUp20021Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 21 is set"
	::= 20021

dpsRTUp21021Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 21 is cleared"
	::= 21021

dpsRTUp20022Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 22 is set"
	::= 20022

dpsRTUp21022Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 22 is cleared"
	::= 21022

dpsRTUp20023Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 23 is set"
	::= 20023

dpsRTUp21023Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 23 is cleared"
	::= 21023

dpsRTUp20024Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 24 is set"
	::= 20024

dpsRTUp21024Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 24 is cleared"
	::= 21024

dpsRTUp20025Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 25 is set"
	::= 20025

dpsRTUp21025Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 25 is cleared"
	::= 21025

dpsRTUp20026Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 26 is set"
	::= 20026

dpsRTUp21026Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 26 is cleared"
	::= 21026

dpsRTUp20027Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 27 is set"
	::= 20027

dpsRTUp21027Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 27 is cleared"
	::= 21027

dpsRTUp20028Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 28 is set"
	::= 20028

dpsRTUp21028Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 28 is cleared"
	::= 21028

dpsRTUp20029Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 29 is set"
	::= 20029

dpsRTUp21029Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 29 is cleared"
	::= 21029

dpsRTUp20030Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 30 is set"
	::= 20030

dpsRTUp21030Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 30 is cleared"
	::= 21030

dpsRTUp20031Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 31 is set"
	::= 20031

dpsRTUp21031Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 31 is cleared"
	::= 21031

dpsRTUp20032Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 32 is set"
	::= 20032

dpsRTUp21032Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 32 is cleared"
	::= 21032

dpsRTUp20033Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 33 is set"
	::= 20033

dpsRTUp21033Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 33 is cleared"
	::= 21033

dpsRTUp20034Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 34 is set"
	::= 20034

dpsRTUp21034Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 34 is cleared"
	::= 21034

dpsRTUp20035Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 35 is set"
	::= 20035

dpsRTUp21035Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 35 is cleared"
	::= 21035

dpsRTUp20036Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 36 is set"
	::= 20036

dpsRTUp21036Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 36 is cleared"
	::= 21036

dpsRTUp20037Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 37 is set"
	::= 20037

dpsRTUp21037Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 37 is cleared"
	::= 21037

dpsRTUp20038Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 38 is set"
	::= 20038

dpsRTUp21038Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 38 is cleared"
	::= 21038

dpsRTUp20039Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 39 is set"
	::= 20039

dpsRTUp21039Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 39 is cleared"
	::= 21039

dpsRTUp20040Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 40 is set"
	::= 20040

dpsRTUp21040Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 40 is cleared"
	::= 21040

dpsRTUp20041Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 41 is set"
	::= 20041

dpsRTUp21041Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 41 is cleared"
	::= 21041

dpsRTUp20042Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 42 is set"
	::= 20042

dpsRTUp21042Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 42 is cleared"
	::= 21042

dpsRTUp20043Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 43 is set"
	::= 20043

dpsRTUp21043Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 43 is cleared"
	::= 21043

dpsRTUp20044Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 44 is set"
	::= 20044

dpsRTUp21044Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 44 is cleared"
	::= 21044

dpsRTUp20045Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 45 is set"
	::= 20045

dpsRTUp21045Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 45 is cleared"
	::= 21045

dpsRTUp20046Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 46 is set"
	::= 20046

dpsRTUp21046Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 46 is cleared"
	::= 21046

dpsRTUp20047Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 47 is set"
	::= 20047

dpsRTUp21047Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 47 is cleared"
	::= 21047

dpsRTUp20048Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 48 is set"
	::= 20048

dpsRTUp21048Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 48 is cleared"
	::= 21048

dpsRTUp20049Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 49 is set"
	::= 20049

dpsRTUp21049Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 49 is cleared"
	::= 21049

dpsRTUp20050Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 50 is set"
	::= 20050

dpsRTUp21050Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 50 is cleared"
	::= 21050

dpsRTUp20051Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 51 is set"
	::= 20051

dpsRTUp21051Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 51 is cleared"
	::= 21051

dpsRTUp20052Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 52 is set"
	::= 20052

dpsRTUp21052Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 52 is cleared"
	::= 21052

dpsRTUp20053Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 53 is set"
	::= 20053

dpsRTUp21053Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 53 is cleared"
	::= 21053

dpsRTUp20054Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 54 is set"
	::= 20054

dpsRTUp21054Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 54 is cleared"
	::= 21054

dpsRTUp20055Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 55 is set"
	::= 20055

dpsRTUp21055Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 55 is cleared"
	::= 21055

dpsRTUp20056Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 56 is set"
	::= 20056

dpsRTUp21056Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 56 is cleared"
	::= 21056

dpsRTUp20057Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 57 is set"
	::= 20057

dpsRTUp21057Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 57 is cleared"
	::= 21057

dpsRTUp20058Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 58 is set"
	::= 20058

dpsRTUp21058Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 58 is cleared"
	::= 21058

dpsRTUp20059Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 59 is set"
	::= 20059

dpsRTUp21059Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 59 is cleared"
	::= 21059

dpsRTUp20060Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 60 is set"
	::= 20060

dpsRTUp21060Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 60 is cleared"
	::= 21060

dpsRTUp20061Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 61 is set"
	::= 20061

dpsRTUp21061Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 61 is cleared"
	::= 21061

dpsRTUp20062Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 62 is set"
	::= 20062

dpsRTUp21062Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 62 is cleared"
	::= 21062

dpsRTUp20063Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 63 is set"
	::= 20063

dpsRTUp21063Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 63 is cleared"
	::= 21063

dpsRTUp20064Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 64 is set"
	::= 20064

dpsRTUp21064Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 1 point 64 is cleared"
	::= 21064

dpsRTUp20065Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 1 is set"
	::= 20065

dpsRTUp21065Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 1 is cleared"
	::= 21065

dpsRTUp20066Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 2 is set"
	::= 20066

dpsRTUp21066Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 2 is cleared"
	::= 21066

dpsRTUp20067Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 3 is set"
	::= 20067

dpsRTUp21067Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 3 is cleared"
	::= 21067

dpsRTUp20068Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 4 is set"
	::= 20068

dpsRTUp21068Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 4 is cleared"
	::= 21068

dpsRTUp20069Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 5 is set"
	::= 20069

dpsRTUp21069Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 5 is cleared"
	::= 21069

dpsRTUp20070Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 6 is set"
	::= 20070

dpsRTUp21070Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 6 is cleared"
	::= 21070

dpsRTUp20071Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 7 is set"
	::= 20071

dpsRTUp21071Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 7 is cleared"
	::= 21071

dpsRTUp20072Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 8 is set"
	::= 20072

dpsRTUp21072Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 8 is cleared"
	::= 21072

dpsRTUp20073Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 9 is set"
	::= 20073

dpsRTUp21073Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 9 is cleared"
	::= 21073

dpsRTUp20074Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 10 is set"
	::= 20074

dpsRTUp21074Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 10 is cleared"
	::= 21074

dpsRTUp20075Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 11 is set"
	::= 20075

dpsRTUp21075Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 11 is cleared"
	::= 21075

dpsRTUp20076Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 12 is set"
	::= 20076

dpsRTUp21076Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 12 is cleared"
	::= 21076

dpsRTUp20077Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 13 is set"
	::= 20077

dpsRTUp21077Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 13 is cleared"
	::= 21077

dpsRTUp20078Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 14 is set"
	::= 20078

dpsRTUp21078Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 14 is cleared"
	::= 21078

dpsRTUp20079Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 15 is set"
	::= 20079

dpsRTUp21079Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 15 is cleared"
	::= 21079

dpsRTUp20080Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 16 is set"
	::= 20080

dpsRTUp21080Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 16 is cleared"
	::= 21080

dpsRTUp20081Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 17 is set"
	::= 20081

dpsRTUp21081Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 17 is cleared"
	::= 21081

dpsRTUp20082Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 18 is set"
	::= 20082

dpsRTUp21082Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 18 is cleared"
	::= 21082

dpsRTUp20083Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 19 is set"
	::= 20083

dpsRTUp21083Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 19 is cleared"
	::= 21083

dpsRTUp20084Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 20 is set"
	::= 20084

dpsRTUp21084Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 20 is cleared"
	::= 21084

dpsRTUp20085Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 21 is set"
	::= 20085

dpsRTUp21085Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 21 is cleared"
	::= 21085

dpsRTUp20086Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 22 is set"
	::= 20086

dpsRTUp21086Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 22 is cleared"
	::= 21086

dpsRTUp20087Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 23 is set"
	::= 20087

dpsRTUp21087Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 23 is cleared"
	::= 21087

dpsRTUp20088Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 24 is set"
	::= 20088

dpsRTUp21088Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 24 is cleared"
	::= 21088

dpsRTUp20089Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 25 is set"
	::= 20089

dpsRTUp21089Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 25 is cleared"
	::= 21089

dpsRTUp20090Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 26 is set"
	::= 20090

dpsRTUp21090Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 26 is cleared"
	::= 21090

dpsRTUp20091Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 27 is set"
	::= 20091

dpsRTUp21091Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 27 is cleared"
	::= 21091

dpsRTUp20092Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 28 is set"
	::= 20092

dpsRTUp21092Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 28 is cleared"
	::= 21092

dpsRTUp20093Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 29 is set"
	::= 20093

dpsRTUp21093Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 29 is cleared"
	::= 21093

dpsRTUp20094Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 30 is set"
	::= 20094

dpsRTUp21094Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 30 is cleared"
	::= 21094

dpsRTUp20095Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 31 is set"
	::= 20095

dpsRTUp21095Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 31 is cleared"
	::= 21095

dpsRTUp20096Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 32 is set"
	::= 20096

dpsRTUp21096Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 32 is cleared"
	::= 21096

dpsRTUp20097Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 33 is set"
	::= 20097

dpsRTUp21097Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 33 is cleared"
	::= 21097

dpsRTUp20098Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 34 is set"
	::= 20098

dpsRTUp21098Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 34 is cleared"
	::= 21098

dpsRTUp20099Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 35 is set"
	::= 20099

dpsRTUp21099Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 35 is cleared"
	::= 21099

dpsRTUp20100Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 36 is set"
	::= 20100

dpsRTUp21100Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 36 is cleared"
	::= 21100

dpsRTUp20101Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 37 is set"
	::= 20101

dpsRTUp21101Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 37 is cleared"
	::= 21101

dpsRTUp20102Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 38 is set"
	::= 20102

dpsRTUp21102Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 38 is cleared"
	::= 21102

dpsRTUp20103Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 39 is set"
	::= 20103

dpsRTUp21103Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 39 is cleared"
	::= 21103

dpsRTUp20104Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 40 is set"
	::= 20104

dpsRTUp21104Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 40 is cleared"
	::= 21104

dpsRTUp20105Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 41 is set"
	::= 20105

dpsRTUp21105Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 41 is cleared"
	::= 21105

dpsRTUp20106Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 42 is set"
	::= 20106

dpsRTUp21106Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 42 is cleared"
	::= 21106

dpsRTUp20107Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 43 is set"
	::= 20107

dpsRTUp21107Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 43 is cleared"
	::= 21107

dpsRTUp20108Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 44 is set"
	::= 20108

dpsRTUp21108Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 44 is cleared"
	::= 21108

dpsRTUp20109Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 45 is set"
	::= 20109

dpsRTUp21109Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 45 is cleared"
	::= 21109

dpsRTUp20110Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 46 is set"
	::= 20110

dpsRTUp21110Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 46 is cleared"
	::= 21110

dpsRTUp20111Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 47 is set"
	::= 20111

dpsRTUp21111Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 47 is cleared"
	::= 21111

dpsRTUp20112Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 48 is set"
	::= 20112

dpsRTUp21112Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 48 is cleared"
	::= 21112

dpsRTUp20113Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 49 is set"
	::= 20113

dpsRTUp21113Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 49 is cleared"
	::= 21113

dpsRTUp20114Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 50 is set"
	::= 20114

dpsRTUp21114Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 50 is cleared"
	::= 21114

dpsRTUp20115Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 51 is set"
	::= 20115

dpsRTUp21115Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 51 is cleared"
	::= 21115

dpsRTUp20116Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 52 is set"
	::= 20116

dpsRTUp21116Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 52 is cleared"
	::= 21116

dpsRTUp20117Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 53 is set"
	::= 20117

dpsRTUp21117Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 53 is cleared"
	::= 21117

dpsRTUp20118Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 54 is set"
	::= 20118

dpsRTUp21118Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 54 is cleared"
	::= 21118

dpsRTUp20119Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 55 is set"
	::= 20119

dpsRTUp21119Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 55 is cleared"
	::= 21119

dpsRTUp20120Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 56 is set"
	::= 20120

dpsRTUp21120Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 56 is cleared"
	::= 21120

dpsRTUp20121Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 57 is set"
	::= 20121

dpsRTUp21121Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 57 is cleared"
	::= 21121

dpsRTUp20122Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 58 is set"
	::= 20122

dpsRTUp21122Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 58 is cleared"
	::= 21122

dpsRTUp20123Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 59 is set"
	::= 20123

dpsRTUp21123Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 59 is cleared"
	::= 21123

dpsRTUp20124Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 60 is set"
	::= 20124

dpsRTUp21124Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 60 is cleared"
	::= 21124

dpsRTUp20125Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 61 is set"
	::= 20125

dpsRTUp21125Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 61 is cleared"
	::= 21125

dpsRTUp20126Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 62 is set"
	::= 20126

dpsRTUp21126Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 62 is cleared"
	::= 21126

dpsRTUp20127Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 63 is set"
	::= 20127

dpsRTUp21127Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 63 is cleared"
	::= 21127

dpsRTUp20128Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 64 is set"
	::= 20128

dpsRTUp21128Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 2 point 64 is cleared"
	::= 21128

dpsRTUp20129Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 1 is set"
	::= 20129

dpsRTUp21129Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 1 is cleared"
	::= 21129

dpsRTUp20130Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 2 is set"
	::= 20130

dpsRTUp21130Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 2 is cleared"
	::= 21130

dpsRTUp20131Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 3 is set"
	::= 20131

dpsRTUp21131Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 3 is cleared"
	::= 21131

dpsRTUp20132Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 4 is set"
	::= 20132

dpsRTUp21132Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 4 is cleared"
	::= 21132

dpsRTUp20133Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 5 is set"
	::= 20133

dpsRTUp21133Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 5 is cleared"
	::= 21133

dpsRTUp20134Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 6 is set"
	::= 20134

dpsRTUp21134Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 6 is cleared"
	::= 21134

dpsRTUp20135Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 7 is set"
	::= 20135

dpsRTUp21135Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 7 is cleared"
	::= 21135

dpsRTUp20136Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 8 is set"
	::= 20136

dpsRTUp21136Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 8 is cleared"
	::= 21136

dpsRTUp20137Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 9 is set"
	::= 20137

dpsRTUp21137Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 9 is cleared"
	::= 21137

dpsRTUp20138Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 10 is set"
	::= 20138

dpsRTUp21138Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 10 is cleared"
	::= 21138

dpsRTUp20139Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 11 is set"
	::= 20139

dpsRTUp21139Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 11 is cleared"
	::= 21139

dpsRTUp20140Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 12 is set"
	::= 20140

dpsRTUp21140Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 12 is cleared"
	::= 21140

dpsRTUp20141Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 13 is set"
	::= 20141

dpsRTUp21141Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 13 is cleared"
	::= 21141

dpsRTUp20142Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 14 is set"
	::= 20142

dpsRTUp21142Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 14 is cleared"
	::= 21142

dpsRTUp20143Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 15 is set"
	::= 20143

dpsRTUp21143Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 15 is cleared"
	::= 21143

dpsRTUp20144Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 16 is set"
	::= 20144

dpsRTUp21144Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 16 is cleared"
	::= 21144

dpsRTUp20145Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 17 is set"
	::= 20145

dpsRTUp21145Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 17 is cleared"
	::= 21145

dpsRTUp20146Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 18 is set"
	::= 20146

dpsRTUp21146Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 18 is cleared"
	::= 21146

dpsRTUp20147Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 19 is set"
	::= 20147

dpsRTUp21147Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 19 is cleared"
	::= 21147

dpsRTUp20148Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 20 is set"
	::= 20148

dpsRTUp21148Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 20 is cleared"
	::= 21148

dpsRTUp20149Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 21 is set"
	::= 20149

dpsRTUp21149Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 21 is cleared"
	::= 21149

dpsRTUp20150Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 22 is set"
	::= 20150

dpsRTUp21150Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 22 is cleared"
	::= 21150

dpsRTUp20151Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 23 is set"
	::= 20151

dpsRTUp21151Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 23 is cleared"
	::= 21151

dpsRTUp20152Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 24 is set"
	::= 20152

dpsRTUp21152Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 24 is cleared"
	::= 21152

dpsRTUp20153Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 25 is set"
	::= 20153

dpsRTUp21153Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 25 is cleared"
	::= 21153

dpsRTUp20154Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 26 is set"
	::= 20154

dpsRTUp21154Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 26 is cleared"
	::= 21154

dpsRTUp20155Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 27 is set"
	::= 20155

dpsRTUp21155Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 27 is cleared"
	::= 21155

dpsRTUp20156Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 28 is set"
	::= 20156

dpsRTUp21156Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 28 is cleared"
	::= 21156

dpsRTUp20157Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 29 is set"
	::= 20157

dpsRTUp21157Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 29 is cleared"
	::= 21157

dpsRTUp20158Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 30 is set"
	::= 20158

dpsRTUp21158Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 30 is cleared"
	::= 21158

dpsRTUp20159Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 31 is set"
	::= 20159

dpsRTUp21159Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 31 is cleared"
	::= 21159

dpsRTUp20160Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 32 is set"
	::= 20160

dpsRTUp21160Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 32 is cleared"
	::= 21160

dpsRTUp20161Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 33 is set"
	::= 20161

dpsRTUp21161Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 33 is cleared"
	::= 21161

dpsRTUp20162Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 34 is set"
	::= 20162

dpsRTUp21162Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 34 is cleared"
	::= 21162

dpsRTUp20163Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 35 is set"
	::= 20163

dpsRTUp21163Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 35 is cleared"
	::= 21163

dpsRTUp20164Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 36 is set"
	::= 20164

dpsRTUp21164Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 36 is cleared"
	::= 21164

dpsRTUp20165Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 37 is set"
	::= 20165

dpsRTUp21165Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 37 is cleared"
	::= 21165

dpsRTUp20166Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 38 is set"
	::= 20166

dpsRTUp21166Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 38 is cleared"
	::= 21166

dpsRTUp20167Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 39 is set"
	::= 20167

dpsRTUp21167Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 39 is cleared"
	::= 21167

dpsRTUp20168Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 40 is set"
	::= 20168

dpsRTUp21168Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 40 is cleared"
	::= 21168

dpsRTUp20169Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 41 is set"
	::= 20169

dpsRTUp21169Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 41 is cleared"
	::= 21169

dpsRTUp20170Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 42 is set"
	::= 20170

dpsRTUp21170Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 42 is cleared"
	::= 21170

dpsRTUp20171Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 43 is set"
	::= 20171

dpsRTUp21171Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 43 is cleared"
	::= 21171

dpsRTUp20172Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 44 is set"
	::= 20172

dpsRTUp21172Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 44 is cleared"
	::= 21172

dpsRTUp20173Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 45 is set"
	::= 20173

dpsRTUp21173Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 45 is cleared"
	::= 21173

dpsRTUp20174Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 46 is set"
	::= 20174

dpsRTUp21174Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 46 is cleared"
	::= 21174

dpsRTUp20175Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 47 is set"
	::= 20175

dpsRTUp21175Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 47 is cleared"
	::= 21175

dpsRTUp20176Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 48 is set"
	::= 20176

dpsRTUp21176Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 48 is cleared"
	::= 21176

dpsRTUp20177Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 49 is set"
	::= 20177

dpsRTUp21177Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 49 is cleared"
	::= 21177

dpsRTUp20178Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 50 is set"
	::= 20178

dpsRTUp21178Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 50 is cleared"
	::= 21178

dpsRTUp20179Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 51 is set"
	::= 20179

dpsRTUp21179Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 51 is cleared"
	::= 21179

dpsRTUp20180Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 52 is set"
	::= 20180

dpsRTUp21180Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 52 is cleared"
	::= 21180

dpsRTUp20181Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 53 is set"
	::= 20181

dpsRTUp21181Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 53 is cleared"
	::= 21181

dpsRTUp20182Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 54 is set"
	::= 20182

dpsRTUp21182Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 54 is cleared"
	::= 21182

dpsRTUp20183Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 55 is set"
	::= 20183

dpsRTUp21183Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 55 is cleared"
	::= 21183

dpsRTUp20184Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 56 is set"
	::= 20184

dpsRTUp21184Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 56 is cleared"
	::= 21184

dpsRTUp20185Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 57 is set"
	::= 20185

dpsRTUp21185Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 57 is cleared"
	::= 21185

dpsRTUp20186Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 58 is set"
	::= 20186

dpsRTUp21186Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 58 is cleared"
	::= 21186

dpsRTUp20187Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 59 is set"
	::= 20187

dpsRTUp21187Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 59 is cleared"
	::= 21187

dpsRTUp20188Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 60 is set"
	::= 20188

dpsRTUp21188Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 60 is cleared"
	::= 21188

dpsRTUp20189Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 61 is set"
	::= 20189

dpsRTUp21189Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 61 is cleared"
	::= 21189

dpsRTUp20190Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 62 is set"
	::= 20190

dpsRTUp21190Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 62 is cleared"
	::= 21190

dpsRTUp20191Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 63 is set"
	::= 20191

dpsRTUp21191Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 63 is cleared"
	::= 21191

dpsRTUp20192Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 64 is set"
	::= 20192

dpsRTUp21192Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 3 point 64 is cleared"
	::= 21192

dpsRTUp20193Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 1 is set"
	::= 20193

dpsRTUp21193Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 1 is cleared"
	::= 21193

dpsRTUp20194Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 2 is set"
	::= 20194

dpsRTUp21194Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 2 is cleared"
	::= 21194

dpsRTUp20195Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 3 is set"
	::= 20195

dpsRTUp21195Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 3 is cleared"
	::= 21195

dpsRTUp20196Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 4 is set"
	::= 20196

dpsRTUp21196Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 4 is cleared"
	::= 21196

dpsRTUp20197Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 5 is set"
	::= 20197

dpsRTUp21197Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 5 is cleared"
	::= 21197

dpsRTUp20198Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 6 is set"
	::= 20198

dpsRTUp21198Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 6 is cleared"
	::= 21198

dpsRTUp20199Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 7 is set"
	::= 20199

dpsRTUp21199Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 7 is cleared"
	::= 21199

dpsRTUp20200Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 8 is set"
	::= 20200

dpsRTUp21200Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 8 is cleared"
	::= 21200

dpsRTUp20201Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 9 is set"
	::= 20201

dpsRTUp21201Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 9 is cleared"
	::= 21201

dpsRTUp20202Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 10 is set"
	::= 20202

dpsRTUp21202Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 10 is cleared"
	::= 21202

dpsRTUp20203Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 11 is set"
	::= 20203

dpsRTUp21203Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 11 is cleared"
	::= 21203

dpsRTUp20204Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 12 is set"
	::= 20204

dpsRTUp21204Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 12 is cleared"
	::= 21204

dpsRTUp20205Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 13 is set"
	::= 20205

dpsRTUp21205Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 13 is cleared"
	::= 21205

dpsRTUp20206Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 14 is set"
	::= 20206

dpsRTUp21206Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 14 is cleared"
	::= 21206

dpsRTUp20207Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 15 is set"
	::= 20207

dpsRTUp21207Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 15 is cleared"
	::= 21207

dpsRTUp20208Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 16 is set"
	::= 20208

dpsRTUp21208Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 16 is cleared"
	::= 21208

dpsRTUp20209Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 17 is set"
	::= 20209

dpsRTUp21209Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 17 is cleared"
	::= 21209

dpsRTUp20210Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 18 is set"
	::= 20210

dpsRTUp21210Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 18 is cleared"
	::= 21210

dpsRTUp20211Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 19 is set"
	::= 20211

dpsRTUp21211Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 19 is cleared"
	::= 21211

dpsRTUp20212Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 20 is set"
	::= 20212

dpsRTUp21212Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 20 is cleared"
	::= 21212

dpsRTUp20213Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 21 is set"
	::= 20213

dpsRTUp21213Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 21 is cleared"
	::= 21213

dpsRTUp20214Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 22 is set"
	::= 20214

dpsRTUp21214Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 22 is cleared"
	::= 21214

dpsRTUp20215Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 23 is set"
	::= 20215

dpsRTUp21215Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 23 is cleared"
	::= 21215

dpsRTUp20216Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 24 is set"
	::= 20216

dpsRTUp21216Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 24 is cleared"
	::= 21216

dpsRTUp20217Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 25 is set"
	::= 20217

dpsRTUp21217Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 25 is cleared"
	::= 21217

dpsRTUp20218Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 26 is set"
	::= 20218

dpsRTUp21218Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 26 is cleared"
	::= 21218

dpsRTUp20219Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 27 is set"
	::= 20219

dpsRTUp21219Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 27 is cleared"
	::= 21219

dpsRTUp20220Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 28 is set"
	::= 20220

dpsRTUp21220Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 28 is cleared"
	::= 21220

dpsRTUp20221Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 29 is set"
	::= 20221

dpsRTUp21221Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 29 is cleared"
	::= 21221

dpsRTUp20222Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 30 is set"
	::= 20222

dpsRTUp21222Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 30 is cleared"
	::= 21222

dpsRTUp20223Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 31 is set"
	::= 20223

dpsRTUp21223Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 31 is cleared"
	::= 21223

dpsRTUp20224Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 32 is set"
	::= 20224

dpsRTUp21224Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 32 is cleared"
	::= 21224

dpsRTUp20225Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 33 is set"
	::= 20225

dpsRTUp21225Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 33 is cleared"
	::= 21225

dpsRTUp20226Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 34 is set"
	::= 20226

dpsRTUp21226Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 34 is cleared"
	::= 21226

dpsRTUp20227Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 35 is set"
	::= 20227

dpsRTUp21227Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 35 is cleared"
	::= 21227

dpsRTUp20228Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 36 is set"
	::= 20228

dpsRTUp21228Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 36 is cleared"
	::= 21228

dpsRTUp20229Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 37 is set"
	::= 20229

dpsRTUp21229Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 37 is cleared"
	::= 21229

dpsRTUp20230Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 38 is set"
	::= 20230

dpsRTUp21230Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 38 is cleared"
	::= 21230

dpsRTUp20231Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 39 is set"
	::= 20231

dpsRTUp21231Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 39 is cleared"
	::= 21231

dpsRTUp20232Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 40 is set"
	::= 20232

dpsRTUp21232Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 40 is cleared"
	::= 21232

dpsRTUp20233Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 41 is set"
	::= 20233

dpsRTUp21233Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 41 is cleared"
	::= 21233

dpsRTUp20234Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 42 is set"
	::= 20234

dpsRTUp21234Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 42 is cleared"
	::= 21234

dpsRTUp20235Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 43 is set"
	::= 20235

dpsRTUp21235Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 43 is cleared"
	::= 21235

dpsRTUp20236Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 44 is set"
	::= 20236

dpsRTUp21236Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 44 is cleared"
	::= 21236

dpsRTUp20237Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 45 is set"
	::= 20237

dpsRTUp21237Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 45 is cleared"
	::= 21237

dpsRTUp20238Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 46 is set"
	::= 20238

dpsRTUp21238Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 46 is cleared"
	::= 21238

dpsRTUp20239Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 47 is set"
	::= 20239

dpsRTUp21239Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 47 is cleared"
	::= 21239

dpsRTUp20240Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 48 is set"
	::= 20240

dpsRTUp21240Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 48 is cleared"
	::= 21240

dpsRTUp20241Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 49 is set"
	::= 20241

dpsRTUp21241Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 49 is cleared"
	::= 21241

dpsRTUp20242Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 50 is set"
	::= 20242

dpsRTUp21242Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 50 is cleared"
	::= 21242

dpsRTUp20243Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 51 is set"
	::= 20243

dpsRTUp21243Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 51 is cleared"
	::= 21243

dpsRTUp20244Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 52 is set"
	::= 20244

dpsRTUp21244Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 52 is cleared"
	::= 21244

dpsRTUp20245Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 53 is set"
	::= 20245

dpsRTUp21245Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 53 is cleared"
	::= 21245

dpsRTUp20246Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 54 is set"
	::= 20246

dpsRTUp21246Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 54 is cleared"
	::= 21246

dpsRTUp20247Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 55 is set"
	::= 20247

dpsRTUp21247Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 55 is cleared"
	::= 21247

dpsRTUp20248Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 56 is set"
	::= 20248

dpsRTUp21248Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 56 is cleared"
	::= 21248

dpsRTUp20249Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 57 is set"
	::= 20249

dpsRTUp21249Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 57 is cleared"
	::= 21249

dpsRTUp20250Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 58 is set"
	::= 20250

dpsRTUp21250Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 58 is cleared"
	::= 21250

dpsRTUp20251Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 59 is set"
	::= 20251

dpsRTUp21251Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 59 is cleared"
	::= 21251

dpsRTUp20252Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 60 is set"
	::= 20252

dpsRTUp21252Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 60 is cleared"
	::= 21252

dpsRTUp20253Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 61 is set"
	::= 20253

dpsRTUp21253Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 61 is cleared"
	::= 21253

dpsRTUp20254Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 62 is set"
	::= 20254

dpsRTUp21254Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 62 is cleared"
	::= 21254

dpsRTUp20255Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 63 is set"
	::= 20255

dpsRTUp21255Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 63 is cleared"
	::= 21255

dpsRTUp20256Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 64 is set"
	::= 20256

dpsRTUp21256Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 4 point 64 is cleared"
	::= 21256

dpsRTUp20257Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 1 is set"
	::= 20257

dpsRTUp21257Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 1 is cleared"
	::= 21257

dpsRTUp20258Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 2 is set"
	::= 20258

dpsRTUp21258Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 2 is cleared"
	::= 21258

dpsRTUp20259Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 3 is set"
	::= 20259

dpsRTUp21259Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 3 is cleared"
	::= 21259

dpsRTUp20260Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 4 is set"
	::= 20260

dpsRTUp21260Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 4 is cleared"
	::= 21260

dpsRTUp20261Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 5 is set"
	::= 20261

dpsRTUp21261Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 5 is cleared"
	::= 21261

dpsRTUp20262Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 6 is set"
	::= 20262

dpsRTUp21262Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 6 is cleared"
	::= 21262

dpsRTUp20263Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 7 is set"
	::= 20263

dpsRTUp21263Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 7 is cleared"
	::= 21263

dpsRTUp20264Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 8 is set"
	::= 20264

dpsRTUp21264Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 8 is cleared"
	::= 21264

dpsRTUp20265Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 9 is set"
	::= 20265

dpsRTUp21265Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 9 is cleared"
	::= 21265

dpsRTUp20266Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 10 is set"
	::= 20266

dpsRTUp21266Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 10 is cleared"
	::= 21266

dpsRTUp20267Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 11 is set"
	::= 20267

dpsRTUp21267Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 11 is cleared"
	::= 21267

dpsRTUp20268Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 12 is set"
	::= 20268

dpsRTUp21268Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 12 is cleared"
	::= 21268

dpsRTUp20269Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 13 is set"
	::= 20269

dpsRTUp21269Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 13 is cleared"
	::= 21269

dpsRTUp20270Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 14 is set"
	::= 20270

dpsRTUp21270Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 14 is cleared"
	::= 21270

dpsRTUp20271Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 15 is set"
	::= 20271

dpsRTUp21271Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 15 is cleared"
	::= 21271

dpsRTUp20272Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 16 is set"
	::= 20272

dpsRTUp21272Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 16 is cleared"
	::= 21272

dpsRTUp20273Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 17 is set"
	::= 20273

dpsRTUp21273Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 17 is cleared"
	::= 21273

dpsRTUp20274Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 18 is set"
	::= 20274

dpsRTUp21274Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 18 is cleared"
	::= 21274

dpsRTUp20275Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 19 is set"
	::= 20275

dpsRTUp21275Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 19 is cleared"
	::= 21275

dpsRTUp20276Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 20 is set"
	::= 20276

dpsRTUp21276Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 20 is cleared"
	::= 21276

dpsRTUp20277Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 21 is set"
	::= 20277

dpsRTUp21277Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 21 is cleared"
	::= 21277

dpsRTUp20278Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 22 is set"
	::= 20278

dpsRTUp21278Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 22 is cleared"
	::= 21278

dpsRTUp20279Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 23 is set"
	::= 20279

dpsRTUp21279Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 23 is cleared"
	::= 21279

dpsRTUp20280Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 24 is set"
	::= 20280

dpsRTUp21280Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 24 is cleared"
	::= 21280

dpsRTUp20281Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 25 is set"
	::= 20281

dpsRTUp21281Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 25 is cleared"
	::= 21281

dpsRTUp20282Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 26 is set"
	::= 20282

dpsRTUp21282Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 26 is cleared"
	::= 21282

dpsRTUp20283Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 27 is set"
	::= 20283

dpsRTUp21283Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 27 is cleared"
	::= 21283

dpsRTUp20284Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 28 is set"
	::= 20284

dpsRTUp21284Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 28 is cleared"
	::= 21284

dpsRTUp20285Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 29 is set"
	::= 20285

dpsRTUp21285Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 29 is cleared"
	::= 21285

dpsRTUp20286Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 30 is set"
	::= 20286

dpsRTUp21286Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 30 is cleared"
	::= 21286

dpsRTUp20287Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 31 is set"
	::= 20287

dpsRTUp21287Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 31 is cleared"
	::= 21287

dpsRTUp20288Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 32 is set"
	::= 20288

dpsRTUp21288Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 32 is cleared"
	::= 21288

dpsRTUp20289Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 33 is set"
	::= 20289

dpsRTUp21289Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 33 is cleared"
	::= 21289

dpsRTUp20290Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 34 is set"
	::= 20290

dpsRTUp21290Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 34 is cleared"
	::= 21290

dpsRTUp20291Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 35 is set"
	::= 20291

dpsRTUp21291Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 35 is cleared"
	::= 21291

dpsRTUp20292Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 36 is set"
	::= 20292

dpsRTUp21292Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 36 is cleared"
	::= 21292

dpsRTUp20293Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 37 is set"
	::= 20293

dpsRTUp21293Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 37 is cleared"
	::= 21293

dpsRTUp20294Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 38 is set"
	::= 20294

dpsRTUp21294Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 38 is cleared"
	::= 21294

dpsRTUp20295Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 39 is set"
	::= 20295

dpsRTUp21295Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 39 is cleared"
	::= 21295

dpsRTUp20296Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 40 is set"
	::= 20296

dpsRTUp21296Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 40 is cleared"
	::= 21296

dpsRTUp20297Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 41 is set"
	::= 20297

dpsRTUp21297Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 41 is cleared"
	::= 21297

dpsRTUp20298Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 42 is set"
	::= 20298

dpsRTUp21298Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 42 is cleared"
	::= 21298

dpsRTUp20299Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 43 is set"
	::= 20299

dpsRTUp21299Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 43 is cleared"
	::= 21299

dpsRTUp20300Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 44 is set"
	::= 20300

dpsRTUp21300Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 44 is cleared"
	::= 21300

dpsRTUp20301Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 45 is set"
	::= 20301

dpsRTUp21301Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 45 is cleared"
	::= 21301

dpsRTUp20302Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 46 is set"
	::= 20302

dpsRTUp21302Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 46 is cleared"
	::= 21302

dpsRTUp20303Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 47 is set"
	::= 20303

dpsRTUp21303Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 47 is cleared"
	::= 21303

dpsRTUp20304Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 48 is set"
	::= 20304

dpsRTUp21304Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 48 is cleared"
	::= 21304

dpsRTUp20305Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 49 is set"
	::= 20305

dpsRTUp21305Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 49 is cleared"
	::= 21305

dpsRTUp20306Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 50 is set"
	::= 20306

dpsRTUp21306Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 50 is cleared"
	::= 21306

dpsRTUp20307Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 51 is set"
	::= 20307

dpsRTUp21307Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 51 is cleared"
	::= 21307

dpsRTUp20308Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 52 is set"
	::= 20308

dpsRTUp21308Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 52 is cleared"
	::= 21308

dpsRTUp20309Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 53 is set"
	::= 20309

dpsRTUp21309Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 53 is cleared"
	::= 21309

dpsRTUp20310Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 54 is set"
	::= 20310

dpsRTUp21310Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 54 is cleared"
	::= 21310

dpsRTUp20311Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 55 is set"
	::= 20311

dpsRTUp21311Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 55 is cleared"
	::= 21311

dpsRTUp20312Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 56 is set"
	::= 20312

dpsRTUp21312Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 56 is cleared"
	::= 21312

dpsRTUp20313Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 57 is set"
	::= 20313

dpsRTUp21313Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 57 is cleared"
	::= 21313

dpsRTUp20314Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 58 is set"
	::= 20314

dpsRTUp21314Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 58 is cleared"
	::= 21314

dpsRTUp20315Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 59 is set"
	::= 20315

dpsRTUp21315Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 59 is cleared"
	::= 21315

dpsRTUp20316Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 60 is set"
	::= 20316

dpsRTUp21316Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 60 is cleared"
	::= 21316

dpsRTUp20317Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 61 is set"
	::= 20317

dpsRTUp21317Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 61 is cleared"
	::= 21317

dpsRTUp20318Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 62 is set"
	::= 20318

dpsRTUp21318Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 62 is cleared"
	::= 21318

dpsRTUp20319Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 63 is set"
	::= 20319

dpsRTUp21319Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 63 is cleared"
	::= 21319

dpsRTUp20320Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 64 is set"
	::= 20320

dpsRTUp21320Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 5 point 64 is cleared"
	::= 21320

dpsRTUp20321Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 1 is set"
	::= 20321

dpsRTUp21321Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 1 is cleared"
	::= 21321

dpsRTUp20322Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 2 is set"
	::= 20322

dpsRTUp21322Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 2 is cleared"
	::= 21322

dpsRTUp20323Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 3 is set"
	::= 20323

dpsRTUp21323Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 3 is cleared"
	::= 21323

dpsRTUp20324Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 4 is set"
	::= 20324

dpsRTUp21324Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 4 is cleared"
	::= 21324

dpsRTUp20325Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 5 is set"
	::= 20325

dpsRTUp21325Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 5 is cleared"
	::= 21325

dpsRTUp20326Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 6 is set"
	::= 20326

dpsRTUp21326Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 6 is cleared"
	::= 21326

dpsRTUp20327Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 7 is set"
	::= 20327

dpsRTUp21327Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 7 is cleared"
	::= 21327

dpsRTUp20328Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 8 is set"
	::= 20328

dpsRTUp21328Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 8 is cleared"
	::= 21328

dpsRTUp20329Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 9 is set"
	::= 20329

dpsRTUp21329Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 9 is cleared"
	::= 21329

dpsRTUp20330Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 10 is set"
	::= 20330

dpsRTUp21330Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 10 is cleared"
	::= 21330

dpsRTUp20331Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 11 is set"
	::= 20331

dpsRTUp21331Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 11 is cleared"
	::= 21331

dpsRTUp20332Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 12 is set"
	::= 20332

dpsRTUp21332Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 12 is cleared"
	::= 21332

dpsRTUp20333Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 13 is set"
	::= 20333

dpsRTUp21333Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 13 is cleared"
	::= 21333

dpsRTUp20334Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 14 is set"
	::= 20334

dpsRTUp21334Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 14 is cleared"
	::= 21334

dpsRTUp20335Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 15 is set"
	::= 20335

dpsRTUp21335Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 15 is cleared"
	::= 21335

dpsRTUp20336Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 16 is set"
	::= 20336

dpsRTUp21336Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 16 is cleared"
	::= 21336

dpsRTUp20337Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 17 is set"
	::= 20337

dpsRTUp21337Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 17 is cleared"
	::= 21337

dpsRTUp20338Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 18 is set"
	::= 20338

dpsRTUp21338Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 18 is cleared"
	::= 21338

dpsRTUp20339Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 19 is set"
	::= 20339

dpsRTUp21339Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 19 is cleared"
	::= 21339

dpsRTUp20340Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 20 is set"
	::= 20340

dpsRTUp21340Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 20 is cleared"
	::= 21340

dpsRTUp20341Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 21 is set"
	::= 20341

dpsRTUp21341Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 21 is cleared"
	::= 21341

dpsRTUp20342Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 22 is set"
	::= 20342

dpsRTUp21342Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 22 is cleared"
	::= 21342

dpsRTUp20343Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 23 is set"
	::= 20343

dpsRTUp21343Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 23 is cleared"
	::= 21343

dpsRTUp20344Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 24 is set"
	::= 20344

dpsRTUp21344Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 24 is cleared"
	::= 21344

dpsRTUp20345Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 25 is set"
	::= 20345

dpsRTUp21345Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 25 is cleared"
	::= 21345

dpsRTUp20346Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 26 is set"
	::= 20346

dpsRTUp21346Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 26 is cleared"
	::= 21346

dpsRTUp20347Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 27 is set"
	::= 20347

dpsRTUp21347Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 27 is cleared"
	::= 21347

dpsRTUp20348Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 28 is set"
	::= 20348

dpsRTUp21348Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 28 is cleared"
	::= 21348

dpsRTUp20349Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 29 is set"
	::= 20349

dpsRTUp21349Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 29 is cleared"
	::= 21349

dpsRTUp20350Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 30 is set"
	::= 20350

dpsRTUp21350Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 30 is cleared"
	::= 21350

dpsRTUp20351Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 31 is set"
	::= 20351

dpsRTUp21351Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 31 is cleared"
	::= 21351

dpsRTUp20352Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 32 is set"
	::= 20352

dpsRTUp21352Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 32 is cleared"
	::= 21352

dpsRTUp20353Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 33 is set"
	::= 20353

dpsRTUp21353Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 33 is cleared"
	::= 21353

dpsRTUp20354Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 34 is set"
	::= 20354

dpsRTUp21354Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 34 is cleared"
	::= 21354

dpsRTUp20355Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 35 is set"
	::= 20355

dpsRTUp21355Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 35 is cleared"
	::= 21355

dpsRTUp20356Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 36 is set"
	::= 20356

dpsRTUp21356Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 36 is cleared"
	::= 21356

dpsRTUp20357Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 37 is set"
	::= 20357

dpsRTUp21357Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 37 is cleared"
	::= 21357

dpsRTUp20358Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 38 is set"
	::= 20358

dpsRTUp21358Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 38 is cleared"
	::= 21358

dpsRTUp20359Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 39 is set"
	::= 20359

dpsRTUp21359Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 39 is cleared"
	::= 21359

dpsRTUp20360Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 40 is set"
	::= 20360

dpsRTUp21360Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 40 is cleared"
	::= 21360

dpsRTUp20361Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 41 is set"
	::= 20361

dpsRTUp21361Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 41 is cleared"
	::= 21361

dpsRTUp20362Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 42 is set"
	::= 20362

dpsRTUp21362Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 42 is cleared"
	::= 21362

dpsRTUp20363Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 43 is set"
	::= 20363

dpsRTUp21363Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 43 is cleared"
	::= 21363

dpsRTUp20364Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 44 is set"
	::= 20364

dpsRTUp21364Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 44 is cleared"
	::= 21364

dpsRTUp20365Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 45 is set"
	::= 20365

dpsRTUp21365Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 45 is cleared"
	::= 21365

dpsRTUp20366Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 46 is set"
	::= 20366

dpsRTUp21366Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 46 is cleared"
	::= 21366

dpsRTUp20367Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 47 is set"
	::= 20367

dpsRTUp21367Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 47 is cleared"
	::= 21367

dpsRTUp20368Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 48 is set"
	::= 20368

dpsRTUp21368Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 48 is cleared"
	::= 21368

dpsRTUp20369Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 49 is set"
	::= 20369

dpsRTUp21369Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 49 is cleared"
	::= 21369

dpsRTUp20370Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 50 is set"
	::= 20370

dpsRTUp21370Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 50 is cleared"
	::= 21370

dpsRTUp20371Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 51 is set"
	::= 20371

dpsRTUp21371Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 51 is cleared"
	::= 21371

dpsRTUp20372Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 52 is set"
	::= 20372

dpsRTUp21372Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 52 is cleared"
	::= 21372

dpsRTUp20373Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 53 is set"
	::= 20373

dpsRTUp21373Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 53 is cleared"
	::= 21373

dpsRTUp20374Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 54 is set"
	::= 20374

dpsRTUp21374Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 54 is cleared"
	::= 21374

dpsRTUp20375Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 55 is set"
	::= 20375

dpsRTUp21375Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 55 is cleared"
	::= 21375

dpsRTUp20376Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 56 is set"
	::= 20376

dpsRTUp21376Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 56 is cleared"
	::= 21376

dpsRTUp20377Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 57 is set"
	::= 20377

dpsRTUp21377Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 57 is cleared"
	::= 21377

dpsRTUp20378Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 58 is set"
	::= 20378

dpsRTUp21378Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 58 is cleared"
	::= 21378

dpsRTUp20379Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 59 is set"
	::= 20379

dpsRTUp21379Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 59 is cleared"
	::= 21379

dpsRTUp20380Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 60 is set"
	::= 20380

dpsRTUp21380Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 60 is cleared"
	::= 21380

dpsRTUp20381Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 61 is set"
	::= 20381

dpsRTUp21381Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 61 is cleared"
	::= 21381

dpsRTUp20382Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 62 is set"
	::= 20382

dpsRTUp21382Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 62 is cleared"
	::= 21382

dpsRTUp20383Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 63 is set"
	::= 20383

dpsRTUp21383Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 63 is cleared"
	::= 21383

dpsRTUp20384Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 64 is set"
	::= 20384

dpsRTUp21384Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 6 point 64 is cleared"
	::= 21384

dpsRTUp20385Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 1 is set"
	::= 20385

dpsRTUp21385Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 1 is cleared"
	::= 21385

dpsRTUp20386Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 2 is set"
	::= 20386

dpsRTUp21386Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 2 is cleared"
	::= 21386

dpsRTUp20387Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 3 is set"
	::= 20387

dpsRTUp21387Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 3 is cleared"
	::= 21387

dpsRTUp20388Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 4 is set"
	::= 20388

dpsRTUp21388Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 4 is cleared"
	::= 21388

dpsRTUp20389Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 5 is set"
	::= 20389

dpsRTUp21389Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 5 is cleared"
	::= 21389

dpsRTUp20390Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 6 is set"
	::= 20390

dpsRTUp21390Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 6 is cleared"
	::= 21390

dpsRTUp20391Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 7 is set"
	::= 20391

dpsRTUp21391Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 7 is cleared"
	::= 21391

dpsRTUp20392Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 8 is set"
	::= 20392

dpsRTUp21392Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 8 is cleared"
	::= 21392

dpsRTUp20393Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 9 is set"
	::= 20393

dpsRTUp21393Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 9 is cleared"
	::= 21393

dpsRTUp20394Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 10 is set"
	::= 20394

dpsRTUp21394Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 10 is cleared"
	::= 21394

dpsRTUp20395Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 11 is set"
	::= 20395

dpsRTUp21395Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 11 is cleared"
	::= 21395

dpsRTUp20396Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 12 is set"
	::= 20396

dpsRTUp21396Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 12 is cleared"
	::= 21396

dpsRTUp20397Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 13 is set"
	::= 20397

dpsRTUp21397Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 13 is cleared"
	::= 21397

dpsRTUp20398Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 14 is set"
	::= 20398

dpsRTUp21398Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 14 is cleared"
	::= 21398

dpsRTUp20399Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 15 is set"
	::= 20399

dpsRTUp21399Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 15 is cleared"
	::= 21399

dpsRTUp20400Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 16 is set"
	::= 20400

dpsRTUp21400Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 16 is cleared"
	::= 21400

dpsRTUp20401Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 17 is set"
	::= 20401

dpsRTUp21401Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 17 is cleared"
	::= 21401

dpsRTUp20402Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 18 is set"
	::= 20402

dpsRTUp21402Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 18 is cleared"
	::= 21402

dpsRTUp20403Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 19 is set"
	::= 20403

dpsRTUp21403Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 19 is cleared"
	::= 21403

dpsRTUp20404Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 20 is set"
	::= 20404

dpsRTUp21404Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 20 is cleared"
	::= 21404

dpsRTUp20405Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 21 is set"
	::= 20405

dpsRTUp21405Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 21 is cleared"
	::= 21405

dpsRTUp20406Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 22 is set"
	::= 20406

dpsRTUp21406Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 22 is cleared"
	::= 21406

dpsRTUp20407Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 23 is set"
	::= 20407

dpsRTUp21407Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 23 is cleared"
	::= 21407

dpsRTUp20408Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 24 is set"
	::= 20408

dpsRTUp21408Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 24 is cleared"
	::= 21408

dpsRTUp20409Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 25 is set"
	::= 20409

dpsRTUp21409Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 25 is cleared"
	::= 21409

dpsRTUp20410Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 26 is set"
	::= 20410

dpsRTUp21410Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 26 is cleared"
	::= 21410

dpsRTUp20411Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 27 is set"
	::= 20411

dpsRTUp21411Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 27 is cleared"
	::= 21411

dpsRTUp20412Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 28 is set"
	::= 20412

dpsRTUp21412Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 28 is cleared"
	::= 21412

dpsRTUp20413Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 29 is set"
	::= 20413

dpsRTUp21413Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 29 is cleared"
	::= 21413

dpsRTUp20414Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 30 is set"
	::= 20414

dpsRTUp21414Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 30 is cleared"
	::= 21414

dpsRTUp20415Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 31 is set"
	::= 20415

dpsRTUp21415Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 31 is cleared"
	::= 21415

dpsRTUp20416Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 32 is set"
	::= 20416

dpsRTUp21416Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 32 is cleared"
	::= 21416

dpsRTUp20417Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 33 is set"
	::= 20417

dpsRTUp21417Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 33 is cleared"
	::= 21417

dpsRTUp20418Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 34 is set"
	::= 20418

dpsRTUp21418Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 34 is cleared"
	::= 21418

dpsRTUp20419Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 35 is set"
	::= 20419

dpsRTUp21419Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 35 is cleared"
	::= 21419

dpsRTUp20420Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 36 is set"
	::= 20420

dpsRTUp21420Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 36 is cleared"
	::= 21420

dpsRTUp20421Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 37 is set"
	::= 20421

dpsRTUp21421Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 37 is cleared"
	::= 21421

dpsRTUp20422Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 38 is set"
	::= 20422

dpsRTUp21422Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 38 is cleared"
	::= 21422

dpsRTUp20423Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 39 is set"
	::= 20423

dpsRTUp21423Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 39 is cleared"
	::= 21423

dpsRTUp20424Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 40 is set"
	::= 20424

dpsRTUp21424Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 40 is cleared"
	::= 21424

dpsRTUp20425Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 41 is set"
	::= 20425

dpsRTUp21425Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 41 is cleared"
	::= 21425

dpsRTUp20426Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 42 is set"
	::= 20426

dpsRTUp21426Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 42 is cleared"
	::= 21426

dpsRTUp20427Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 43 is set"
	::= 20427

dpsRTUp21427Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 43 is cleared"
	::= 21427

dpsRTUp20428Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 44 is set"
	::= 20428

dpsRTUp21428Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 44 is cleared"
	::= 21428

dpsRTUp20429Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 45 is set"
	::= 20429

dpsRTUp21429Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 45 is cleared"
	::= 21429

dpsRTUp20430Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 46 is set"
	::= 20430

dpsRTUp21430Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 46 is cleared"
	::= 21430

dpsRTUp20431Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 47 is set"
	::= 20431

dpsRTUp21431Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 47 is cleared"
	::= 21431

dpsRTUp20432Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 48 is set"
	::= 20432

dpsRTUp21432Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 48 is cleared"
	::= 21432

dpsRTUp20433Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 49 is set"
	::= 20433

dpsRTUp21433Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 49 is cleared"
	::= 21433

dpsRTUp20434Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 50 is set"
	::= 20434

dpsRTUp21434Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 50 is cleared"
	::= 21434

dpsRTUp20435Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 51 is set"
	::= 20435

dpsRTUp21435Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 51 is cleared"
	::= 21435

dpsRTUp20436Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 52 is set"
	::= 20436

dpsRTUp21436Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 52 is cleared"
	::= 21436

dpsRTUp20437Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 53 is set"
	::= 20437

dpsRTUp21437Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 53 is cleared"
	::= 21437

dpsRTUp20438Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 54 is set"
	::= 20438

dpsRTUp21438Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 54 is cleared"
	::= 21438

dpsRTUp20439Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 55 is set"
	::= 20439

dpsRTUp21439Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 55 is cleared"
	::= 21439

dpsRTUp20440Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 56 is set"
	::= 20440

dpsRTUp21440Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 56 is cleared"
	::= 21440

dpsRTUp20441Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 57 is set"
	::= 20441

dpsRTUp21441Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 57 is cleared"
	::= 21441

dpsRTUp20442Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 58 is set"
	::= 20442

dpsRTUp21442Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 58 is cleared"
	::= 21442

dpsRTUp20443Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 59 is set"
	::= 20443

dpsRTUp21443Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 59 is cleared"
	::= 21443

dpsRTUp20444Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 60 is set"
	::= 20444

dpsRTUp21444Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 60 is cleared"
	::= 21444

dpsRTUp20445Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 61 is set"
	::= 20445

dpsRTUp21445Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 61 is cleared"
	::= 21445

dpsRTUp20446Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 62 is set"
	::= 20446

dpsRTUp21446Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 62 is cleared"
	::= 21446

dpsRTUp20447Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 63 is set"
	::= 20447

dpsRTUp21447Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 63 is cleared"
	::= 21447

dpsRTUp20448Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 64 is set"
	::= 20448

dpsRTUp21448Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 7 point 64 is cleared"
	::= 21448

dpsRTUp20449Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 1 is set"
	::= 20449

dpsRTUp21449Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 1 is cleared"
	::= 21449

dpsRTUp20450Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 2 is set"
	::= 20450

dpsRTUp21450Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 2 is cleared"
	::= 21450

dpsRTUp20451Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 3 is set"
	::= 20451

dpsRTUp21451Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 3 is cleared"
	::= 21451

dpsRTUp20452Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 4 is set"
	::= 20452

dpsRTUp21452Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 4 is cleared"
	::= 21452

dpsRTUp20453Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 5 is set"
	::= 20453

dpsRTUp21453Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 5 is cleared"
	::= 21453

dpsRTUp20454Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 6 is set"
	::= 20454

dpsRTUp21454Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 6 is cleared"
	::= 21454

dpsRTUp20455Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 7 is set"
	::= 20455

dpsRTUp21455Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 7 is cleared"
	::= 21455

dpsRTUp20456Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 8 is set"
	::= 20456

dpsRTUp21456Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 8 is cleared"
	::= 21456

dpsRTUp20457Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 9 is set"
	::= 20457

dpsRTUp21457Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 9 is cleared"
	::= 21457

dpsRTUp20458Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 10 is set"
	::= 20458

dpsRTUp21458Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 10 is cleared"
	::= 21458

dpsRTUp20459Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 11 is set"
	::= 20459

dpsRTUp21459Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 11 is cleared"
	::= 21459

dpsRTUp20460Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 12 is set"
	::= 20460

dpsRTUp21460Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 12 is cleared"
	::= 21460

dpsRTUp20461Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 13 is set"
	::= 20461

dpsRTUp21461Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 13 is cleared"
	::= 21461

dpsRTUp20462Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 14 is set"
	::= 20462

dpsRTUp21462Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 14 is cleared"
	::= 21462

dpsRTUp20463Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 15 is set"
	::= 20463

dpsRTUp21463Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 15 is cleared"
	::= 21463

dpsRTUp20464Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 16 is set"
	::= 20464

dpsRTUp21464Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 16 is cleared"
	::= 21464

dpsRTUp20465Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 17 is set"
	::= 20465

dpsRTUp21465Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 17 is cleared"
	::= 21465

dpsRTUp20466Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 18 is set"
	::= 20466

dpsRTUp21466Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 18 is cleared"
	::= 21466

dpsRTUp20467Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 19 is set"
	::= 20467

dpsRTUp21467Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 19 is cleared"
	::= 21467

dpsRTUp20468Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 20 is set"
	::= 20468

dpsRTUp21468Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 20 is cleared"
	::= 21468

dpsRTUp20469Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 21 is set"
	::= 20469

dpsRTUp21469Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 21 is cleared"
	::= 21469

dpsRTUp20470Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 22 is set"
	::= 20470

dpsRTUp21470Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 22 is cleared"
	::= 21470

dpsRTUp20471Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 23 is set"
	::= 20471

dpsRTUp21471Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 23 is cleared"
	::= 21471

dpsRTUp20472Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 24 is set"
	::= 20472

dpsRTUp21472Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 24 is cleared"
	::= 21472

dpsRTUp20473Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 25 is set"
	::= 20473

dpsRTUp21473Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 25 is cleared"
	::= 21473

dpsRTUp20474Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 26 is set"
	::= 20474

dpsRTUp21474Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 26 is cleared"
	::= 21474

dpsRTUp20475Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 27 is set"
	::= 20475

dpsRTUp21475Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 27 is cleared"
	::= 21475

dpsRTUp20476Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 28 is set"
	::= 20476

dpsRTUp21476Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 28 is cleared"
	::= 21476

dpsRTUp20477Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 29 is set"
	::= 20477

dpsRTUp21477Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 29 is cleared"
	::= 21477

dpsRTUp20478Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 30 is set"
	::= 20478

dpsRTUp21478Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 30 is cleared"
	::= 21478

dpsRTUp20479Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 31 is set"
	::= 20479

dpsRTUp21479Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 31 is cleared"
	::= 21479

dpsRTUp20480Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 32 is set"
	::= 20480

dpsRTUp21480Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 32 is cleared"
	::= 21480

dpsRTUp20481Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 33 is set"
	::= 20481

dpsRTUp21481Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 33 is cleared"
	::= 21481

dpsRTUp20482Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 34 is set"
	::= 20482

dpsRTUp21482Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 34 is cleared"
	::= 21482

dpsRTUp20483Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 35 is set"
	::= 20483

dpsRTUp21483Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 35 is cleared"
	::= 21483

dpsRTUp20484Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 36 is set"
	::= 20484

dpsRTUp21484Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 36 is cleared"
	::= 21484

dpsRTUp20485Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 37 is set"
	::= 20485

dpsRTUp21485Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 37 is cleared"
	::= 21485

dpsRTUp20486Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 38 is set"
	::= 20486

dpsRTUp21486Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 38 is cleared"
	::= 21486

dpsRTUp20487Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 39 is set"
	::= 20487

dpsRTUp21487Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 39 is cleared"
	::= 21487

dpsRTUp20488Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 40 is set"
	::= 20488

dpsRTUp21488Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 40 is cleared"
	::= 21488

dpsRTUp20489Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 41 is set"
	::= 20489

dpsRTUp21489Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 41 is cleared"
	::= 21489

dpsRTUp20490Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 42 is set"
	::= 20490

dpsRTUp21490Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 42 is cleared"
	::= 21490

dpsRTUp20491Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 43 is set"
	::= 20491

dpsRTUp21491Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 43 is cleared"
	::= 21491

dpsRTUp20492Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 44 is set"
	::= 20492

dpsRTUp21492Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 44 is cleared"
	::= 21492

dpsRTUp20493Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 45 is set"
	::= 20493

dpsRTUp21493Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 45 is cleared"
	::= 21493

dpsRTUp20494Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 46 is set"
	::= 20494

dpsRTUp21494Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 46 is cleared"
	::= 21494

dpsRTUp20495Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 47 is set"
	::= 20495

dpsRTUp21495Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 47 is cleared"
	::= 21495

dpsRTUp20496Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 48 is set"
	::= 20496

dpsRTUp21496Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 48 is cleared"
	::= 21496

dpsRTUp20497Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 49 is set"
	::= 20497

dpsRTUp21497Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 49 is cleared"
	::= 21497

dpsRTUp20498Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 50 is set"
	::= 20498

dpsRTUp21498Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 50 is cleared"
	::= 21498

dpsRTUp20499Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 51 is set"
	::= 20499

dpsRTUp21499Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 51 is cleared"
	::= 21499

dpsRTUp20500Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 52 is set"
	::= 20500

dpsRTUp21500Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 52 is cleared"
	::= 21500

dpsRTUp20501Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 53 is set"
	::= 20501

dpsRTUp21501Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 53 is cleared"
	::= 21501

dpsRTUp20502Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 54 is set"
	::= 20502

dpsRTUp21502Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 54 is cleared"
	::= 21502

dpsRTUp20503Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 55 is set"
	::= 20503

dpsRTUp21503Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 55 is cleared"
	::= 21503

dpsRTUp20504Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 56 is set"
	::= 20504

dpsRTUp21504Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 56 is cleared"
	::= 21504

dpsRTUp20505Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 57 is set"
	::= 20505

dpsRTUp21505Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 57 is cleared"
	::= 21505

dpsRTUp20506Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 58 is set"
	::= 20506

dpsRTUp21506Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 58 is cleared"
	::= 21506

dpsRTUp20507Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 59 is set"
	::= 20507

dpsRTUp21507Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 59 is cleared"
	::= 21507

dpsRTUp20508Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 60 is set"
	::= 20508

dpsRTUp21508Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 60 is cleared"
	::= 21508

dpsRTUp20509Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 61 is set"
	::= 20509

dpsRTUp21509Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 61 is cleared"
	::= 21509

dpsRTUp20510Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 62 is set"
	::= 20510

dpsRTUp21510Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 62 is cleared"
	::= 21510

dpsRTUp20511Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 63 is set"
	::= 20511

dpsRTUp21511Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 63 is cleared"
	::= 21511

dpsRTUp20512Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 64 is set"
	::= 20512

dpsRTUp21512Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 6 display 8 point 64 is cleared"
	::= 21512

dpsRTUp22001Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 1 is set"
	::= 22001

dpsRTUp23001Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 1 is cleared"
	::= 23001

dpsRTUp22002Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 2 is set"
	::= 22002

dpsRTUp23002Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 2 is cleared"
	::= 23002

dpsRTUp22003Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 3 is set"
	::= 22003

dpsRTUp23003Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 3 is cleared"
	::= 23003

dpsRTUp22004Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 4 is set"
	::= 22004

dpsRTUp23004Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 4 is cleared"
	::= 23004

dpsRTUp22005Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 5 is set"
	::= 22005

dpsRTUp23005Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 5 is cleared"
	::= 23005

dpsRTUp22006Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 6 is set"
	::= 22006

dpsRTUp23006Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 6 is cleared"
	::= 23006

dpsRTUp22007Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 7 is set"
	::= 22007

dpsRTUp23007Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 7 is cleared"
	::= 23007

dpsRTUp22008Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 8 is set"
	::= 22008

dpsRTUp23008Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 8 is cleared"
	::= 23008

dpsRTUp22009Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 9 is set"
	::= 22009

dpsRTUp23009Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 9 is cleared"
	::= 23009

dpsRTUp22010Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 10 is set"
	::= 22010

dpsRTUp23010Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 10 is cleared"
	::= 23010

dpsRTUp22011Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 11 is set"
	::= 22011

dpsRTUp23011Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 11 is cleared"
	::= 23011

dpsRTUp22012Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 12 is set"
	::= 22012

dpsRTUp23012Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 12 is cleared"
	::= 23012

dpsRTUp22013Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 13 is set"
	::= 22013

dpsRTUp23013Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 13 is cleared"
	::= 23013

dpsRTUp22014Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 14 is set"
	::= 22014

dpsRTUp23014Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 14 is cleared"
	::= 23014

dpsRTUp22015Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 15 is set"
	::= 22015

dpsRTUp23015Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 15 is cleared"
	::= 23015

dpsRTUp22016Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 16 is set"
	::= 22016

dpsRTUp23016Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 16 is cleared"
	::= 23016

dpsRTUp22017Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 17 is set"
	::= 22017

dpsRTUp23017Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 17 is cleared"
	::= 23017

dpsRTUp22018Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 18 is set"
	::= 22018

dpsRTUp23018Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 18 is cleared"
	::= 23018

dpsRTUp22019Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 19 is set"
	::= 22019

dpsRTUp23019Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 19 is cleared"
	::= 23019

dpsRTUp22020Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 20 is set"
	::= 22020

dpsRTUp23020Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 20 is cleared"
	::= 23020

dpsRTUp22021Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 21 is set"
	::= 22021

dpsRTUp23021Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 21 is cleared"
	::= 23021

dpsRTUp22022Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 22 is set"
	::= 22022

dpsRTUp23022Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 22 is cleared"
	::= 23022

dpsRTUp22023Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 23 is set"
	::= 22023

dpsRTUp23023Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 23 is cleared"
	::= 23023

dpsRTUp22024Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 24 is set"
	::= 22024

dpsRTUp23024Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 24 is cleared"
	::= 23024

dpsRTUp22025Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 25 is set"
	::= 22025

dpsRTUp23025Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 25 is cleared"
	::= 23025

dpsRTUp22026Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 26 is set"
	::= 22026

dpsRTUp23026Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 26 is cleared"
	::= 23026

dpsRTUp22027Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 27 is set"
	::= 22027

dpsRTUp23027Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 27 is cleared"
	::= 23027

dpsRTUp22028Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 28 is set"
	::= 22028

dpsRTUp23028Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 28 is cleared"
	::= 23028

dpsRTUp22029Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 29 is set"
	::= 22029

dpsRTUp23029Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 29 is cleared"
	::= 23029

dpsRTUp22030Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 30 is set"
	::= 22030

dpsRTUp23030Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 30 is cleared"
	::= 23030

dpsRTUp22031Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 31 is set"
	::= 22031

dpsRTUp23031Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 31 is cleared"
	::= 23031

dpsRTUp22032Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 32 is set"
	::= 22032

dpsRTUp23032Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 32 is cleared"
	::= 23032

dpsRTUp22033Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 33 is set"
	::= 22033

dpsRTUp23033Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 33 is cleared"
	::= 23033

dpsRTUp22034Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 34 is set"
	::= 22034

dpsRTUp23034Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 34 is cleared"
	::= 23034

dpsRTUp22035Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 35 is set"
	::= 22035

dpsRTUp23035Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 35 is cleared"
	::= 23035

dpsRTUp22036Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 36 is set"
	::= 22036

dpsRTUp23036Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 36 is cleared"
	::= 23036

dpsRTUp22037Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 37 is set"
	::= 22037

dpsRTUp23037Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 37 is cleared"
	::= 23037

dpsRTUp22038Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 38 is set"
	::= 22038

dpsRTUp23038Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 38 is cleared"
	::= 23038

dpsRTUp22039Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 39 is set"
	::= 22039

dpsRTUp23039Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 39 is cleared"
	::= 23039

dpsRTUp22040Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 40 is set"
	::= 22040

dpsRTUp23040Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 40 is cleared"
	::= 23040

dpsRTUp22041Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 41 is set"
	::= 22041

dpsRTUp23041Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 41 is cleared"
	::= 23041

dpsRTUp22042Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 42 is set"
	::= 22042

dpsRTUp23042Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 42 is cleared"
	::= 23042

dpsRTUp22043Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 43 is set"
	::= 22043

dpsRTUp23043Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 43 is cleared"
	::= 23043

dpsRTUp22044Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 44 is set"
	::= 22044

dpsRTUp23044Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 44 is cleared"
	::= 23044

dpsRTUp22045Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 45 is set"
	::= 22045

dpsRTUp23045Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 45 is cleared"
	::= 23045

dpsRTUp22046Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 46 is set"
	::= 22046

dpsRTUp23046Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 46 is cleared"
	::= 23046

dpsRTUp22047Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 47 is set"
	::= 22047

dpsRTUp23047Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 47 is cleared"
	::= 23047

dpsRTUp22048Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 48 is set"
	::= 22048

dpsRTUp23048Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 48 is cleared"
	::= 23048

dpsRTUp22049Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 49 is set"
	::= 22049

dpsRTUp23049Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 49 is cleared"
	::= 23049

dpsRTUp22050Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 50 is set"
	::= 22050

dpsRTUp23050Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 50 is cleared"
	::= 23050

dpsRTUp22051Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 51 is set"
	::= 22051

dpsRTUp23051Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 51 is cleared"
	::= 23051

dpsRTUp22052Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 52 is set"
	::= 22052

dpsRTUp23052Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 52 is cleared"
	::= 23052

dpsRTUp22053Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 53 is set"
	::= 22053

dpsRTUp23053Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 53 is cleared"
	::= 23053

dpsRTUp22054Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 54 is set"
	::= 22054

dpsRTUp23054Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 54 is cleared"
	::= 23054

dpsRTUp22055Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 55 is set"
	::= 22055

dpsRTUp23055Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 55 is cleared"
	::= 23055

dpsRTUp22056Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 56 is set"
	::= 22056

dpsRTUp23056Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 56 is cleared"
	::= 23056

dpsRTUp22057Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 57 is set"
	::= 22057

dpsRTUp23057Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 57 is cleared"
	::= 23057

dpsRTUp22058Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 58 is set"
	::= 22058

dpsRTUp23058Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 58 is cleared"
	::= 23058

dpsRTUp22059Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 59 is set"
	::= 22059

dpsRTUp23059Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 59 is cleared"
	::= 23059

dpsRTUp22060Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 60 is set"
	::= 22060

dpsRTUp23060Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 60 is cleared"
	::= 23060

dpsRTUp22061Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 61 is set"
	::= 22061

dpsRTUp23061Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 61 is cleared"
	::= 23061

dpsRTUp22062Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 62 is set"
	::= 22062

dpsRTUp23062Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 62 is cleared"
	::= 23062

dpsRTUp22063Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 63 is set"
	::= 22063

dpsRTUp23063Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 63 is cleared"
	::= 23063

dpsRTUp22064Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 64 is set"
	::= 22064

dpsRTUp23064Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 1 point 64 is cleared"
	::= 23064

dpsRTUp22065Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 1 is set"
	::= 22065

dpsRTUp23065Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 1 is cleared"
	::= 23065

dpsRTUp22066Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 2 is set"
	::= 22066

dpsRTUp23066Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 2 is cleared"
	::= 23066

dpsRTUp22067Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 3 is set"
	::= 22067

dpsRTUp23067Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 3 is cleared"
	::= 23067

dpsRTUp22068Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 4 is set"
	::= 22068

dpsRTUp23068Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 4 is cleared"
	::= 23068

dpsRTUp22069Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 5 is set"
	::= 22069

dpsRTUp23069Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 5 is cleared"
	::= 23069

dpsRTUp22070Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 6 is set"
	::= 22070

dpsRTUp23070Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 6 is cleared"
	::= 23070

dpsRTUp22071Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 7 is set"
	::= 22071

dpsRTUp23071Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 7 is cleared"
	::= 23071

dpsRTUp22072Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 8 is set"
	::= 22072

dpsRTUp23072Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 8 is cleared"
	::= 23072

dpsRTUp22073Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 9 is set"
	::= 22073

dpsRTUp23073Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 9 is cleared"
	::= 23073

dpsRTUp22074Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 10 is set"
	::= 22074

dpsRTUp23074Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 10 is cleared"
	::= 23074

dpsRTUp22075Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 11 is set"
	::= 22075

dpsRTUp23075Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 11 is cleared"
	::= 23075

dpsRTUp22076Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 12 is set"
	::= 22076

dpsRTUp23076Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 12 is cleared"
	::= 23076

dpsRTUp22077Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 13 is set"
	::= 22077

dpsRTUp23077Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 13 is cleared"
	::= 23077

dpsRTUp22078Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 14 is set"
	::= 22078

dpsRTUp23078Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 14 is cleared"
	::= 23078

dpsRTUp22079Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 15 is set"
	::= 22079

dpsRTUp23079Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 15 is cleared"
	::= 23079

dpsRTUp22080Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 16 is set"
	::= 22080

dpsRTUp23080Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 16 is cleared"
	::= 23080

dpsRTUp22081Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 17 is set"
	::= 22081

dpsRTUp23081Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 17 is cleared"
	::= 23081

dpsRTUp22082Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 18 is set"
	::= 22082

dpsRTUp23082Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 18 is cleared"
	::= 23082

dpsRTUp22083Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 19 is set"
	::= 22083

dpsRTUp23083Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 19 is cleared"
	::= 23083

dpsRTUp22084Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 20 is set"
	::= 22084

dpsRTUp23084Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 20 is cleared"
	::= 23084

dpsRTUp22085Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 21 is set"
	::= 22085

dpsRTUp23085Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 21 is cleared"
	::= 23085

dpsRTUp22086Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 22 is set"
	::= 22086

dpsRTUp23086Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 22 is cleared"
	::= 23086

dpsRTUp22087Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 23 is set"
	::= 22087

dpsRTUp23087Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 23 is cleared"
	::= 23087

dpsRTUp22088Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 24 is set"
	::= 22088

dpsRTUp23088Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 24 is cleared"
	::= 23088

dpsRTUp22089Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 25 is set"
	::= 22089

dpsRTUp23089Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 25 is cleared"
	::= 23089

dpsRTUp22090Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 26 is set"
	::= 22090

dpsRTUp23090Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 26 is cleared"
	::= 23090

dpsRTUp22091Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 27 is set"
	::= 22091

dpsRTUp23091Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 27 is cleared"
	::= 23091

dpsRTUp22092Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 28 is set"
	::= 22092

dpsRTUp23092Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 28 is cleared"
	::= 23092

dpsRTUp22093Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 29 is set"
	::= 22093

dpsRTUp23093Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 29 is cleared"
	::= 23093

dpsRTUp22094Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 30 is set"
	::= 22094

dpsRTUp23094Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 30 is cleared"
	::= 23094

dpsRTUp22095Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 31 is set"
	::= 22095

dpsRTUp23095Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 31 is cleared"
	::= 23095

dpsRTUp22096Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 32 is set"
	::= 22096

dpsRTUp23096Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 32 is cleared"
	::= 23096

dpsRTUp22097Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 33 is set"
	::= 22097

dpsRTUp23097Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 33 is cleared"
	::= 23097

dpsRTUp22098Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 34 is set"
	::= 22098

dpsRTUp23098Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 34 is cleared"
	::= 23098

dpsRTUp22099Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 35 is set"
	::= 22099

dpsRTUp23099Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 35 is cleared"
	::= 23099

dpsRTUp22100Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 36 is set"
	::= 22100

dpsRTUp23100Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 36 is cleared"
	::= 23100

dpsRTUp22101Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 37 is set"
	::= 22101

dpsRTUp23101Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 37 is cleared"
	::= 23101

dpsRTUp22102Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 38 is set"
	::= 22102

dpsRTUp23102Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 38 is cleared"
	::= 23102

dpsRTUp22103Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 39 is set"
	::= 22103

dpsRTUp23103Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 39 is cleared"
	::= 23103

dpsRTUp22104Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 40 is set"
	::= 22104

dpsRTUp23104Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 40 is cleared"
	::= 23104

dpsRTUp22105Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 41 is set"
	::= 22105

dpsRTUp23105Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 41 is cleared"
	::= 23105

dpsRTUp22106Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 42 is set"
	::= 22106

dpsRTUp23106Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 42 is cleared"
	::= 23106

dpsRTUp22107Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 43 is set"
	::= 22107

dpsRTUp23107Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 43 is cleared"
	::= 23107

dpsRTUp22108Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 44 is set"
	::= 22108

dpsRTUp23108Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 44 is cleared"
	::= 23108

dpsRTUp22109Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 45 is set"
	::= 22109

dpsRTUp23109Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 45 is cleared"
	::= 23109

dpsRTUp22110Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 46 is set"
	::= 22110

dpsRTUp23110Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 46 is cleared"
	::= 23110

dpsRTUp22111Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 47 is set"
	::= 22111

dpsRTUp23111Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 47 is cleared"
	::= 23111

dpsRTUp22112Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 48 is set"
	::= 22112

dpsRTUp23112Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 48 is cleared"
	::= 23112

dpsRTUp22113Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 49 is set"
	::= 22113

dpsRTUp23113Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 49 is cleared"
	::= 23113

dpsRTUp22114Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 50 is set"
	::= 22114

dpsRTUp23114Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 50 is cleared"
	::= 23114

dpsRTUp22115Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 51 is set"
	::= 22115

dpsRTUp23115Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 51 is cleared"
	::= 23115

dpsRTUp22116Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 52 is set"
	::= 22116

dpsRTUp23116Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 52 is cleared"
	::= 23116

dpsRTUp22117Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 53 is set"
	::= 22117

dpsRTUp23117Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 53 is cleared"
	::= 23117

dpsRTUp22118Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 54 is set"
	::= 22118

dpsRTUp23118Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 54 is cleared"
	::= 23118

dpsRTUp22119Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 55 is set"
	::= 22119

dpsRTUp23119Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 55 is cleared"
	::= 23119

dpsRTUp22120Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 56 is set"
	::= 22120

dpsRTUp23120Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 56 is cleared"
	::= 23120

dpsRTUp22121Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 57 is set"
	::= 22121

dpsRTUp23121Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 57 is cleared"
	::= 23121

dpsRTUp22122Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 58 is set"
	::= 22122

dpsRTUp23122Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 58 is cleared"
	::= 23122

dpsRTUp22123Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 59 is set"
	::= 22123

dpsRTUp23123Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 59 is cleared"
	::= 23123

dpsRTUp22124Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 60 is set"
	::= 22124

dpsRTUp23124Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 60 is cleared"
	::= 23124

dpsRTUp22125Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 61 is set"
	::= 22125

dpsRTUp23125Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 61 is cleared"
	::= 23125

dpsRTUp22126Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 62 is set"
	::= 22126

dpsRTUp23126Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 62 is cleared"
	::= 23126

dpsRTUp22127Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 63 is set"
	::= 22127

dpsRTUp23127Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 63 is cleared"
	::= 23127

dpsRTUp22128Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 64 is set"
	::= 22128

dpsRTUp23128Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 2 point 64 is cleared"
	::= 23128

dpsRTUp22129Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 1 is set"
	::= 22129

dpsRTUp23129Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 1 is cleared"
	::= 23129

dpsRTUp22130Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 2 is set"
	::= 22130

dpsRTUp23130Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 2 is cleared"
	::= 23130

dpsRTUp22131Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 3 is set"
	::= 22131

dpsRTUp23131Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 3 is cleared"
	::= 23131

dpsRTUp22132Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 4 is set"
	::= 22132

dpsRTUp23132Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 4 is cleared"
	::= 23132

dpsRTUp22133Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 5 is set"
	::= 22133

dpsRTUp23133Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 5 is cleared"
	::= 23133

dpsRTUp22134Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 6 is set"
	::= 22134

dpsRTUp23134Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 6 is cleared"
	::= 23134

dpsRTUp22135Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 7 is set"
	::= 22135

dpsRTUp23135Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 7 is cleared"
	::= 23135

dpsRTUp22136Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 8 is set"
	::= 22136

dpsRTUp23136Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 8 is cleared"
	::= 23136

dpsRTUp22137Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 9 is set"
	::= 22137

dpsRTUp23137Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 9 is cleared"
	::= 23137

dpsRTUp22138Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 10 is set"
	::= 22138

dpsRTUp23138Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 10 is cleared"
	::= 23138

dpsRTUp22139Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 11 is set"
	::= 22139

dpsRTUp23139Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 11 is cleared"
	::= 23139

dpsRTUp22140Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 12 is set"
	::= 22140

dpsRTUp23140Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 12 is cleared"
	::= 23140

dpsRTUp22141Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 13 is set"
	::= 22141

dpsRTUp23141Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 13 is cleared"
	::= 23141

dpsRTUp22142Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 14 is set"
	::= 22142

dpsRTUp23142Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 14 is cleared"
	::= 23142

dpsRTUp22143Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 15 is set"
	::= 22143

dpsRTUp23143Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 15 is cleared"
	::= 23143

dpsRTUp22144Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 16 is set"
	::= 22144

dpsRTUp23144Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 16 is cleared"
	::= 23144

dpsRTUp22145Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 17 is set"
	::= 22145

dpsRTUp23145Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 17 is cleared"
	::= 23145

dpsRTUp22146Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 18 is set"
	::= 22146

dpsRTUp23146Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 18 is cleared"
	::= 23146

dpsRTUp22147Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 19 is set"
	::= 22147

dpsRTUp23147Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 19 is cleared"
	::= 23147

dpsRTUp22148Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 20 is set"
	::= 22148

dpsRTUp23148Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 20 is cleared"
	::= 23148

dpsRTUp22149Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 21 is set"
	::= 22149

dpsRTUp23149Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 21 is cleared"
	::= 23149

dpsRTUp22150Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 22 is set"
	::= 22150

dpsRTUp23150Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 22 is cleared"
	::= 23150

dpsRTUp22151Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 23 is set"
	::= 22151

dpsRTUp23151Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 23 is cleared"
	::= 23151

dpsRTUp22152Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 24 is set"
	::= 22152

dpsRTUp23152Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 24 is cleared"
	::= 23152

dpsRTUp22153Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 25 is set"
	::= 22153

dpsRTUp23153Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 25 is cleared"
	::= 23153

dpsRTUp22154Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 26 is set"
	::= 22154

dpsRTUp23154Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 26 is cleared"
	::= 23154

dpsRTUp22155Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 27 is set"
	::= 22155

dpsRTUp23155Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 27 is cleared"
	::= 23155

dpsRTUp22156Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 28 is set"
	::= 22156

dpsRTUp23156Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 28 is cleared"
	::= 23156

dpsRTUp22157Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 29 is set"
	::= 22157

dpsRTUp23157Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 29 is cleared"
	::= 23157

dpsRTUp22158Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 30 is set"
	::= 22158

dpsRTUp23158Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 30 is cleared"
	::= 23158

dpsRTUp22159Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 31 is set"
	::= 22159

dpsRTUp23159Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 31 is cleared"
	::= 23159

dpsRTUp22160Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 32 is set"
	::= 22160

dpsRTUp23160Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 32 is cleared"
	::= 23160

dpsRTUp22161Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 33 is set"
	::= 22161

dpsRTUp23161Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 33 is cleared"
	::= 23161

dpsRTUp22162Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 34 is set"
	::= 22162

dpsRTUp23162Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 34 is cleared"
	::= 23162

dpsRTUp22163Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 35 is set"
	::= 22163

dpsRTUp23163Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 35 is cleared"
	::= 23163

dpsRTUp22164Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 36 is set"
	::= 22164

dpsRTUp23164Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 36 is cleared"
	::= 23164

dpsRTUp22165Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 37 is set"
	::= 22165

dpsRTUp23165Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 37 is cleared"
	::= 23165

dpsRTUp22166Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 38 is set"
	::= 22166

dpsRTUp23166Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 38 is cleared"
	::= 23166

dpsRTUp22167Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 39 is set"
	::= 22167

dpsRTUp23167Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 39 is cleared"
	::= 23167

dpsRTUp22168Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 40 is set"
	::= 22168

dpsRTUp23168Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 40 is cleared"
	::= 23168

dpsRTUp22169Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 41 is set"
	::= 22169

dpsRTUp23169Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 41 is cleared"
	::= 23169

dpsRTUp22170Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 42 is set"
	::= 22170

dpsRTUp23170Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 42 is cleared"
	::= 23170

dpsRTUp22171Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 43 is set"
	::= 22171

dpsRTUp23171Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 43 is cleared"
	::= 23171

dpsRTUp22172Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 44 is set"
	::= 22172

dpsRTUp23172Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 44 is cleared"
	::= 23172

dpsRTUp22173Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 45 is set"
	::= 22173

dpsRTUp23173Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 45 is cleared"
	::= 23173

dpsRTUp22174Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 46 is set"
	::= 22174

dpsRTUp23174Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 46 is cleared"
	::= 23174

dpsRTUp22175Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 47 is set"
	::= 22175

dpsRTUp23175Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 47 is cleared"
	::= 23175

dpsRTUp22176Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 48 is set"
	::= 22176

dpsRTUp23176Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 48 is cleared"
	::= 23176

dpsRTUp22177Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 49 is set"
	::= 22177

dpsRTUp23177Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 49 is cleared"
	::= 23177

dpsRTUp22178Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 50 is set"
	::= 22178

dpsRTUp23178Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 50 is cleared"
	::= 23178

dpsRTUp22179Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 51 is set"
	::= 22179

dpsRTUp23179Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 51 is cleared"
	::= 23179

dpsRTUp22180Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 52 is set"
	::= 22180

dpsRTUp23180Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 52 is cleared"
	::= 23180

dpsRTUp22181Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 53 is set"
	::= 22181

dpsRTUp23181Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 53 is cleared"
	::= 23181

dpsRTUp22182Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 54 is set"
	::= 22182

dpsRTUp23182Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 54 is cleared"
	::= 23182

dpsRTUp22183Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 55 is set"
	::= 22183

dpsRTUp23183Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 55 is cleared"
	::= 23183

dpsRTUp22184Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 56 is set"
	::= 22184

dpsRTUp23184Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 56 is cleared"
	::= 23184

dpsRTUp22185Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 57 is set"
	::= 22185

dpsRTUp23185Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 57 is cleared"
	::= 23185

dpsRTUp22186Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 58 is set"
	::= 22186

dpsRTUp23186Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 58 is cleared"
	::= 23186

dpsRTUp22187Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 59 is set"
	::= 22187

dpsRTUp23187Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 59 is cleared"
	::= 23187

dpsRTUp22188Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 60 is set"
	::= 22188

dpsRTUp23188Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 60 is cleared"
	::= 23188

dpsRTUp22189Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 61 is set"
	::= 22189

dpsRTUp23189Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 61 is cleared"
	::= 23189

dpsRTUp22190Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 62 is set"
	::= 22190

dpsRTUp23190Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 62 is cleared"
	::= 23190

dpsRTUp22191Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 63 is set"
	::= 22191

dpsRTUp23191Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 63 is cleared"
	::= 23191

dpsRTUp22192Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 64 is set"
	::= 22192

dpsRTUp23192Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 3 point 64 is cleared"
	::= 23192

dpsRTUp22193Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 1 is set"
	::= 22193

dpsRTUp23193Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 1 is cleared"
	::= 23193

dpsRTUp22194Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 2 is set"
	::= 22194

dpsRTUp23194Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 2 is cleared"
	::= 23194

dpsRTUp22195Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 3 is set"
	::= 22195

dpsRTUp23195Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 3 is cleared"
	::= 23195

dpsRTUp22196Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 4 is set"
	::= 22196

dpsRTUp23196Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 4 is cleared"
	::= 23196

dpsRTUp22197Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 5 is set"
	::= 22197

dpsRTUp23197Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 5 is cleared"
	::= 23197

dpsRTUp22198Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 6 is set"
	::= 22198

dpsRTUp23198Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 6 is cleared"
	::= 23198

dpsRTUp22199Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 7 is set"
	::= 22199

dpsRTUp23199Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 7 is cleared"
	::= 23199

dpsRTUp22200Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 8 is set"
	::= 22200

dpsRTUp23200Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 8 is cleared"
	::= 23200

dpsRTUp22201Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 9 is set"
	::= 22201

dpsRTUp23201Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 9 is cleared"
	::= 23201

dpsRTUp22202Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 10 is set"
	::= 22202

dpsRTUp23202Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 10 is cleared"
	::= 23202

dpsRTUp22203Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 11 is set"
	::= 22203

dpsRTUp23203Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 11 is cleared"
	::= 23203

dpsRTUp22204Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 12 is set"
	::= 22204

dpsRTUp23204Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 12 is cleared"
	::= 23204

dpsRTUp22205Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 13 is set"
	::= 22205

dpsRTUp23205Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 13 is cleared"
	::= 23205

dpsRTUp22206Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 14 is set"
	::= 22206

dpsRTUp23206Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 14 is cleared"
	::= 23206

dpsRTUp22207Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 15 is set"
	::= 22207

dpsRTUp23207Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 15 is cleared"
	::= 23207

dpsRTUp22208Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 16 is set"
	::= 22208

dpsRTUp23208Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 16 is cleared"
	::= 23208

dpsRTUp22209Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 17 is set"
	::= 22209

dpsRTUp23209Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 17 is cleared"
	::= 23209

dpsRTUp22210Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 18 is set"
	::= 22210

dpsRTUp23210Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 18 is cleared"
	::= 23210

dpsRTUp22211Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 19 is set"
	::= 22211

dpsRTUp23211Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 19 is cleared"
	::= 23211

dpsRTUp22212Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 20 is set"
	::= 22212

dpsRTUp23212Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 20 is cleared"
	::= 23212

dpsRTUp22213Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 21 is set"
	::= 22213

dpsRTUp23213Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 21 is cleared"
	::= 23213

dpsRTUp22214Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 22 is set"
	::= 22214

dpsRTUp23214Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 22 is cleared"
	::= 23214

dpsRTUp22215Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 23 is set"
	::= 22215

dpsRTUp23215Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 23 is cleared"
	::= 23215

dpsRTUp22216Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 24 is set"
	::= 22216

dpsRTUp23216Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 24 is cleared"
	::= 23216

dpsRTUp22217Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 25 is set"
	::= 22217

dpsRTUp23217Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 25 is cleared"
	::= 23217

dpsRTUp22218Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 26 is set"
	::= 22218

dpsRTUp23218Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 26 is cleared"
	::= 23218

dpsRTUp22219Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 27 is set"
	::= 22219

dpsRTUp23219Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 27 is cleared"
	::= 23219

dpsRTUp22220Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 28 is set"
	::= 22220

dpsRTUp23220Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 28 is cleared"
	::= 23220

dpsRTUp22221Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 29 is set"
	::= 22221

dpsRTUp23221Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 29 is cleared"
	::= 23221

dpsRTUp22222Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 30 is set"
	::= 22222

dpsRTUp23222Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 30 is cleared"
	::= 23222

dpsRTUp22223Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 31 is set"
	::= 22223

dpsRTUp23223Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 31 is cleared"
	::= 23223

dpsRTUp22224Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 32 is set"
	::= 22224

dpsRTUp23224Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 32 is cleared"
	::= 23224

dpsRTUp22225Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 33 is set"
	::= 22225

dpsRTUp23225Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 33 is cleared"
	::= 23225

dpsRTUp22226Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 34 is set"
	::= 22226

dpsRTUp23226Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 34 is cleared"
	::= 23226

dpsRTUp22227Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 35 is set"
	::= 22227

dpsRTUp23227Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 35 is cleared"
	::= 23227

dpsRTUp22228Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 36 is set"
	::= 22228

dpsRTUp23228Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 36 is cleared"
	::= 23228

dpsRTUp22229Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 37 is set"
	::= 22229

dpsRTUp23229Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 37 is cleared"
	::= 23229

dpsRTUp22230Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 38 is set"
	::= 22230

dpsRTUp23230Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 38 is cleared"
	::= 23230

dpsRTUp22231Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 39 is set"
	::= 22231

dpsRTUp23231Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 39 is cleared"
	::= 23231

dpsRTUp22232Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 40 is set"
	::= 22232

dpsRTUp23232Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 40 is cleared"
	::= 23232

dpsRTUp22233Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 41 is set"
	::= 22233

dpsRTUp23233Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 41 is cleared"
	::= 23233

dpsRTUp22234Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 42 is set"
	::= 22234

dpsRTUp23234Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 42 is cleared"
	::= 23234

dpsRTUp22235Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 43 is set"
	::= 22235

dpsRTUp23235Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 43 is cleared"
	::= 23235

dpsRTUp22236Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 44 is set"
	::= 22236

dpsRTUp23236Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 44 is cleared"
	::= 23236

dpsRTUp22237Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 45 is set"
	::= 22237

dpsRTUp23237Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 45 is cleared"
	::= 23237

dpsRTUp22238Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 46 is set"
	::= 22238

dpsRTUp23238Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 46 is cleared"
	::= 23238

dpsRTUp22239Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 47 is set"
	::= 22239

dpsRTUp23239Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 47 is cleared"
	::= 23239

dpsRTUp22240Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 48 is set"
	::= 22240

dpsRTUp23240Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 48 is cleared"
	::= 23240

dpsRTUp22241Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 49 is set"
	::= 22241

dpsRTUp23241Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 49 is cleared"
	::= 23241

dpsRTUp22242Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 50 is set"
	::= 22242

dpsRTUp23242Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 50 is cleared"
	::= 23242

dpsRTUp22243Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 51 is set"
	::= 22243

dpsRTUp23243Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 51 is cleared"
	::= 23243

dpsRTUp22244Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 52 is set"
	::= 22244

dpsRTUp23244Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 52 is cleared"
	::= 23244

dpsRTUp22245Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 53 is set"
	::= 22245

dpsRTUp23245Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 53 is cleared"
	::= 23245

dpsRTUp22246Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 54 is set"
	::= 22246

dpsRTUp23246Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 54 is cleared"
	::= 23246

dpsRTUp22247Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 55 is set"
	::= 22247

dpsRTUp23247Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 55 is cleared"
	::= 23247

dpsRTUp22248Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 56 is set"
	::= 22248

dpsRTUp23248Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 56 is cleared"
	::= 23248

dpsRTUp22249Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 57 is set"
	::= 22249

dpsRTUp23249Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 57 is cleared"
	::= 23249

dpsRTUp22250Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 58 is set"
	::= 22250

dpsRTUp23250Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 58 is cleared"
	::= 23250

dpsRTUp22251Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 59 is set"
	::= 22251

dpsRTUp23251Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 59 is cleared"
	::= 23251

dpsRTUp22252Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 60 is set"
	::= 22252

dpsRTUp23252Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 60 is cleared"
	::= 23252

dpsRTUp22253Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 61 is set"
	::= 22253

dpsRTUp23253Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 61 is cleared"
	::= 23253

dpsRTUp22254Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 62 is set"
	::= 22254

dpsRTUp23254Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 62 is cleared"
	::= 23254

dpsRTUp22255Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 63 is set"
	::= 22255

dpsRTUp23255Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 63 is cleared"
	::= 23255

dpsRTUp22256Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 64 is set"
	::= 22256

dpsRTUp23256Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 4 point 64 is cleared"
	::= 23256

dpsRTUp22257Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 1 is set"
	::= 22257

dpsRTUp23257Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 1 is cleared"
	::= 23257

dpsRTUp22258Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 2 is set"
	::= 22258

dpsRTUp23258Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 2 is cleared"
	::= 23258

dpsRTUp22259Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 3 is set"
	::= 22259

dpsRTUp23259Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 3 is cleared"
	::= 23259

dpsRTUp22260Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 4 is set"
	::= 22260

dpsRTUp23260Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 4 is cleared"
	::= 23260

dpsRTUp22261Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 5 is set"
	::= 22261

dpsRTUp23261Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 5 is cleared"
	::= 23261

dpsRTUp22262Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 6 is set"
	::= 22262

dpsRTUp23262Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 6 is cleared"
	::= 23262

dpsRTUp22263Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 7 is set"
	::= 22263

dpsRTUp23263Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 7 is cleared"
	::= 23263

dpsRTUp22264Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 8 is set"
	::= 22264

dpsRTUp23264Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 8 is cleared"
	::= 23264

dpsRTUp22265Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 9 is set"
	::= 22265

dpsRTUp23265Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 9 is cleared"
	::= 23265

dpsRTUp22266Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 10 is set"
	::= 22266

dpsRTUp23266Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 10 is cleared"
	::= 23266

dpsRTUp22267Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 11 is set"
	::= 22267

dpsRTUp23267Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 11 is cleared"
	::= 23267

dpsRTUp22268Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 12 is set"
	::= 22268

dpsRTUp23268Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 12 is cleared"
	::= 23268

dpsRTUp22269Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 13 is set"
	::= 22269

dpsRTUp23269Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 13 is cleared"
	::= 23269

dpsRTUp22270Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 14 is set"
	::= 22270

dpsRTUp23270Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 14 is cleared"
	::= 23270

dpsRTUp22271Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 15 is set"
	::= 22271

dpsRTUp23271Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 15 is cleared"
	::= 23271

dpsRTUp22272Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 16 is set"
	::= 22272

dpsRTUp23272Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 16 is cleared"
	::= 23272

dpsRTUp22273Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 17 is set"
	::= 22273

dpsRTUp23273Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 17 is cleared"
	::= 23273

dpsRTUp22274Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 18 is set"
	::= 22274

dpsRTUp23274Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 18 is cleared"
	::= 23274

dpsRTUp22275Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 19 is set"
	::= 22275

dpsRTUp23275Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 19 is cleared"
	::= 23275

dpsRTUp22276Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 20 is set"
	::= 22276

dpsRTUp23276Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 20 is cleared"
	::= 23276

dpsRTUp22277Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 21 is set"
	::= 22277

dpsRTUp23277Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 21 is cleared"
	::= 23277

dpsRTUp22278Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 22 is set"
	::= 22278

dpsRTUp23278Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 22 is cleared"
	::= 23278

dpsRTUp22279Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 23 is set"
	::= 22279

dpsRTUp23279Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 23 is cleared"
	::= 23279

dpsRTUp22280Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 24 is set"
	::= 22280

dpsRTUp23280Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 24 is cleared"
	::= 23280

dpsRTUp22281Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 25 is set"
	::= 22281

dpsRTUp23281Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 25 is cleared"
	::= 23281

dpsRTUp22282Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 26 is set"
	::= 22282

dpsRTUp23282Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 26 is cleared"
	::= 23282

dpsRTUp22283Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 27 is set"
	::= 22283

dpsRTUp23283Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 27 is cleared"
	::= 23283

dpsRTUp22284Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 28 is set"
	::= 22284

dpsRTUp23284Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 28 is cleared"
	::= 23284

dpsRTUp22285Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 29 is set"
	::= 22285

dpsRTUp23285Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 29 is cleared"
	::= 23285

dpsRTUp22286Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 30 is set"
	::= 22286

dpsRTUp23286Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 30 is cleared"
	::= 23286

dpsRTUp22287Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 31 is set"
	::= 22287

dpsRTUp23287Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 31 is cleared"
	::= 23287

dpsRTUp22288Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 32 is set"
	::= 22288

dpsRTUp23288Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 32 is cleared"
	::= 23288

dpsRTUp22289Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 33 is set"
	::= 22289

dpsRTUp23289Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 33 is cleared"
	::= 23289

dpsRTUp22290Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 34 is set"
	::= 22290

dpsRTUp23290Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 34 is cleared"
	::= 23290

dpsRTUp22291Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 35 is set"
	::= 22291

dpsRTUp23291Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 35 is cleared"
	::= 23291

dpsRTUp22292Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 36 is set"
	::= 22292

dpsRTUp23292Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 36 is cleared"
	::= 23292

dpsRTUp22293Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 37 is set"
	::= 22293

dpsRTUp23293Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 37 is cleared"
	::= 23293

dpsRTUp22294Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 38 is set"
	::= 22294

dpsRTUp23294Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 38 is cleared"
	::= 23294

dpsRTUp22295Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 39 is set"
	::= 22295

dpsRTUp23295Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 39 is cleared"
	::= 23295

dpsRTUp22296Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 40 is set"
	::= 22296

dpsRTUp23296Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 40 is cleared"
	::= 23296

dpsRTUp22297Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 41 is set"
	::= 22297

dpsRTUp23297Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 41 is cleared"
	::= 23297

dpsRTUp22298Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 42 is set"
	::= 22298

dpsRTUp23298Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 42 is cleared"
	::= 23298

dpsRTUp22299Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 43 is set"
	::= 22299

dpsRTUp23299Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 43 is cleared"
	::= 23299

dpsRTUp22300Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 44 is set"
	::= 22300

dpsRTUp23300Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 44 is cleared"
	::= 23300

dpsRTUp22301Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 45 is set"
	::= 22301

dpsRTUp23301Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 45 is cleared"
	::= 23301

dpsRTUp22302Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 46 is set"
	::= 22302

dpsRTUp23302Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 46 is cleared"
	::= 23302

dpsRTUp22303Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 47 is set"
	::= 22303

dpsRTUp23303Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 47 is cleared"
	::= 23303

dpsRTUp22304Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 48 is set"
	::= 22304

dpsRTUp23304Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 48 is cleared"
	::= 23304

dpsRTUp22305Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 49 is set"
	::= 22305

dpsRTUp23305Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 49 is cleared"
	::= 23305

dpsRTUp22306Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 50 is set"
	::= 22306

dpsRTUp23306Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 50 is cleared"
	::= 23306

dpsRTUp22307Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 51 is set"
	::= 22307

dpsRTUp23307Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 51 is cleared"
	::= 23307

dpsRTUp22308Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 52 is set"
	::= 22308

dpsRTUp23308Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 52 is cleared"
	::= 23308

dpsRTUp22309Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 53 is set"
	::= 22309

dpsRTUp23309Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 53 is cleared"
	::= 23309

dpsRTUp22310Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 54 is set"
	::= 22310

dpsRTUp23310Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 54 is cleared"
	::= 23310

dpsRTUp22311Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 55 is set"
	::= 22311

dpsRTUp23311Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 55 is cleared"
	::= 23311

dpsRTUp22312Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 56 is set"
	::= 22312

dpsRTUp23312Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 56 is cleared"
	::= 23312

dpsRTUp22313Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 57 is set"
	::= 22313

dpsRTUp23313Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 57 is cleared"
	::= 23313

dpsRTUp22314Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 58 is set"
	::= 22314

dpsRTUp23314Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 58 is cleared"
	::= 23314

dpsRTUp22315Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 59 is set"
	::= 22315

dpsRTUp23315Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 59 is cleared"
	::= 23315

dpsRTUp22316Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 60 is set"
	::= 22316

dpsRTUp23316Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 60 is cleared"
	::= 23316

dpsRTUp22317Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 61 is set"
	::= 22317

dpsRTUp23317Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 61 is cleared"
	::= 23317

dpsRTUp22318Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 62 is set"
	::= 22318

dpsRTUp23318Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 62 is cleared"
	::= 23318

dpsRTUp22319Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 63 is set"
	::= 22319

dpsRTUp23319Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 63 is cleared"
	::= 23319

dpsRTUp22320Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 64 is set"
	::= 22320

dpsRTUp23320Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 5 point 64 is cleared"
	::= 23320

dpsRTUp22321Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 1 is set"
	::= 22321

dpsRTUp23321Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 1 is cleared"
	::= 23321

dpsRTUp22322Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 2 is set"
	::= 22322

dpsRTUp23322Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 2 is cleared"
	::= 23322

dpsRTUp22323Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 3 is set"
	::= 22323

dpsRTUp23323Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 3 is cleared"
	::= 23323

dpsRTUp22324Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 4 is set"
	::= 22324

dpsRTUp23324Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 4 is cleared"
	::= 23324

dpsRTUp22325Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 5 is set"
	::= 22325

dpsRTUp23325Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 5 is cleared"
	::= 23325

dpsRTUp22326Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 6 is set"
	::= 22326

dpsRTUp23326Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 6 is cleared"
	::= 23326

dpsRTUp22327Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 7 is set"
	::= 22327

dpsRTUp23327Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 7 is cleared"
	::= 23327

dpsRTUp22328Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 8 is set"
	::= 22328

dpsRTUp23328Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 8 is cleared"
	::= 23328

dpsRTUp22329Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 9 is set"
	::= 22329

dpsRTUp23329Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 9 is cleared"
	::= 23329

dpsRTUp22330Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 10 is set"
	::= 22330

dpsRTUp23330Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 10 is cleared"
	::= 23330

dpsRTUp22331Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 11 is set"
	::= 22331

dpsRTUp23331Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 11 is cleared"
	::= 23331

dpsRTUp22332Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 12 is set"
	::= 22332

dpsRTUp23332Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 12 is cleared"
	::= 23332

dpsRTUp22333Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 13 is set"
	::= 22333

dpsRTUp23333Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 13 is cleared"
	::= 23333

dpsRTUp22334Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 14 is set"
	::= 22334

dpsRTUp23334Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 14 is cleared"
	::= 23334

dpsRTUp22335Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 15 is set"
	::= 22335

dpsRTUp23335Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 15 is cleared"
	::= 23335

dpsRTUp22336Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 16 is set"
	::= 22336

dpsRTUp23336Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 16 is cleared"
	::= 23336

dpsRTUp22337Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 17 is set"
	::= 22337

dpsRTUp23337Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 17 is cleared"
	::= 23337

dpsRTUp22338Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 18 is set"
	::= 22338

dpsRTUp23338Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 18 is cleared"
	::= 23338

dpsRTUp22339Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 19 is set"
	::= 22339

dpsRTUp23339Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 19 is cleared"
	::= 23339

dpsRTUp22340Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 20 is set"
	::= 22340

dpsRTUp23340Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 20 is cleared"
	::= 23340

dpsRTUp22341Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 21 is set"
	::= 22341

dpsRTUp23341Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 21 is cleared"
	::= 23341

dpsRTUp22342Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 22 is set"
	::= 22342

dpsRTUp23342Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 22 is cleared"
	::= 23342

dpsRTUp22343Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 23 is set"
	::= 22343

dpsRTUp23343Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 23 is cleared"
	::= 23343

dpsRTUp22344Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 24 is set"
	::= 22344

dpsRTUp23344Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 24 is cleared"
	::= 23344

dpsRTUp22345Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 25 is set"
	::= 22345

dpsRTUp23345Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 25 is cleared"
	::= 23345

dpsRTUp22346Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 26 is set"
	::= 22346

dpsRTUp23346Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 26 is cleared"
	::= 23346

dpsRTUp22347Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 27 is set"
	::= 22347

dpsRTUp23347Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 27 is cleared"
	::= 23347

dpsRTUp22348Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 28 is set"
	::= 22348

dpsRTUp23348Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 28 is cleared"
	::= 23348

dpsRTUp22349Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 29 is set"
	::= 22349

dpsRTUp23349Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 29 is cleared"
	::= 23349

dpsRTUp22350Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 30 is set"
	::= 22350

dpsRTUp23350Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 30 is cleared"
	::= 23350

dpsRTUp22351Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 31 is set"
	::= 22351

dpsRTUp23351Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 31 is cleared"
	::= 23351

dpsRTUp22352Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 32 is set"
	::= 22352

dpsRTUp23352Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 32 is cleared"
	::= 23352

dpsRTUp22353Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 33 is set"
	::= 22353

dpsRTUp23353Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 33 is cleared"
	::= 23353

dpsRTUp22354Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 34 is set"
	::= 22354

dpsRTUp23354Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 34 is cleared"
	::= 23354

dpsRTUp22355Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 35 is set"
	::= 22355

dpsRTUp23355Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 35 is cleared"
	::= 23355

dpsRTUp22356Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 36 is set"
	::= 22356

dpsRTUp23356Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 36 is cleared"
	::= 23356

dpsRTUp22357Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 37 is set"
	::= 22357

dpsRTUp23357Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 37 is cleared"
	::= 23357

dpsRTUp22358Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 38 is set"
	::= 22358

dpsRTUp23358Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 38 is cleared"
	::= 23358

dpsRTUp22359Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 39 is set"
	::= 22359

dpsRTUp23359Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 39 is cleared"
	::= 23359

dpsRTUp22360Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 40 is set"
	::= 22360

dpsRTUp23360Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 40 is cleared"
	::= 23360

dpsRTUp22361Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 41 is set"
	::= 22361

dpsRTUp23361Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 41 is cleared"
	::= 23361

dpsRTUp22362Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 42 is set"
	::= 22362

dpsRTUp23362Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 42 is cleared"
	::= 23362

dpsRTUp22363Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 43 is set"
	::= 22363

dpsRTUp23363Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 43 is cleared"
	::= 23363

dpsRTUp22364Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 44 is set"
	::= 22364

dpsRTUp23364Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 44 is cleared"
	::= 23364

dpsRTUp22365Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 45 is set"
	::= 22365

dpsRTUp23365Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 45 is cleared"
	::= 23365

dpsRTUp22366Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 46 is set"
	::= 22366

dpsRTUp23366Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 46 is cleared"
	::= 23366

dpsRTUp22367Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 47 is set"
	::= 22367

dpsRTUp23367Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 47 is cleared"
	::= 23367

dpsRTUp22368Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 48 is set"
	::= 22368

dpsRTUp23368Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 48 is cleared"
	::= 23368

dpsRTUp22369Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 49 is set"
	::= 22369

dpsRTUp23369Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 49 is cleared"
	::= 23369

dpsRTUp22370Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 50 is set"
	::= 22370

dpsRTUp23370Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 50 is cleared"
	::= 23370

dpsRTUp22371Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 51 is set"
	::= 22371

dpsRTUp23371Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 51 is cleared"
	::= 23371

dpsRTUp22372Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 52 is set"
	::= 22372

dpsRTUp23372Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 52 is cleared"
	::= 23372

dpsRTUp22373Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 53 is set"
	::= 22373

dpsRTUp23373Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 53 is cleared"
	::= 23373

dpsRTUp22374Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 54 is set"
	::= 22374

dpsRTUp23374Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 54 is cleared"
	::= 23374

dpsRTUp22375Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 55 is set"
	::= 22375

dpsRTUp23375Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 55 is cleared"
	::= 23375

dpsRTUp22376Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 56 is set"
	::= 22376

dpsRTUp23376Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 56 is cleared"
	::= 23376

dpsRTUp22377Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 57 is set"
	::= 22377

dpsRTUp23377Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 57 is cleared"
	::= 23377

dpsRTUp22378Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 58 is set"
	::= 22378

dpsRTUp23378Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 58 is cleared"
	::= 23378

dpsRTUp22379Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 59 is set"
	::= 22379

dpsRTUp23379Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 59 is cleared"
	::= 23379

dpsRTUp22380Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 60 is set"
	::= 22380

dpsRTUp23380Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 60 is cleared"
	::= 23380

dpsRTUp22381Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 61 is set"
	::= 22381

dpsRTUp23381Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 61 is cleared"
	::= 23381

dpsRTUp22382Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 62 is set"
	::= 22382

dpsRTUp23382Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 62 is cleared"
	::= 23382

dpsRTUp22383Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 63 is set"
	::= 22383

dpsRTUp23383Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 63 is cleared"
	::= 23383

dpsRTUp22384Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 64 is set"
	::= 22384

dpsRTUp23384Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 6 point 64 is cleared"
	::= 23384

dpsRTUp22385Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 1 is set"
	::= 22385

dpsRTUp23385Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 1 is cleared"
	::= 23385

dpsRTUp22386Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 2 is set"
	::= 22386

dpsRTUp23386Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 2 is cleared"
	::= 23386

dpsRTUp22387Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 3 is set"
	::= 22387

dpsRTUp23387Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 3 is cleared"
	::= 23387

dpsRTUp22388Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 4 is set"
	::= 22388

dpsRTUp23388Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 4 is cleared"
	::= 23388

dpsRTUp22389Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 5 is set"
	::= 22389

dpsRTUp23389Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 5 is cleared"
	::= 23389

dpsRTUp22390Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 6 is set"
	::= 22390

dpsRTUp23390Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 6 is cleared"
	::= 23390

dpsRTUp22391Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 7 is set"
	::= 22391

dpsRTUp23391Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 7 is cleared"
	::= 23391

dpsRTUp22392Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 8 is set"
	::= 22392

dpsRTUp23392Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 8 is cleared"
	::= 23392

dpsRTUp22393Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 9 is set"
	::= 22393

dpsRTUp23393Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 9 is cleared"
	::= 23393

dpsRTUp22394Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 10 is set"
	::= 22394

dpsRTUp23394Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 10 is cleared"
	::= 23394

dpsRTUp22395Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 11 is set"
	::= 22395

dpsRTUp23395Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 11 is cleared"
	::= 23395

dpsRTUp22396Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 12 is set"
	::= 22396

dpsRTUp23396Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 12 is cleared"
	::= 23396

dpsRTUp22397Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 13 is set"
	::= 22397

dpsRTUp23397Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 13 is cleared"
	::= 23397

dpsRTUp22398Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 14 is set"
	::= 22398

dpsRTUp23398Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 14 is cleared"
	::= 23398

dpsRTUp22399Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 15 is set"
	::= 22399

dpsRTUp23399Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 15 is cleared"
	::= 23399

dpsRTUp22400Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 16 is set"
	::= 22400

dpsRTUp23400Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 16 is cleared"
	::= 23400

dpsRTUp22401Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 17 is set"
	::= 22401

dpsRTUp23401Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 17 is cleared"
	::= 23401

dpsRTUp22402Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 18 is set"
	::= 22402

dpsRTUp23402Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 18 is cleared"
	::= 23402

dpsRTUp22403Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 19 is set"
	::= 22403

dpsRTUp23403Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 19 is cleared"
	::= 23403

dpsRTUp22404Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 20 is set"
	::= 22404

dpsRTUp23404Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 20 is cleared"
	::= 23404

dpsRTUp22405Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 21 is set"
	::= 22405

dpsRTUp23405Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 21 is cleared"
	::= 23405

dpsRTUp22406Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 22 is set"
	::= 22406

dpsRTUp23406Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 22 is cleared"
	::= 23406

dpsRTUp22407Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 23 is set"
	::= 22407

dpsRTUp23407Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 23 is cleared"
	::= 23407

dpsRTUp22408Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 24 is set"
	::= 22408

dpsRTUp23408Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 24 is cleared"
	::= 23408

dpsRTUp22409Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 25 is set"
	::= 22409

dpsRTUp23409Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 25 is cleared"
	::= 23409

dpsRTUp22410Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 26 is set"
	::= 22410

dpsRTUp23410Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 26 is cleared"
	::= 23410

dpsRTUp22411Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 27 is set"
	::= 22411

dpsRTUp23411Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 27 is cleared"
	::= 23411

dpsRTUp22412Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 28 is set"
	::= 22412

dpsRTUp23412Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 28 is cleared"
	::= 23412

dpsRTUp22413Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 29 is set"
	::= 22413

dpsRTUp23413Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 29 is cleared"
	::= 23413

dpsRTUp22414Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 30 is set"
	::= 22414

dpsRTUp23414Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 30 is cleared"
	::= 23414

dpsRTUp22415Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 31 is set"
	::= 22415

dpsRTUp23415Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 31 is cleared"
	::= 23415

dpsRTUp22416Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 32 is set"
	::= 22416

dpsRTUp23416Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 32 is cleared"
	::= 23416

dpsRTUp22417Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 33 is set"
	::= 22417

dpsRTUp23417Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 33 is cleared"
	::= 23417

dpsRTUp22418Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 34 is set"
	::= 22418

dpsRTUp23418Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 34 is cleared"
	::= 23418

dpsRTUp22419Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 35 is set"
	::= 22419

dpsRTUp23419Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 35 is cleared"
	::= 23419

dpsRTUp22420Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 36 is set"
	::= 22420

dpsRTUp23420Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 36 is cleared"
	::= 23420

dpsRTUp22421Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 37 is set"
	::= 22421

dpsRTUp23421Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 37 is cleared"
	::= 23421

dpsRTUp22422Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 38 is set"
	::= 22422

dpsRTUp23422Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 38 is cleared"
	::= 23422

dpsRTUp22423Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 39 is set"
	::= 22423

dpsRTUp23423Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 39 is cleared"
	::= 23423

dpsRTUp22424Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 40 is set"
	::= 22424

dpsRTUp23424Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 40 is cleared"
	::= 23424

dpsRTUp22425Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 41 is set"
	::= 22425

dpsRTUp23425Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 41 is cleared"
	::= 23425

dpsRTUp22426Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 42 is set"
	::= 22426

dpsRTUp23426Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 42 is cleared"
	::= 23426

dpsRTUp22427Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 43 is set"
	::= 22427

dpsRTUp23427Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 43 is cleared"
	::= 23427

dpsRTUp22428Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 44 is set"
	::= 22428

dpsRTUp23428Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 44 is cleared"
	::= 23428

dpsRTUp22429Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 45 is set"
	::= 22429

dpsRTUp23429Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 45 is cleared"
	::= 23429

dpsRTUp22430Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 46 is set"
	::= 22430

dpsRTUp23430Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 46 is cleared"
	::= 23430

dpsRTUp22431Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 47 is set"
	::= 22431

dpsRTUp23431Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 47 is cleared"
	::= 23431

dpsRTUp22432Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 48 is set"
	::= 22432

dpsRTUp23432Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 48 is cleared"
	::= 23432

dpsRTUp22433Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 49 is set"
	::= 22433

dpsRTUp23433Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 49 is cleared"
	::= 23433

dpsRTUp22434Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 50 is set"
	::= 22434

dpsRTUp23434Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 50 is cleared"
	::= 23434

dpsRTUp22435Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 51 is set"
	::= 22435

dpsRTUp23435Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 51 is cleared"
	::= 23435

dpsRTUp22436Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 52 is set"
	::= 22436

dpsRTUp23436Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 52 is cleared"
	::= 23436

dpsRTUp22437Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 53 is set"
	::= 22437

dpsRTUp23437Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 53 is cleared"
	::= 23437

dpsRTUp22438Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 54 is set"
	::= 22438

dpsRTUp23438Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 54 is cleared"
	::= 23438

dpsRTUp22439Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 55 is set"
	::= 22439

dpsRTUp23439Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 55 is cleared"
	::= 23439

dpsRTUp22440Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 56 is set"
	::= 22440

dpsRTUp23440Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 56 is cleared"
	::= 23440

dpsRTUp22441Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 57 is set"
	::= 22441

dpsRTUp23441Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 57 is cleared"
	::= 23441

dpsRTUp22442Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 58 is set"
	::= 22442

dpsRTUp23442Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 58 is cleared"
	::= 23442

dpsRTUp22443Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 59 is set"
	::= 22443

dpsRTUp23443Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 59 is cleared"
	::= 23443

dpsRTUp22444Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 60 is set"
	::= 22444

dpsRTUp23444Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 60 is cleared"
	::= 23444

dpsRTUp22445Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 61 is set"
	::= 22445

dpsRTUp23445Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 61 is cleared"
	::= 23445

dpsRTUp22446Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 62 is set"
	::= 22446

dpsRTUp23446Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 62 is cleared"
	::= 23446

dpsRTUp22447Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 63 is set"
	::= 22447

dpsRTUp23447Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 63 is cleared"
	::= 23447

dpsRTUp22448Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 64 is set"
	::= 22448

dpsRTUp23448Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 7 point 64 is cleared"
	::= 23448

dpsRTUp22449Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 1 is set"
	::= 22449

dpsRTUp23449Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 1 is cleared"
	::= 23449

dpsRTUp22450Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 2 is set"
	::= 22450

dpsRTUp23450Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 2 is cleared"
	::= 23450

dpsRTUp22451Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 3 is set"
	::= 22451

dpsRTUp23451Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 3 is cleared"
	::= 23451

dpsRTUp22452Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 4 is set"
	::= 22452

dpsRTUp23452Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 4 is cleared"
	::= 23452

dpsRTUp22453Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 5 is set"
	::= 22453

dpsRTUp23453Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 5 is cleared"
	::= 23453

dpsRTUp22454Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 6 is set"
	::= 22454

dpsRTUp23454Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 6 is cleared"
	::= 23454

dpsRTUp22455Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 7 is set"
	::= 22455

dpsRTUp23455Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 7 is cleared"
	::= 23455

dpsRTUp22456Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 8 is set"
	::= 22456

dpsRTUp23456Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 8 is cleared"
	::= 23456

dpsRTUp22457Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 9 is set"
	::= 22457

dpsRTUp23457Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 9 is cleared"
	::= 23457

dpsRTUp22458Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 10 is set"
	::= 22458

dpsRTUp23458Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 10 is cleared"
	::= 23458

dpsRTUp22459Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 11 is set"
	::= 22459

dpsRTUp23459Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 11 is cleared"
	::= 23459

dpsRTUp22460Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 12 is set"
	::= 22460

dpsRTUp23460Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 12 is cleared"
	::= 23460

dpsRTUp22461Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 13 is set"
	::= 22461

dpsRTUp23461Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 13 is cleared"
	::= 23461

dpsRTUp22462Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 14 is set"
	::= 22462

dpsRTUp23462Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 14 is cleared"
	::= 23462

dpsRTUp22463Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 15 is set"
	::= 22463

dpsRTUp23463Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 15 is cleared"
	::= 23463

dpsRTUp22464Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 16 is set"
	::= 22464

dpsRTUp23464Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 16 is cleared"
	::= 23464

dpsRTUp22465Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 17 is set"
	::= 22465

dpsRTUp23465Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 17 is cleared"
	::= 23465

dpsRTUp22466Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 18 is set"
	::= 22466

dpsRTUp23466Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 18 is cleared"
	::= 23466

dpsRTUp22467Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 19 is set"
	::= 22467

dpsRTUp23467Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 19 is cleared"
	::= 23467

dpsRTUp22468Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 20 is set"
	::= 22468

dpsRTUp23468Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 20 is cleared"
	::= 23468

dpsRTUp22469Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 21 is set"
	::= 22469

dpsRTUp23469Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 21 is cleared"
	::= 23469

dpsRTUp22470Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 22 is set"
	::= 22470

dpsRTUp23470Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 22 is cleared"
	::= 23470

dpsRTUp22471Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 23 is set"
	::= 22471

dpsRTUp23471Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 23 is cleared"
	::= 23471

dpsRTUp22472Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 24 is set"
	::= 22472

dpsRTUp23472Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 24 is cleared"
	::= 23472

dpsRTUp22473Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 25 is set"
	::= 22473

dpsRTUp23473Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 25 is cleared"
	::= 23473

dpsRTUp22474Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 26 is set"
	::= 22474

dpsRTUp23474Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 26 is cleared"
	::= 23474

dpsRTUp22475Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 27 is set"
	::= 22475

dpsRTUp23475Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 27 is cleared"
	::= 23475

dpsRTUp22476Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 28 is set"
	::= 22476

dpsRTUp23476Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 28 is cleared"
	::= 23476

dpsRTUp22477Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 29 is set"
	::= 22477

dpsRTUp23477Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 29 is cleared"
	::= 23477

dpsRTUp22478Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 30 is set"
	::= 22478

dpsRTUp23478Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 30 is cleared"
	::= 23478

dpsRTUp22479Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 31 is set"
	::= 22479

dpsRTUp23479Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 31 is cleared"
	::= 23479

dpsRTUp22480Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 32 is set"
	::= 22480

dpsRTUp23480Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 32 is cleared"
	::= 23480

dpsRTUp22481Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 33 is set"
	::= 22481

dpsRTUp23481Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 33 is cleared"
	::= 23481

dpsRTUp22482Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 34 is set"
	::= 22482

dpsRTUp23482Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 34 is cleared"
	::= 23482

dpsRTUp22483Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 35 is set"
	::= 22483

dpsRTUp23483Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 35 is cleared"
	::= 23483

dpsRTUp22484Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 36 is set"
	::= 22484

dpsRTUp23484Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 36 is cleared"
	::= 23484

dpsRTUp22485Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 37 is set"
	::= 22485

dpsRTUp23485Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 37 is cleared"
	::= 23485

dpsRTUp22486Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 38 is set"
	::= 22486

dpsRTUp23486Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 38 is cleared"
	::= 23486

dpsRTUp22487Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 39 is set"
	::= 22487

dpsRTUp23487Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 39 is cleared"
	::= 23487

dpsRTUp22488Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 40 is set"
	::= 22488

dpsRTUp23488Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 40 is cleared"
	::= 23488

dpsRTUp22489Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 41 is set"
	::= 22489

dpsRTUp23489Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 41 is cleared"
	::= 23489

dpsRTUp22490Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 42 is set"
	::= 22490

dpsRTUp23490Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 42 is cleared"
	::= 23490

dpsRTUp22491Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 43 is set"
	::= 22491

dpsRTUp23491Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 43 is cleared"
	::= 23491

dpsRTUp22492Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 44 is set"
	::= 22492

dpsRTUp23492Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 44 is cleared"
	::= 23492

dpsRTUp22493Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 45 is set"
	::= 22493

dpsRTUp23493Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 45 is cleared"
	::= 23493

dpsRTUp22494Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 46 is set"
	::= 22494

dpsRTUp23494Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 46 is cleared"
	::= 23494

dpsRTUp22495Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 47 is set"
	::= 22495

dpsRTUp23495Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 47 is cleared"
	::= 23495

dpsRTUp22496Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 48 is set"
	::= 22496

dpsRTUp23496Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 48 is cleared"
	::= 23496

dpsRTUp22497Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 49 is set"
	::= 22497

dpsRTUp23497Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 49 is cleared"
	::= 23497

dpsRTUp22498Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 50 is set"
	::= 22498

dpsRTUp23498Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 50 is cleared"
	::= 23498

dpsRTUp22499Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 51 is set"
	::= 22499

dpsRTUp23499Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 51 is cleared"
	::= 23499

dpsRTUp22500Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 52 is set"
	::= 22500

dpsRTUp23500Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 52 is cleared"
	::= 23500

dpsRTUp22501Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 53 is set"
	::= 22501

dpsRTUp23501Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 53 is cleared"
	::= 23501

dpsRTUp22502Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 54 is set"
	::= 22502

dpsRTUp23502Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 54 is cleared"
	::= 23502

dpsRTUp22503Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 55 is set"
	::= 22503

dpsRTUp23503Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 55 is cleared"
	::= 23503

dpsRTUp22504Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 56 is set"
	::= 22504

dpsRTUp23504Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 56 is cleared"
	::= 23504

dpsRTUp22505Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 57 is set"
	::= 22505

dpsRTUp23505Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 57 is cleared"
	::= 23505

dpsRTUp22506Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 58 is set"
	::= 22506

dpsRTUp23506Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 58 is cleared"
	::= 23506

dpsRTUp22507Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 59 is set"
	::= 22507

dpsRTUp23507Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 59 is cleared"
	::= 23507

dpsRTUp22508Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 60 is set"
	::= 22508

dpsRTUp23508Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 60 is cleared"
	::= 23508

dpsRTUp22509Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 61 is set"
	::= 22509

dpsRTUp23509Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 61 is cleared"
	::= 23509

dpsRTUp22510Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 62 is set"
	::= 22510

dpsRTUp23510Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 62 is cleared"
	::= 23510

dpsRTUp22511Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 63 is set"
	::= 22511

dpsRTUp23511Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 63 is cleared"
	::= 23511

dpsRTUp22512Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 64 is set"
	::= 22512

dpsRTUp23512Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 7 display 8 point 64 is cleared"
	::= 23512

dpsRTUp24001Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 1 is set"
	::= 24001

dpsRTUp25001Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 1 is cleared"
	::= 25001

dpsRTUp24002Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 2 is set"
	::= 24002

dpsRTUp25002Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 2 is cleared"
	::= 25002

dpsRTUp24003Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 3 is set"
	::= 24003

dpsRTUp25003Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 3 is cleared"
	::= 25003

dpsRTUp24004Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 4 is set"
	::= 24004

dpsRTUp25004Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 4 is cleared"
	::= 25004

dpsRTUp24005Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 5 is set"
	::= 24005

dpsRTUp25005Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 5 is cleared"
	::= 25005

dpsRTUp24006Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 6 is set"
	::= 24006

dpsRTUp25006Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 6 is cleared"
	::= 25006

dpsRTUp24007Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 7 is set"
	::= 24007

dpsRTUp25007Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 7 is cleared"
	::= 25007

dpsRTUp24008Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 8 is set"
	::= 24008

dpsRTUp25008Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 8 is cleared"
	::= 25008

dpsRTUp24009Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 9 is set"
	::= 24009

dpsRTUp25009Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 9 is cleared"
	::= 25009

dpsRTUp24010Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 10 is set"
	::= 24010

dpsRTUp25010Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 10 is cleared"
	::= 25010

dpsRTUp24011Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 11 is set"
	::= 24011

dpsRTUp25011Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 11 is cleared"
	::= 25011

dpsRTUp24012Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 12 is set"
	::= 24012

dpsRTUp25012Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 12 is cleared"
	::= 25012

dpsRTUp24013Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 13 is set"
	::= 24013

dpsRTUp25013Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 13 is cleared"
	::= 25013

dpsRTUp24014Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 14 is set"
	::= 24014

dpsRTUp25014Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 14 is cleared"
	::= 25014

dpsRTUp24015Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 15 is set"
	::= 24015

dpsRTUp25015Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 15 is cleared"
	::= 25015

dpsRTUp24016Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 16 is set"
	::= 24016

dpsRTUp25016Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 16 is cleared"
	::= 25016

dpsRTUp24017Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 17 is set"
	::= 24017

dpsRTUp25017Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 17 is cleared"
	::= 25017

dpsRTUp24018Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 18 is set"
	::= 24018

dpsRTUp25018Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 18 is cleared"
	::= 25018

dpsRTUp24019Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 19 is set"
	::= 24019

dpsRTUp25019Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 19 is cleared"
	::= 25019

dpsRTUp24020Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 20 is set"
	::= 24020

dpsRTUp25020Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 20 is cleared"
	::= 25020

dpsRTUp24021Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 21 is set"
	::= 24021

dpsRTUp25021Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 21 is cleared"
	::= 25021

dpsRTUp24022Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 22 is set"
	::= 24022

dpsRTUp25022Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 22 is cleared"
	::= 25022

dpsRTUp24023Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 23 is set"
	::= 24023

dpsRTUp25023Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 23 is cleared"
	::= 25023

dpsRTUp24024Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 24 is set"
	::= 24024

dpsRTUp25024Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 24 is cleared"
	::= 25024

dpsRTUp24025Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 25 is set"
	::= 24025

dpsRTUp25025Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 25 is cleared"
	::= 25025

dpsRTUp24026Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 26 is set"
	::= 24026

dpsRTUp25026Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 26 is cleared"
	::= 25026

dpsRTUp24027Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 27 is set"
	::= 24027

dpsRTUp25027Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 27 is cleared"
	::= 25027

dpsRTUp24028Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 28 is set"
	::= 24028

dpsRTUp25028Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 28 is cleared"
	::= 25028

dpsRTUp24029Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 29 is set"
	::= 24029

dpsRTUp25029Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 29 is cleared"
	::= 25029

dpsRTUp24030Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 30 is set"
	::= 24030

dpsRTUp25030Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 30 is cleared"
	::= 25030

dpsRTUp24031Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 31 is set"
	::= 24031

dpsRTUp25031Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 31 is cleared"
	::= 25031

dpsRTUp24032Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 32 is set"
	::= 24032

dpsRTUp25032Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 32 is cleared"
	::= 25032

dpsRTUp24033Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 33 is set"
	::= 24033

dpsRTUp25033Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 33 is cleared"
	::= 25033

dpsRTUp24034Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 34 is set"
	::= 24034

dpsRTUp25034Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 34 is cleared"
	::= 25034

dpsRTUp24035Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 35 is set"
	::= 24035

dpsRTUp25035Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 35 is cleared"
	::= 25035

dpsRTUp24036Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 36 is set"
	::= 24036

dpsRTUp25036Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 36 is cleared"
	::= 25036

dpsRTUp24037Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 37 is set"
	::= 24037

dpsRTUp25037Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 37 is cleared"
	::= 25037

dpsRTUp24038Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 38 is set"
	::= 24038

dpsRTUp25038Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 38 is cleared"
	::= 25038

dpsRTUp24039Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 39 is set"
	::= 24039

dpsRTUp25039Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 39 is cleared"
	::= 25039

dpsRTUp24040Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 40 is set"
	::= 24040

dpsRTUp25040Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 40 is cleared"
	::= 25040

dpsRTUp24041Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 41 is set"
	::= 24041

dpsRTUp25041Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 41 is cleared"
	::= 25041

dpsRTUp24042Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 42 is set"
	::= 24042

dpsRTUp25042Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 42 is cleared"
	::= 25042

dpsRTUp24043Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 43 is set"
	::= 24043

dpsRTUp25043Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 43 is cleared"
	::= 25043

dpsRTUp24044Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 44 is set"
	::= 24044

dpsRTUp25044Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 44 is cleared"
	::= 25044

dpsRTUp24045Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 45 is set"
	::= 24045

dpsRTUp25045Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 45 is cleared"
	::= 25045

dpsRTUp24046Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 46 is set"
	::= 24046

dpsRTUp25046Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 46 is cleared"
	::= 25046

dpsRTUp24047Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 47 is set"
	::= 24047

dpsRTUp25047Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 47 is cleared"
	::= 25047

dpsRTUp24048Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 48 is set"
	::= 24048

dpsRTUp25048Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 48 is cleared"
	::= 25048

dpsRTUp24049Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 49 is set"
	::= 24049

dpsRTUp25049Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 49 is cleared"
	::= 25049

dpsRTUp24050Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 50 is set"
	::= 24050

dpsRTUp25050Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 50 is cleared"
	::= 25050

dpsRTUp24051Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 51 is set"
	::= 24051

dpsRTUp25051Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 51 is cleared"
	::= 25051

dpsRTUp24052Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 52 is set"
	::= 24052

dpsRTUp25052Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 52 is cleared"
	::= 25052

dpsRTUp24053Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 53 is set"
	::= 24053

dpsRTUp25053Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 53 is cleared"
	::= 25053

dpsRTUp24054Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 54 is set"
	::= 24054

dpsRTUp25054Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 54 is cleared"
	::= 25054

dpsRTUp24055Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 55 is set"
	::= 24055

dpsRTUp25055Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 55 is cleared"
	::= 25055

dpsRTUp24056Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 56 is set"
	::= 24056

dpsRTUp25056Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 56 is cleared"
	::= 25056

dpsRTUp24057Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 57 is set"
	::= 24057

dpsRTUp25057Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 57 is cleared"
	::= 25057

dpsRTUp24058Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 58 is set"
	::= 24058

dpsRTUp25058Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 58 is cleared"
	::= 25058

dpsRTUp24059Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 59 is set"
	::= 24059

dpsRTUp25059Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 59 is cleared"
	::= 25059

dpsRTUp24060Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 60 is set"
	::= 24060

dpsRTUp25060Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 60 is cleared"
	::= 25060

dpsRTUp24061Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 61 is set"
	::= 24061

dpsRTUp25061Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 61 is cleared"
	::= 25061

dpsRTUp24062Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 62 is set"
	::= 24062

dpsRTUp25062Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 62 is cleared"
	::= 25062

dpsRTUp24063Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 63 is set"
	::= 24063

dpsRTUp25063Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 63 is cleared"
	::= 25063

dpsRTUp24064Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 64 is set"
	::= 24064

dpsRTUp25064Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 1 point 64 is cleared"
	::= 25064

dpsRTUp24065Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 1 is set"
	::= 24065

dpsRTUp25065Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 1 is cleared"
	::= 25065

dpsRTUp24066Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 2 is set"
	::= 24066

dpsRTUp25066Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 2 is cleared"
	::= 25066

dpsRTUp24067Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 3 is set"
	::= 24067

dpsRTUp25067Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 3 is cleared"
	::= 25067

dpsRTUp24068Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 4 is set"
	::= 24068

dpsRTUp25068Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 4 is cleared"
	::= 25068

dpsRTUp24069Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 5 is set"
	::= 24069

dpsRTUp25069Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 5 is cleared"
	::= 25069

dpsRTUp24070Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 6 is set"
	::= 24070

dpsRTUp25070Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 6 is cleared"
	::= 25070

dpsRTUp24071Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 7 is set"
	::= 24071

dpsRTUp25071Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 7 is cleared"
	::= 25071

dpsRTUp24072Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 8 is set"
	::= 24072

dpsRTUp25072Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 8 is cleared"
	::= 25072

dpsRTUp24073Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 9 is set"
	::= 24073

dpsRTUp25073Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 9 is cleared"
	::= 25073

dpsRTUp24074Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 10 is set"
	::= 24074

dpsRTUp25074Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 10 is cleared"
	::= 25074

dpsRTUp24075Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 11 is set"
	::= 24075

dpsRTUp25075Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 11 is cleared"
	::= 25075

dpsRTUp24076Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 12 is set"
	::= 24076

dpsRTUp25076Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 12 is cleared"
	::= 25076

dpsRTUp24077Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 13 is set"
	::= 24077

dpsRTUp25077Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 13 is cleared"
	::= 25077

dpsRTUp24078Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 14 is set"
	::= 24078

dpsRTUp25078Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 14 is cleared"
	::= 25078

dpsRTUp24079Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 15 is set"
	::= 24079

dpsRTUp25079Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 15 is cleared"
	::= 25079

dpsRTUp24080Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 16 is set"
	::= 24080

dpsRTUp25080Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 16 is cleared"
	::= 25080

dpsRTUp24081Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 17 is set"
	::= 24081

dpsRTUp25081Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 17 is cleared"
	::= 25081

dpsRTUp24082Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 18 is set"
	::= 24082

dpsRTUp25082Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 18 is cleared"
	::= 25082

dpsRTUp24083Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 19 is set"
	::= 24083

dpsRTUp25083Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 19 is cleared"
	::= 25083

dpsRTUp24084Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 20 is set"
	::= 24084

dpsRTUp25084Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 20 is cleared"
	::= 25084

dpsRTUp24085Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 21 is set"
	::= 24085

dpsRTUp25085Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 21 is cleared"
	::= 25085

dpsRTUp24086Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 22 is set"
	::= 24086

dpsRTUp25086Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 22 is cleared"
	::= 25086

dpsRTUp24087Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 23 is set"
	::= 24087

dpsRTUp25087Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 23 is cleared"
	::= 25087

dpsRTUp24088Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 24 is set"
	::= 24088

dpsRTUp25088Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 24 is cleared"
	::= 25088

dpsRTUp24089Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 25 is set"
	::= 24089

dpsRTUp25089Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 25 is cleared"
	::= 25089

dpsRTUp24090Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 26 is set"
	::= 24090

dpsRTUp25090Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 26 is cleared"
	::= 25090

dpsRTUp24091Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 27 is set"
	::= 24091

dpsRTUp25091Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 27 is cleared"
	::= 25091

dpsRTUp24092Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 28 is set"
	::= 24092

dpsRTUp25092Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 28 is cleared"
	::= 25092

dpsRTUp24093Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 29 is set"
	::= 24093

dpsRTUp25093Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 29 is cleared"
	::= 25093

dpsRTUp24094Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 30 is set"
	::= 24094

dpsRTUp25094Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 30 is cleared"
	::= 25094

dpsRTUp24095Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 31 is set"
	::= 24095

dpsRTUp25095Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 31 is cleared"
	::= 25095

dpsRTUp24096Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 32 is set"
	::= 24096

dpsRTUp25096Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 32 is cleared"
	::= 25096

dpsRTUp24097Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 33 is set"
	::= 24097

dpsRTUp25097Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 33 is cleared"
	::= 25097

dpsRTUp24098Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 34 is set"
	::= 24098

dpsRTUp25098Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 34 is cleared"
	::= 25098

dpsRTUp24099Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 35 is set"
	::= 24099

dpsRTUp25099Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 35 is cleared"
	::= 25099

dpsRTUp24100Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 36 is set"
	::= 24100

dpsRTUp25100Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 36 is cleared"
	::= 25100

dpsRTUp24101Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 37 is set"
	::= 24101

dpsRTUp25101Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 37 is cleared"
	::= 25101

dpsRTUp24102Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 38 is set"
	::= 24102

dpsRTUp25102Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 38 is cleared"
	::= 25102

dpsRTUp24103Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 39 is set"
	::= 24103

dpsRTUp25103Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 39 is cleared"
	::= 25103

dpsRTUp24104Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 40 is set"
	::= 24104

dpsRTUp25104Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 40 is cleared"
	::= 25104

dpsRTUp24105Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 41 is set"
	::= 24105

dpsRTUp25105Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 41 is cleared"
	::= 25105

dpsRTUp24106Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 42 is set"
	::= 24106

dpsRTUp25106Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 42 is cleared"
	::= 25106

dpsRTUp24107Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 43 is set"
	::= 24107

dpsRTUp25107Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 43 is cleared"
	::= 25107

dpsRTUp24108Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 44 is set"
	::= 24108

dpsRTUp25108Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 44 is cleared"
	::= 25108

dpsRTUp24109Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 45 is set"
	::= 24109

dpsRTUp25109Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 45 is cleared"
	::= 25109

dpsRTUp24110Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 46 is set"
	::= 24110

dpsRTUp25110Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 46 is cleared"
	::= 25110

dpsRTUp24111Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 47 is set"
	::= 24111

dpsRTUp25111Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 47 is cleared"
	::= 25111

dpsRTUp24112Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 48 is set"
	::= 24112

dpsRTUp25112Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 48 is cleared"
	::= 25112

dpsRTUp24113Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 49 is set"
	::= 24113

dpsRTUp25113Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 49 is cleared"
	::= 25113

dpsRTUp24114Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 50 is set"
	::= 24114

dpsRTUp25114Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 50 is cleared"
	::= 25114

dpsRTUp24115Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 51 is set"
	::= 24115

dpsRTUp25115Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 51 is cleared"
	::= 25115

dpsRTUp24116Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 52 is set"
	::= 24116

dpsRTUp25116Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 52 is cleared"
	::= 25116

dpsRTUp24117Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 53 is set"
	::= 24117

dpsRTUp25117Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 53 is cleared"
	::= 25117

dpsRTUp24118Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 54 is set"
	::= 24118

dpsRTUp25118Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 54 is cleared"
	::= 25118

dpsRTUp24119Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 55 is set"
	::= 24119

dpsRTUp25119Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 55 is cleared"
	::= 25119

dpsRTUp24120Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 56 is set"
	::= 24120

dpsRTUp25120Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 56 is cleared"
	::= 25120

dpsRTUp24121Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 57 is set"
	::= 24121

dpsRTUp25121Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 57 is cleared"
	::= 25121

dpsRTUp24122Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 58 is set"
	::= 24122

dpsRTUp25122Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 58 is cleared"
	::= 25122

dpsRTUp24123Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 59 is set"
	::= 24123

dpsRTUp25123Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 59 is cleared"
	::= 25123

dpsRTUp24124Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 60 is set"
	::= 24124

dpsRTUp25124Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 60 is cleared"
	::= 25124

dpsRTUp24125Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 61 is set"
	::= 24125

dpsRTUp25125Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 61 is cleared"
	::= 25125

dpsRTUp24126Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 62 is set"
	::= 24126

dpsRTUp25126Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 62 is cleared"
	::= 25126

dpsRTUp24127Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 63 is set"
	::= 24127

dpsRTUp25127Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 63 is cleared"
	::= 25127

dpsRTUp24128Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 64 is set"
	::= 24128

dpsRTUp25128Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 2 point 64 is cleared"
	::= 25128

dpsRTUp24129Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 1 is set"
	::= 24129

dpsRTUp25129Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 1 is cleared"
	::= 25129

dpsRTUp24130Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 2 is set"
	::= 24130

dpsRTUp25130Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 2 is cleared"
	::= 25130

dpsRTUp24131Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 3 is set"
	::= 24131

dpsRTUp25131Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 3 is cleared"
	::= 25131

dpsRTUp24132Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 4 is set"
	::= 24132

dpsRTUp25132Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 4 is cleared"
	::= 25132

dpsRTUp24133Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 5 is set"
	::= 24133

dpsRTUp25133Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 5 is cleared"
	::= 25133

dpsRTUp24134Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 6 is set"
	::= 24134

dpsRTUp25134Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 6 is cleared"
	::= 25134

dpsRTUp24135Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 7 is set"
	::= 24135

dpsRTUp25135Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 7 is cleared"
	::= 25135

dpsRTUp24136Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 8 is set"
	::= 24136

dpsRTUp25136Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 8 is cleared"
	::= 25136

dpsRTUp24137Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 9 is set"
	::= 24137

dpsRTUp25137Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 9 is cleared"
	::= 25137

dpsRTUp24138Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 10 is set"
	::= 24138

dpsRTUp25138Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 10 is cleared"
	::= 25138

dpsRTUp24139Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 11 is set"
	::= 24139

dpsRTUp25139Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 11 is cleared"
	::= 25139

dpsRTUp24140Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 12 is set"
	::= 24140

dpsRTUp25140Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 12 is cleared"
	::= 25140

dpsRTUp24141Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 13 is set"
	::= 24141

dpsRTUp25141Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 13 is cleared"
	::= 25141

dpsRTUp24142Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 14 is set"
	::= 24142

dpsRTUp25142Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 14 is cleared"
	::= 25142

dpsRTUp24143Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 15 is set"
	::= 24143

dpsRTUp25143Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 15 is cleared"
	::= 25143

dpsRTUp24144Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 16 is set"
	::= 24144

dpsRTUp25144Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 16 is cleared"
	::= 25144

dpsRTUp24145Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 17 is set"
	::= 24145

dpsRTUp25145Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 17 is cleared"
	::= 25145

dpsRTUp24146Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 18 is set"
	::= 24146

dpsRTUp25146Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 18 is cleared"
	::= 25146

dpsRTUp24147Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 19 is set"
	::= 24147

dpsRTUp25147Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 19 is cleared"
	::= 25147

dpsRTUp24148Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 20 is set"
	::= 24148

dpsRTUp25148Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 20 is cleared"
	::= 25148

dpsRTUp24149Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 21 is set"
	::= 24149

dpsRTUp25149Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 21 is cleared"
	::= 25149

dpsRTUp24150Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 22 is set"
	::= 24150

dpsRTUp25150Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 22 is cleared"
	::= 25150

dpsRTUp24151Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 23 is set"
	::= 24151

dpsRTUp25151Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 23 is cleared"
	::= 25151

dpsRTUp24152Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 24 is set"
	::= 24152

dpsRTUp25152Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 24 is cleared"
	::= 25152

dpsRTUp24153Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 25 is set"
	::= 24153

dpsRTUp25153Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 25 is cleared"
	::= 25153

dpsRTUp24154Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 26 is set"
	::= 24154

dpsRTUp25154Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 26 is cleared"
	::= 25154

dpsRTUp24155Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 27 is set"
	::= 24155

dpsRTUp25155Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 27 is cleared"
	::= 25155

dpsRTUp24156Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 28 is set"
	::= 24156

dpsRTUp25156Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 28 is cleared"
	::= 25156

dpsRTUp24157Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 29 is set"
	::= 24157

dpsRTUp25157Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 29 is cleared"
	::= 25157

dpsRTUp24158Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 30 is set"
	::= 24158

dpsRTUp25158Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 30 is cleared"
	::= 25158

dpsRTUp24159Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 31 is set"
	::= 24159

dpsRTUp25159Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 31 is cleared"
	::= 25159

dpsRTUp24160Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 32 is set"
	::= 24160

dpsRTUp25160Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 32 is cleared"
	::= 25160

dpsRTUp24161Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 33 is set"
	::= 24161

dpsRTUp25161Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 33 is cleared"
	::= 25161

dpsRTUp24162Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 34 is set"
	::= 24162

dpsRTUp25162Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 34 is cleared"
	::= 25162

dpsRTUp24163Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 35 is set"
	::= 24163

dpsRTUp25163Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 35 is cleared"
	::= 25163

dpsRTUp24164Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 36 is set"
	::= 24164

dpsRTUp25164Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 36 is cleared"
	::= 25164

dpsRTUp24165Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 37 is set"
	::= 24165

dpsRTUp25165Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 37 is cleared"
	::= 25165

dpsRTUp24166Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 38 is set"
	::= 24166

dpsRTUp25166Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 38 is cleared"
	::= 25166

dpsRTUp24167Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 39 is set"
	::= 24167

dpsRTUp25167Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 39 is cleared"
	::= 25167

dpsRTUp24168Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 40 is set"
	::= 24168

dpsRTUp25168Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 40 is cleared"
	::= 25168

dpsRTUp24169Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 41 is set"
	::= 24169

dpsRTUp25169Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 41 is cleared"
	::= 25169

dpsRTUp24170Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 42 is set"
	::= 24170

dpsRTUp25170Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 42 is cleared"
	::= 25170

dpsRTUp24171Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 43 is set"
	::= 24171

dpsRTUp25171Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 43 is cleared"
	::= 25171

dpsRTUp24172Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 44 is set"
	::= 24172

dpsRTUp25172Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 44 is cleared"
	::= 25172

dpsRTUp24173Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 45 is set"
	::= 24173

dpsRTUp25173Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 45 is cleared"
	::= 25173

dpsRTUp24174Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 46 is set"
	::= 24174

dpsRTUp25174Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 46 is cleared"
	::= 25174

dpsRTUp24175Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 47 is set"
	::= 24175

dpsRTUp25175Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 47 is cleared"
	::= 25175

dpsRTUp24176Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 48 is set"
	::= 24176

dpsRTUp25176Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 48 is cleared"
	::= 25176

dpsRTUp24177Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 49 is set"
	::= 24177

dpsRTUp25177Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 49 is cleared"
	::= 25177

dpsRTUp24178Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 50 is set"
	::= 24178

dpsRTUp25178Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 50 is cleared"
	::= 25178

dpsRTUp24179Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 51 is set"
	::= 24179

dpsRTUp25179Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 51 is cleared"
	::= 25179

dpsRTUp24180Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 52 is set"
	::= 24180

dpsRTUp25180Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 52 is cleared"
	::= 25180

dpsRTUp24181Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 53 is set"
	::= 24181

dpsRTUp25181Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 53 is cleared"
	::= 25181

dpsRTUp24182Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 54 is set"
	::= 24182

dpsRTUp25182Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 54 is cleared"
	::= 25182

dpsRTUp24183Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 55 is set"
	::= 24183

dpsRTUp25183Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 55 is cleared"
	::= 25183

dpsRTUp24184Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 56 is set"
	::= 24184

dpsRTUp25184Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 56 is cleared"
	::= 25184

dpsRTUp24185Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 57 is set"
	::= 24185

dpsRTUp25185Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 57 is cleared"
	::= 25185

dpsRTUp24186Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 58 is set"
	::= 24186

dpsRTUp25186Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 58 is cleared"
	::= 25186

dpsRTUp24187Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 59 is set"
	::= 24187

dpsRTUp25187Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 59 is cleared"
	::= 25187

dpsRTUp24188Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 60 is set"
	::= 24188

dpsRTUp25188Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 60 is cleared"
	::= 25188

dpsRTUp24189Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 61 is set"
	::= 24189

dpsRTUp25189Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 61 is cleared"
	::= 25189

dpsRTUp24190Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 62 is set"
	::= 24190

dpsRTUp25190Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 62 is cleared"
	::= 25190

dpsRTUp24191Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 63 is set"
	::= 24191

dpsRTUp25191Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 63 is cleared"
	::= 25191

dpsRTUp24192Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 64 is set"
	::= 24192

dpsRTUp25192Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 3 point 64 is cleared"
	::= 25192

dpsRTUp24193Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 1 is set"
	::= 24193

dpsRTUp25193Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 1 is cleared"
	::= 25193

dpsRTUp24194Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 2 is set"
	::= 24194

dpsRTUp25194Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 2 is cleared"
	::= 25194

dpsRTUp24195Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 3 is set"
	::= 24195

dpsRTUp25195Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 3 is cleared"
	::= 25195

dpsRTUp24196Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 4 is set"
	::= 24196

dpsRTUp25196Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 4 is cleared"
	::= 25196

dpsRTUp24197Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 5 is set"
	::= 24197

dpsRTUp25197Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 5 is cleared"
	::= 25197

dpsRTUp24198Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 6 is set"
	::= 24198

dpsRTUp25198Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 6 is cleared"
	::= 25198

dpsRTUp24199Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 7 is set"
	::= 24199

dpsRTUp25199Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 7 is cleared"
	::= 25199

dpsRTUp24200Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 8 is set"
	::= 24200

dpsRTUp25200Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 8 is cleared"
	::= 25200

dpsRTUp24201Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 9 is set"
	::= 24201

dpsRTUp25201Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 9 is cleared"
	::= 25201

dpsRTUp24202Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 10 is set"
	::= 24202

dpsRTUp25202Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 10 is cleared"
	::= 25202

dpsRTUp24203Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 11 is set"
	::= 24203

dpsRTUp25203Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 11 is cleared"
	::= 25203

dpsRTUp24204Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 12 is set"
	::= 24204

dpsRTUp25204Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 12 is cleared"
	::= 25204

dpsRTUp24205Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 13 is set"
	::= 24205

dpsRTUp25205Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 13 is cleared"
	::= 25205

dpsRTUp24206Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 14 is set"
	::= 24206

dpsRTUp25206Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 14 is cleared"
	::= 25206

dpsRTUp24207Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 15 is set"
	::= 24207

dpsRTUp25207Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 15 is cleared"
	::= 25207

dpsRTUp24208Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 16 is set"
	::= 24208

dpsRTUp25208Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 16 is cleared"
	::= 25208

dpsRTUp24209Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 17 is set"
	::= 24209

dpsRTUp25209Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 17 is cleared"
	::= 25209

dpsRTUp24210Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 18 is set"
	::= 24210

dpsRTUp25210Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 18 is cleared"
	::= 25210

dpsRTUp24211Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 19 is set"
	::= 24211

dpsRTUp25211Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 19 is cleared"
	::= 25211

dpsRTUp24212Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 20 is set"
	::= 24212

dpsRTUp25212Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 20 is cleared"
	::= 25212

dpsRTUp24213Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 21 is set"
	::= 24213

dpsRTUp25213Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 21 is cleared"
	::= 25213

dpsRTUp24214Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 22 is set"
	::= 24214

dpsRTUp25214Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 22 is cleared"
	::= 25214

dpsRTUp24215Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 23 is set"
	::= 24215

dpsRTUp25215Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 23 is cleared"
	::= 25215

dpsRTUp24216Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 24 is set"
	::= 24216

dpsRTUp25216Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 24 is cleared"
	::= 25216

dpsRTUp24217Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 25 is set"
	::= 24217

dpsRTUp25217Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 25 is cleared"
	::= 25217

dpsRTUp24218Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 26 is set"
	::= 24218

dpsRTUp25218Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 26 is cleared"
	::= 25218

dpsRTUp24219Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 27 is set"
	::= 24219

dpsRTUp25219Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 27 is cleared"
	::= 25219

dpsRTUp24220Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 28 is set"
	::= 24220

dpsRTUp25220Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 28 is cleared"
	::= 25220

dpsRTUp24221Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 29 is set"
	::= 24221

dpsRTUp25221Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 29 is cleared"
	::= 25221

dpsRTUp24222Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 30 is set"
	::= 24222

dpsRTUp25222Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 30 is cleared"
	::= 25222

dpsRTUp24223Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 31 is set"
	::= 24223

dpsRTUp25223Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 31 is cleared"
	::= 25223

dpsRTUp24224Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 32 is set"
	::= 24224

dpsRTUp25224Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 32 is cleared"
	::= 25224

dpsRTUp24225Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 33 is set"
	::= 24225

dpsRTUp25225Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 33 is cleared"
	::= 25225

dpsRTUp24226Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 34 is set"
	::= 24226

dpsRTUp25226Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 34 is cleared"
	::= 25226

dpsRTUp24227Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 35 is set"
	::= 24227

dpsRTUp25227Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 35 is cleared"
	::= 25227

dpsRTUp24228Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 36 is set"
	::= 24228

dpsRTUp25228Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 36 is cleared"
	::= 25228

dpsRTUp24229Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 37 is set"
	::= 24229

dpsRTUp25229Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 37 is cleared"
	::= 25229

dpsRTUp24230Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 38 is set"
	::= 24230

dpsRTUp25230Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 38 is cleared"
	::= 25230

dpsRTUp24231Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 39 is set"
	::= 24231

dpsRTUp25231Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 39 is cleared"
	::= 25231

dpsRTUp24232Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 40 is set"
	::= 24232

dpsRTUp25232Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 40 is cleared"
	::= 25232

dpsRTUp24233Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 41 is set"
	::= 24233

dpsRTUp25233Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 41 is cleared"
	::= 25233

dpsRTUp24234Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 42 is set"
	::= 24234

dpsRTUp25234Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 42 is cleared"
	::= 25234

dpsRTUp24235Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 43 is set"
	::= 24235

dpsRTUp25235Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 43 is cleared"
	::= 25235

dpsRTUp24236Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 44 is set"
	::= 24236

dpsRTUp25236Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 44 is cleared"
	::= 25236

dpsRTUp24237Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 45 is set"
	::= 24237

dpsRTUp25237Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 45 is cleared"
	::= 25237

dpsRTUp24238Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 46 is set"
	::= 24238

dpsRTUp25238Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 46 is cleared"
	::= 25238

dpsRTUp24239Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 47 is set"
	::= 24239

dpsRTUp25239Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 47 is cleared"
	::= 25239

dpsRTUp24240Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 48 is set"
	::= 24240

dpsRTUp25240Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 48 is cleared"
	::= 25240

dpsRTUp24241Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 49 is set"
	::= 24241

dpsRTUp25241Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 49 is cleared"
	::= 25241

dpsRTUp24242Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 50 is set"
	::= 24242

dpsRTUp25242Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 50 is cleared"
	::= 25242

dpsRTUp24243Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 51 is set"
	::= 24243

dpsRTUp25243Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 51 is cleared"
	::= 25243

dpsRTUp24244Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 52 is set"
	::= 24244

dpsRTUp25244Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 52 is cleared"
	::= 25244

dpsRTUp24245Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 53 is set"
	::= 24245

dpsRTUp25245Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 53 is cleared"
	::= 25245

dpsRTUp24246Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 54 is set"
	::= 24246

dpsRTUp25246Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 54 is cleared"
	::= 25246

dpsRTUp24247Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 55 is set"
	::= 24247

dpsRTUp25247Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 55 is cleared"
	::= 25247

dpsRTUp24248Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 56 is set"
	::= 24248

dpsRTUp25248Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 56 is cleared"
	::= 25248

dpsRTUp24249Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 57 is set"
	::= 24249

dpsRTUp25249Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 57 is cleared"
	::= 25249

dpsRTUp24250Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 58 is set"
	::= 24250

dpsRTUp25250Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 58 is cleared"
	::= 25250

dpsRTUp24251Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 59 is set"
	::= 24251

dpsRTUp25251Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 59 is cleared"
	::= 25251

dpsRTUp24252Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 60 is set"
	::= 24252

dpsRTUp25252Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 60 is cleared"
	::= 25252

dpsRTUp24253Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 61 is set"
	::= 24253

dpsRTUp25253Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 61 is cleared"
	::= 25253

dpsRTUp24254Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 62 is set"
	::= 24254

dpsRTUp25254Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 62 is cleared"
	::= 25254

dpsRTUp24255Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 63 is set"
	::= 24255

dpsRTUp25255Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 63 is cleared"
	::= 25255

dpsRTUp24256Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 64 is set"
	::= 24256

dpsRTUp25256Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 4 point 64 is cleared"
	::= 25256

dpsRTUp24257Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 1 is set"
	::= 24257

dpsRTUp25257Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 1 is cleared"
	::= 25257

dpsRTUp24258Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 2 is set"
	::= 24258

dpsRTUp25258Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 2 is cleared"
	::= 25258

dpsRTUp24259Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 3 is set"
	::= 24259

dpsRTUp25259Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 3 is cleared"
	::= 25259

dpsRTUp24260Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 4 is set"
	::= 24260

dpsRTUp25260Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 4 is cleared"
	::= 25260

dpsRTUp24261Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 5 is set"
	::= 24261

dpsRTUp25261Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 5 is cleared"
	::= 25261

dpsRTUp24262Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 6 is set"
	::= 24262

dpsRTUp25262Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 6 is cleared"
	::= 25262

dpsRTUp24263Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 7 is set"
	::= 24263

dpsRTUp25263Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 7 is cleared"
	::= 25263

dpsRTUp24264Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 8 is set"
	::= 24264

dpsRTUp25264Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 8 is cleared"
	::= 25264

dpsRTUp24265Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 9 is set"
	::= 24265

dpsRTUp25265Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 9 is cleared"
	::= 25265

dpsRTUp24266Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 10 is set"
	::= 24266

dpsRTUp25266Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 10 is cleared"
	::= 25266

dpsRTUp24267Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 11 is set"
	::= 24267

dpsRTUp25267Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 11 is cleared"
	::= 25267

dpsRTUp24268Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 12 is set"
	::= 24268

dpsRTUp25268Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 12 is cleared"
	::= 25268

dpsRTUp24269Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 13 is set"
	::= 24269

dpsRTUp25269Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 13 is cleared"
	::= 25269

dpsRTUp24270Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 14 is set"
	::= 24270

dpsRTUp25270Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 14 is cleared"
	::= 25270

dpsRTUp24271Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 15 is set"
	::= 24271

dpsRTUp25271Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 15 is cleared"
	::= 25271

dpsRTUp24272Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 16 is set"
	::= 24272

dpsRTUp25272Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 16 is cleared"
	::= 25272

dpsRTUp24273Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 17 is set"
	::= 24273

dpsRTUp25273Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 17 is cleared"
	::= 25273

dpsRTUp24274Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 18 is set"
	::= 24274

dpsRTUp25274Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 18 is cleared"
	::= 25274

dpsRTUp24275Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 19 is set"
	::= 24275

dpsRTUp25275Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 19 is cleared"
	::= 25275

dpsRTUp24276Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 20 is set"
	::= 24276

dpsRTUp25276Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 20 is cleared"
	::= 25276

dpsRTUp24277Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 21 is set"
	::= 24277

dpsRTUp25277Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 21 is cleared"
	::= 25277

dpsRTUp24278Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 22 is set"
	::= 24278

dpsRTUp25278Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 22 is cleared"
	::= 25278

dpsRTUp24279Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 23 is set"
	::= 24279

dpsRTUp25279Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 23 is cleared"
	::= 25279

dpsRTUp24280Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 24 is set"
	::= 24280

dpsRTUp25280Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 24 is cleared"
	::= 25280

dpsRTUp24281Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 25 is set"
	::= 24281

dpsRTUp25281Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 25 is cleared"
	::= 25281

dpsRTUp24282Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 26 is set"
	::= 24282

dpsRTUp25282Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 26 is cleared"
	::= 25282

dpsRTUp24283Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 27 is set"
	::= 24283

dpsRTUp25283Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 27 is cleared"
	::= 25283

dpsRTUp24284Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 28 is set"
	::= 24284

dpsRTUp25284Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 28 is cleared"
	::= 25284

dpsRTUp24285Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 29 is set"
	::= 24285

dpsRTUp25285Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 29 is cleared"
	::= 25285

dpsRTUp24286Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 30 is set"
	::= 24286

dpsRTUp25286Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 30 is cleared"
	::= 25286

dpsRTUp24287Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 31 is set"
	::= 24287

dpsRTUp25287Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 31 is cleared"
	::= 25287

dpsRTUp24288Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 32 is set"
	::= 24288

dpsRTUp25288Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 32 is cleared"
	::= 25288

dpsRTUp24289Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 33 is set"
	::= 24289

dpsRTUp25289Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 33 is cleared"
	::= 25289

dpsRTUp24290Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 34 is set"
	::= 24290

dpsRTUp25290Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 34 is cleared"
	::= 25290

dpsRTUp24291Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 35 is set"
	::= 24291

dpsRTUp25291Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 35 is cleared"
	::= 25291

dpsRTUp24292Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 36 is set"
	::= 24292

dpsRTUp25292Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 36 is cleared"
	::= 25292

dpsRTUp24293Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 37 is set"
	::= 24293

dpsRTUp25293Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 37 is cleared"
	::= 25293

dpsRTUp24294Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 38 is set"
	::= 24294

dpsRTUp25294Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 38 is cleared"
	::= 25294

dpsRTUp24295Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 39 is set"
	::= 24295

dpsRTUp25295Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 39 is cleared"
	::= 25295

dpsRTUp24296Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 40 is set"
	::= 24296

dpsRTUp25296Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 40 is cleared"
	::= 25296

dpsRTUp24297Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 41 is set"
	::= 24297

dpsRTUp25297Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 41 is cleared"
	::= 25297

dpsRTUp24298Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 42 is set"
	::= 24298

dpsRTUp25298Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 42 is cleared"
	::= 25298

dpsRTUp24299Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 43 is set"
	::= 24299

dpsRTUp25299Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 43 is cleared"
	::= 25299

dpsRTUp24300Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 44 is set"
	::= 24300

dpsRTUp25300Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 44 is cleared"
	::= 25300

dpsRTUp24301Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 45 is set"
	::= 24301

dpsRTUp25301Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 45 is cleared"
	::= 25301

dpsRTUp24302Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 46 is set"
	::= 24302

dpsRTUp25302Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 46 is cleared"
	::= 25302

dpsRTUp24303Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 47 is set"
	::= 24303

dpsRTUp25303Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 47 is cleared"
	::= 25303

dpsRTUp24304Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 48 is set"
	::= 24304

dpsRTUp25304Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 48 is cleared"
	::= 25304

dpsRTUp24305Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 49 is set"
	::= 24305

dpsRTUp25305Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 49 is cleared"
	::= 25305

dpsRTUp24306Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 50 is set"
	::= 24306

dpsRTUp25306Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 50 is cleared"
	::= 25306

dpsRTUp24307Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 51 is set"
	::= 24307

dpsRTUp25307Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 51 is cleared"
	::= 25307

dpsRTUp24308Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 52 is set"
	::= 24308

dpsRTUp25308Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 52 is cleared"
	::= 25308

dpsRTUp24309Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 53 is set"
	::= 24309

dpsRTUp25309Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 53 is cleared"
	::= 25309

dpsRTUp24310Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 54 is set"
	::= 24310

dpsRTUp25310Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 54 is cleared"
	::= 25310

dpsRTUp24311Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 55 is set"
	::= 24311

dpsRTUp25311Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 55 is cleared"
	::= 25311

dpsRTUp24312Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 56 is set"
	::= 24312

dpsRTUp25312Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 56 is cleared"
	::= 25312

dpsRTUp24313Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 57 is set"
	::= 24313

dpsRTUp25313Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 57 is cleared"
	::= 25313

dpsRTUp24314Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 58 is set"
	::= 24314

dpsRTUp25314Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 58 is cleared"
	::= 25314

dpsRTUp24315Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 59 is set"
	::= 24315

dpsRTUp25315Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 59 is cleared"
	::= 25315

dpsRTUp24316Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 60 is set"
	::= 24316

dpsRTUp25316Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 60 is cleared"
	::= 25316

dpsRTUp24317Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 61 is set"
	::= 24317

dpsRTUp25317Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 61 is cleared"
	::= 25317

dpsRTUp24318Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 62 is set"
	::= 24318

dpsRTUp25318Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 62 is cleared"
	::= 25318

dpsRTUp24319Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 63 is set"
	::= 24319

dpsRTUp25319Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 63 is cleared"
	::= 25319

dpsRTUp24320Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 64 is set"
	::= 24320

dpsRTUp25320Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 5 point 64 is cleared"
	::= 25320

dpsRTUp24321Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 1 is set"
	::= 24321

dpsRTUp25321Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 1 is cleared"
	::= 25321

dpsRTUp24322Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 2 is set"
	::= 24322

dpsRTUp25322Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 2 is cleared"
	::= 25322

dpsRTUp24323Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 3 is set"
	::= 24323

dpsRTUp25323Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 3 is cleared"
	::= 25323

dpsRTUp24324Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 4 is set"
	::= 24324

dpsRTUp25324Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 4 is cleared"
	::= 25324

dpsRTUp24325Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 5 is set"
	::= 24325

dpsRTUp25325Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 5 is cleared"
	::= 25325

dpsRTUp24326Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 6 is set"
	::= 24326

dpsRTUp25326Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 6 is cleared"
	::= 25326

dpsRTUp24327Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 7 is set"
	::= 24327

dpsRTUp25327Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 7 is cleared"
	::= 25327

dpsRTUp24328Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 8 is set"
	::= 24328

dpsRTUp25328Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 8 is cleared"
	::= 25328

dpsRTUp24329Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 9 is set"
	::= 24329

dpsRTUp25329Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 9 is cleared"
	::= 25329

dpsRTUp24330Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 10 is set"
	::= 24330

dpsRTUp25330Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 10 is cleared"
	::= 25330

dpsRTUp24331Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 11 is set"
	::= 24331

dpsRTUp25331Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 11 is cleared"
	::= 25331

dpsRTUp24332Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 12 is set"
	::= 24332

dpsRTUp25332Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 12 is cleared"
	::= 25332

dpsRTUp24333Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 13 is set"
	::= 24333

dpsRTUp25333Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 13 is cleared"
	::= 25333

dpsRTUp24334Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 14 is set"
	::= 24334

dpsRTUp25334Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 14 is cleared"
	::= 25334

dpsRTUp24335Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 15 is set"
	::= 24335

dpsRTUp25335Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 15 is cleared"
	::= 25335

dpsRTUp24336Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 16 is set"
	::= 24336

dpsRTUp25336Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 16 is cleared"
	::= 25336

dpsRTUp24337Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 17 is set"
	::= 24337

dpsRTUp25337Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 17 is cleared"
	::= 25337

dpsRTUp24338Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 18 is set"
	::= 24338

dpsRTUp25338Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 18 is cleared"
	::= 25338

dpsRTUp24339Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 19 is set"
	::= 24339

dpsRTUp25339Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 19 is cleared"
	::= 25339

dpsRTUp24340Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 20 is set"
	::= 24340

dpsRTUp25340Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 20 is cleared"
	::= 25340

dpsRTUp24341Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 21 is set"
	::= 24341

dpsRTUp25341Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 21 is cleared"
	::= 25341

dpsRTUp24342Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 22 is set"
	::= 24342

dpsRTUp25342Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 22 is cleared"
	::= 25342

dpsRTUp24343Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 23 is set"
	::= 24343

dpsRTUp25343Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 23 is cleared"
	::= 25343

dpsRTUp24344Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 24 is set"
	::= 24344

dpsRTUp25344Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 24 is cleared"
	::= 25344

dpsRTUp24345Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 25 is set"
	::= 24345

dpsRTUp25345Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 25 is cleared"
	::= 25345

dpsRTUp24346Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 26 is set"
	::= 24346

dpsRTUp25346Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 26 is cleared"
	::= 25346

dpsRTUp24347Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 27 is set"
	::= 24347

dpsRTUp25347Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 27 is cleared"
	::= 25347

dpsRTUp24348Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 28 is set"
	::= 24348

dpsRTUp25348Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 28 is cleared"
	::= 25348

dpsRTUp24349Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 29 is set"
	::= 24349

dpsRTUp25349Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 29 is cleared"
	::= 25349

dpsRTUp24350Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 30 is set"
	::= 24350

dpsRTUp25350Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 30 is cleared"
	::= 25350

dpsRTUp24351Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 31 is set"
	::= 24351

dpsRTUp25351Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 31 is cleared"
	::= 25351

dpsRTUp24352Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 32 is set"
	::= 24352

dpsRTUp25352Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 32 is cleared"
	::= 25352

dpsRTUp24353Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 33 is set"
	::= 24353

dpsRTUp25353Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 33 is cleared"
	::= 25353

dpsRTUp24354Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 34 is set"
	::= 24354

dpsRTUp25354Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 34 is cleared"
	::= 25354

dpsRTUp24355Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 35 is set"
	::= 24355

dpsRTUp25355Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 35 is cleared"
	::= 25355

dpsRTUp24356Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 36 is set"
	::= 24356

dpsRTUp25356Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 36 is cleared"
	::= 25356

dpsRTUp24357Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 37 is set"
	::= 24357

dpsRTUp25357Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 37 is cleared"
	::= 25357

dpsRTUp24358Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 38 is set"
	::= 24358

dpsRTUp25358Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 38 is cleared"
	::= 25358

dpsRTUp24359Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 39 is set"
	::= 24359

dpsRTUp25359Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 39 is cleared"
	::= 25359

dpsRTUp24360Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 40 is set"
	::= 24360

dpsRTUp25360Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 40 is cleared"
	::= 25360

dpsRTUp24361Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 41 is set"
	::= 24361

dpsRTUp25361Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 41 is cleared"
	::= 25361

dpsRTUp24362Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 42 is set"
	::= 24362

dpsRTUp25362Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 42 is cleared"
	::= 25362

dpsRTUp24363Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 43 is set"
	::= 24363

dpsRTUp25363Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 43 is cleared"
	::= 25363

dpsRTUp24364Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 44 is set"
	::= 24364

dpsRTUp25364Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 44 is cleared"
	::= 25364

dpsRTUp24365Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 45 is set"
	::= 24365

dpsRTUp25365Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 45 is cleared"
	::= 25365

dpsRTUp24366Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 46 is set"
	::= 24366

dpsRTUp25366Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 46 is cleared"
	::= 25366

dpsRTUp24367Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 47 is set"
	::= 24367

dpsRTUp25367Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 47 is cleared"
	::= 25367

dpsRTUp24368Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 48 is set"
	::= 24368

dpsRTUp25368Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 48 is cleared"
	::= 25368

dpsRTUp24369Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 49 is set"
	::= 24369

dpsRTUp25369Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 49 is cleared"
	::= 25369

dpsRTUp24370Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 50 is set"
	::= 24370

dpsRTUp25370Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 50 is cleared"
	::= 25370

dpsRTUp24371Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 51 is set"
	::= 24371

dpsRTUp25371Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 51 is cleared"
	::= 25371

dpsRTUp24372Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 52 is set"
	::= 24372

dpsRTUp25372Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 52 is cleared"
	::= 25372

dpsRTUp24373Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 53 is set"
	::= 24373

dpsRTUp25373Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 53 is cleared"
	::= 25373

dpsRTUp24374Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 54 is set"
	::= 24374

dpsRTUp25374Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 54 is cleared"
	::= 25374

dpsRTUp24375Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 55 is set"
	::= 24375

dpsRTUp25375Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 55 is cleared"
	::= 25375

dpsRTUp24376Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 56 is set"
	::= 24376

dpsRTUp25376Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 56 is cleared"
	::= 25376

dpsRTUp24377Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 57 is set"
	::= 24377

dpsRTUp25377Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 57 is cleared"
	::= 25377

dpsRTUp24378Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 58 is set"
	::= 24378

dpsRTUp25378Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 58 is cleared"
	::= 25378

dpsRTUp24379Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 59 is set"
	::= 24379

dpsRTUp25379Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 59 is cleared"
	::= 25379

dpsRTUp24380Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 60 is set"
	::= 24380

dpsRTUp25380Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 60 is cleared"
	::= 25380

dpsRTUp24381Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 61 is set"
	::= 24381

dpsRTUp25381Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 61 is cleared"
	::= 25381

dpsRTUp24382Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 62 is set"
	::= 24382

dpsRTUp25382Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 62 is cleared"
	::= 25382

dpsRTUp24383Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 63 is set"
	::= 24383

dpsRTUp25383Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 63 is cleared"
	::= 25383

dpsRTUp24384Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 64 is set"
	::= 24384

dpsRTUp25384Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 6 point 64 is cleared"
	::= 25384

dpsRTUp24385Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 1 is set"
	::= 24385

dpsRTUp25385Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 1 is cleared"
	::= 25385

dpsRTUp24386Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 2 is set"
	::= 24386

dpsRTUp25386Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 2 is cleared"
	::= 25386

dpsRTUp24387Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 3 is set"
	::= 24387

dpsRTUp25387Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 3 is cleared"
	::= 25387

dpsRTUp24388Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 4 is set"
	::= 24388

dpsRTUp25388Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 4 is cleared"
	::= 25388

dpsRTUp24389Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 5 is set"
	::= 24389

dpsRTUp25389Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 5 is cleared"
	::= 25389

dpsRTUp24390Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 6 is set"
	::= 24390

dpsRTUp25390Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 6 is cleared"
	::= 25390

dpsRTUp24391Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 7 is set"
	::= 24391

dpsRTUp25391Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 7 is cleared"
	::= 25391

dpsRTUp24392Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 8 is set"
	::= 24392

dpsRTUp25392Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 8 is cleared"
	::= 25392

dpsRTUp24393Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 9 is set"
	::= 24393

dpsRTUp25393Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 9 is cleared"
	::= 25393

dpsRTUp24394Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 10 is set"
	::= 24394

dpsRTUp25394Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 10 is cleared"
	::= 25394

dpsRTUp24395Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 11 is set"
	::= 24395

dpsRTUp25395Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 11 is cleared"
	::= 25395

dpsRTUp24396Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 12 is set"
	::= 24396

dpsRTUp25396Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 12 is cleared"
	::= 25396

dpsRTUp24397Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 13 is set"
	::= 24397

dpsRTUp25397Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 13 is cleared"
	::= 25397

dpsRTUp24398Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 14 is set"
	::= 24398

dpsRTUp25398Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 14 is cleared"
	::= 25398

dpsRTUp24399Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 15 is set"
	::= 24399

dpsRTUp25399Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 15 is cleared"
	::= 25399

dpsRTUp24400Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 16 is set"
	::= 24400

dpsRTUp25400Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 16 is cleared"
	::= 25400

dpsRTUp24401Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 17 is set"
	::= 24401

dpsRTUp25401Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 17 is cleared"
	::= 25401

dpsRTUp24402Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 18 is set"
	::= 24402

dpsRTUp25402Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 18 is cleared"
	::= 25402

dpsRTUp24403Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 19 is set"
	::= 24403

dpsRTUp25403Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 19 is cleared"
	::= 25403

dpsRTUp24404Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 20 is set"
	::= 24404

dpsRTUp25404Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 20 is cleared"
	::= 25404

dpsRTUp24405Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 21 is set"
	::= 24405

dpsRTUp25405Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 21 is cleared"
	::= 25405

dpsRTUp24406Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 22 is set"
	::= 24406

dpsRTUp25406Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 22 is cleared"
	::= 25406

dpsRTUp24407Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 23 is set"
	::= 24407

dpsRTUp25407Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 23 is cleared"
	::= 25407

dpsRTUp24408Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 24 is set"
	::= 24408

dpsRTUp25408Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 24 is cleared"
	::= 25408

dpsRTUp24409Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 25 is set"
	::= 24409

dpsRTUp25409Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 25 is cleared"
	::= 25409

dpsRTUp24410Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 26 is set"
	::= 24410

dpsRTUp25410Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 26 is cleared"
	::= 25410

dpsRTUp24411Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 27 is set"
	::= 24411

dpsRTUp25411Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 27 is cleared"
	::= 25411

dpsRTUp24412Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 28 is set"
	::= 24412

dpsRTUp25412Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 28 is cleared"
	::= 25412

dpsRTUp24413Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 29 is set"
	::= 24413

dpsRTUp25413Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 29 is cleared"
	::= 25413

dpsRTUp24414Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 30 is set"
	::= 24414

dpsRTUp25414Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 30 is cleared"
	::= 25414

dpsRTUp24415Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 31 is set"
	::= 24415

dpsRTUp25415Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 31 is cleared"
	::= 25415

dpsRTUp24416Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 32 is set"
	::= 24416

dpsRTUp25416Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 32 is cleared"
	::= 25416

dpsRTUp24417Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 33 is set"
	::= 24417

dpsRTUp25417Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 33 is cleared"
	::= 25417

dpsRTUp24418Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 34 is set"
	::= 24418

dpsRTUp25418Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 34 is cleared"
	::= 25418

dpsRTUp24419Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 35 is set"
	::= 24419

dpsRTUp25419Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 35 is cleared"
	::= 25419

dpsRTUp24420Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 36 is set"
	::= 24420

dpsRTUp25420Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 36 is cleared"
	::= 25420

dpsRTUp24421Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 37 is set"
	::= 24421

dpsRTUp25421Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 37 is cleared"
	::= 25421

dpsRTUp24422Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 38 is set"
	::= 24422

dpsRTUp25422Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 38 is cleared"
	::= 25422

dpsRTUp24423Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 39 is set"
	::= 24423

dpsRTUp25423Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 39 is cleared"
	::= 25423

dpsRTUp24424Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 40 is set"
	::= 24424

dpsRTUp25424Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 40 is cleared"
	::= 25424

dpsRTUp24425Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 41 is set"
	::= 24425

dpsRTUp25425Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 41 is cleared"
	::= 25425

dpsRTUp24426Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 42 is set"
	::= 24426

dpsRTUp25426Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 42 is cleared"
	::= 25426

dpsRTUp24427Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 43 is set"
	::= 24427

dpsRTUp25427Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 43 is cleared"
	::= 25427

dpsRTUp24428Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 44 is set"
	::= 24428

dpsRTUp25428Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 44 is cleared"
	::= 25428

dpsRTUp24429Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 45 is set"
	::= 24429

dpsRTUp25429Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 45 is cleared"
	::= 25429

dpsRTUp24430Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 46 is set"
	::= 24430

dpsRTUp25430Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 46 is cleared"
	::= 25430

dpsRTUp24431Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 47 is set"
	::= 24431

dpsRTUp25431Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 47 is cleared"
	::= 25431

dpsRTUp24432Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 48 is set"
	::= 24432

dpsRTUp25432Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 48 is cleared"
	::= 25432

dpsRTUp24433Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 49 is set"
	::= 24433

dpsRTUp25433Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 49 is cleared"
	::= 25433

dpsRTUp24434Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 50 is set"
	::= 24434

dpsRTUp25434Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 50 is cleared"
	::= 25434

dpsRTUp24435Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 51 is set"
	::= 24435

dpsRTUp25435Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 51 is cleared"
	::= 25435

dpsRTUp24436Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 52 is set"
	::= 24436

dpsRTUp25436Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 52 is cleared"
	::= 25436

dpsRTUp24437Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 53 is set"
	::= 24437

dpsRTUp25437Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 53 is cleared"
	::= 25437

dpsRTUp24438Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 54 is set"
	::= 24438

dpsRTUp25438Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 54 is cleared"
	::= 25438

dpsRTUp24439Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 55 is set"
	::= 24439

dpsRTUp25439Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 55 is cleared"
	::= 25439

dpsRTUp24440Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 56 is set"
	::= 24440

dpsRTUp25440Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 56 is cleared"
	::= 25440

dpsRTUp24441Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 57 is set"
	::= 24441

dpsRTUp25441Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 57 is cleared"
	::= 25441

dpsRTUp24442Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 58 is set"
	::= 24442

dpsRTUp25442Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 58 is cleared"
	::= 25442

dpsRTUp24443Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 59 is set"
	::= 24443

dpsRTUp25443Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 59 is cleared"
	::= 25443

dpsRTUp24444Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 60 is set"
	::= 24444

dpsRTUp25444Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 60 is cleared"
	::= 25444

dpsRTUp24445Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 61 is set"
	::= 24445

dpsRTUp25445Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 61 is cleared"
	::= 25445

dpsRTUp24446Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 62 is set"
	::= 24446

dpsRTUp25446Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 62 is cleared"
	::= 25446

dpsRTUp24447Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 63 is set"
	::= 24447

dpsRTUp25447Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 63 is cleared"
	::= 25447

dpsRTUp24448Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 64 is set"
	::= 24448

dpsRTUp25448Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 7 point 64 is cleared"
	::= 25448

dpsRTUp24449Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 1 is set"
	::= 24449

dpsRTUp25449Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 1 is cleared"
	::= 25449

dpsRTUp24450Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 2 is set"
	::= 24450

dpsRTUp25450Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 2 is cleared"
	::= 25450

dpsRTUp24451Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 3 is set"
	::= 24451

dpsRTUp25451Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 3 is cleared"
	::= 25451

dpsRTUp24452Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 4 is set"
	::= 24452

dpsRTUp25452Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 4 is cleared"
	::= 25452

dpsRTUp24453Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 5 is set"
	::= 24453

dpsRTUp25453Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 5 is cleared"
	::= 25453

dpsRTUp24454Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 6 is set"
	::= 24454

dpsRTUp25454Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 6 is cleared"
	::= 25454

dpsRTUp24455Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 7 is set"
	::= 24455

dpsRTUp25455Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 7 is cleared"
	::= 25455

dpsRTUp24456Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 8 is set"
	::= 24456

dpsRTUp25456Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 8 is cleared"
	::= 25456

dpsRTUp24457Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 9 is set"
	::= 24457

dpsRTUp25457Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 9 is cleared"
	::= 25457

dpsRTUp24458Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 10 is set"
	::= 24458

dpsRTUp25458Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 10 is cleared"
	::= 25458

dpsRTUp24459Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 11 is set"
	::= 24459

dpsRTUp25459Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 11 is cleared"
	::= 25459

dpsRTUp24460Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 12 is set"
	::= 24460

dpsRTUp25460Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 12 is cleared"
	::= 25460

dpsRTUp24461Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 13 is set"
	::= 24461

dpsRTUp25461Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 13 is cleared"
	::= 25461

dpsRTUp24462Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 14 is set"
	::= 24462

dpsRTUp25462Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 14 is cleared"
	::= 25462

dpsRTUp24463Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 15 is set"
	::= 24463

dpsRTUp25463Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 15 is cleared"
	::= 25463

dpsRTUp24464Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 16 is set"
	::= 24464

dpsRTUp25464Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 16 is cleared"
	::= 25464

dpsRTUp24465Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 17 is set"
	::= 24465

dpsRTUp25465Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 17 is cleared"
	::= 25465

dpsRTUp24466Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 18 is set"
	::= 24466

dpsRTUp25466Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 18 is cleared"
	::= 25466

dpsRTUp24467Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 19 is set"
	::= 24467

dpsRTUp25467Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 19 is cleared"
	::= 25467

dpsRTUp24468Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 20 is set"
	::= 24468

dpsRTUp25468Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 20 is cleared"
	::= 25468

dpsRTUp24469Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 21 is set"
	::= 24469

dpsRTUp25469Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 21 is cleared"
	::= 25469

dpsRTUp24470Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 22 is set"
	::= 24470

dpsRTUp25470Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 22 is cleared"
	::= 25470

dpsRTUp24471Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 23 is set"
	::= 24471

dpsRTUp25471Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 23 is cleared"
	::= 25471

dpsRTUp24472Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 24 is set"
	::= 24472

dpsRTUp25472Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 24 is cleared"
	::= 25472

dpsRTUp24473Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 25 is set"
	::= 24473

dpsRTUp25473Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 25 is cleared"
	::= 25473

dpsRTUp24474Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 26 is set"
	::= 24474

dpsRTUp25474Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 26 is cleared"
	::= 25474

dpsRTUp24475Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 27 is set"
	::= 24475

dpsRTUp25475Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 27 is cleared"
	::= 25475

dpsRTUp24476Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 28 is set"
	::= 24476

dpsRTUp25476Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 28 is cleared"
	::= 25476

dpsRTUp24477Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 29 is set"
	::= 24477

dpsRTUp25477Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 29 is cleared"
	::= 25477

dpsRTUp24478Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 30 is set"
	::= 24478

dpsRTUp25478Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 30 is cleared"
	::= 25478

dpsRTUp24479Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 31 is set"
	::= 24479

dpsRTUp25479Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 31 is cleared"
	::= 25479

dpsRTUp24480Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 32 is set"
	::= 24480

dpsRTUp25480Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 32 is cleared"
	::= 25480

dpsRTUp24481Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 33 is set"
	::= 24481

dpsRTUp25481Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 33 is cleared"
	::= 25481

dpsRTUp24482Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 34 is set"
	::= 24482

dpsRTUp25482Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 34 is cleared"
	::= 25482

dpsRTUp24483Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 35 is set"
	::= 24483

dpsRTUp25483Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 35 is cleared"
	::= 25483

dpsRTUp24484Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 36 is set"
	::= 24484

dpsRTUp25484Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 36 is cleared"
	::= 25484

dpsRTUp24485Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 37 is set"
	::= 24485

dpsRTUp25485Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 37 is cleared"
	::= 25485

dpsRTUp24486Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 38 is set"
	::= 24486

dpsRTUp25486Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 38 is cleared"
	::= 25486

dpsRTUp24487Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 39 is set"
	::= 24487

dpsRTUp25487Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 39 is cleared"
	::= 25487

dpsRTUp24488Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 40 is set"
	::= 24488

dpsRTUp25488Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 40 is cleared"
	::= 25488

dpsRTUp24489Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 41 is set"
	::= 24489

dpsRTUp25489Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 41 is cleared"
	::= 25489

dpsRTUp24490Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 42 is set"
	::= 24490

dpsRTUp25490Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 42 is cleared"
	::= 25490

dpsRTUp24491Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 43 is set"
	::= 24491

dpsRTUp25491Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 43 is cleared"
	::= 25491

dpsRTUp24492Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 44 is set"
	::= 24492

dpsRTUp25492Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 44 is cleared"
	::= 25492

dpsRTUp24493Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 45 is set"
	::= 24493

dpsRTUp25493Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 45 is cleared"
	::= 25493

dpsRTUp24494Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 46 is set"
	::= 24494

dpsRTUp25494Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 46 is cleared"
	::= 25494

dpsRTUp24495Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 47 is set"
	::= 24495

dpsRTUp25495Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 47 is cleared"
	::= 25495

dpsRTUp24496Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 48 is set"
	::= 24496

dpsRTUp25496Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 48 is cleared"
	::= 25496

dpsRTUp24497Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 49 is set"
	::= 24497

dpsRTUp25497Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 49 is cleared"
	::= 25497

dpsRTUp24498Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 50 is set"
	::= 24498

dpsRTUp25498Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 50 is cleared"
	::= 25498

dpsRTUp24499Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 51 is set"
	::= 24499

dpsRTUp25499Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 51 is cleared"
	::= 25499

dpsRTUp24500Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 52 is set"
	::= 24500

dpsRTUp25500Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 52 is cleared"
	::= 25500

dpsRTUp24501Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 53 is set"
	::= 24501

dpsRTUp25501Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 53 is cleared"
	::= 25501

dpsRTUp24502Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 54 is set"
	::= 24502

dpsRTUp25502Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 54 is cleared"
	::= 25502

dpsRTUp24503Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 55 is set"
	::= 24503

dpsRTUp25503Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 55 is cleared"
	::= 25503

dpsRTUp24504Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 56 is set"
	::= 24504

dpsRTUp25504Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 56 is cleared"
	::= 25504

dpsRTUp24505Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 57 is set"
	::= 24505

dpsRTUp25505Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 57 is cleared"
	::= 25505

dpsRTUp24506Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 58 is set"
	::= 24506

dpsRTUp25506Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 58 is cleared"
	::= 25506

dpsRTUp24507Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 59 is set"
	::= 24507

dpsRTUp25507Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 59 is cleared"
	::= 25507

dpsRTUp24508Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 60 is set"
	::= 24508

dpsRTUp25508Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 60 is cleared"
	::= 25508

dpsRTUp24509Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 61 is set"
	::= 24509

dpsRTUp25509Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 61 is cleared"
	::= 25509

dpsRTUp24510Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 62 is set"
	::= 24510

dpsRTUp25510Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 62 is cleared"
	::= 25510

dpsRTUp24511Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 63 is set"
	::= 24511

dpsRTUp25511Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 63 is cleared"
	::= 25511

dpsRTUp24512Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 64 is set"
	::= 24512

dpsRTUp25512Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 8 display 8 point 64 is cleared"
::= 25512

END
