HUAWEI-ETHERNET-PORT-MIB DEFINITIONS ::= BEGIN

		IMPORTS 
			huaweiMgmt			
				FROM HUAWEI-MIB			
			ifIndex, InterfaceIndex
				FROM IF-MIB					
			 TimeTicks,OBJECT-TYPE
				FROM SNMPv2-SMI			
			TruthValue, MacAddress,RowStatus,TEXTUAL-CONVENTION			
				FROM SNMPv2-TC;

		hwEthernet MODULE-IDENTITY
			LAST-UPDATED "200207080900Z"
			ORGANIZATION
				"HAUWEI MIB Standard community
				固网MIB标准化委员会 "
			CONTACT-INFO
				"
				联系地址：中国广东深圳，华为技术有限公司
				"
			DESCRIPTION
				"V01_01_200207080900	
				评审专家：zengyonggang 26094/huawei, daiyuehua 20365/huawei, tongjian 28021/huawei, yuanminghui 31133/huawei, 
					   qizhenglin 27958/huawei, liwei 24366/huawei, zhoushiyong 10726/huawei lichangcai 28618/huawei, 
					   hebo 16103/huawei, xujinsong 19085/huawei, lvzhenfeng 18230/huawei, fuhongxun 29027/huawei, 
					   dongqing 18889/huawei,lijin 22251/huawei, zhangshilin 28161/huawei, heqingjian 9730/huawei, 
				          liuchenglong 25279/huawei			
			        "
			::= { huaweiMgmt 14 }
		
	
			PortList ::= TEXTUAL-CONVENTION
  				STATUS      current
    				DESCRIPTION
  				"Each octet within this value specifies a set of eight
 				       ports, with the first octet specifying ports 1 through
				       8, the second octet specifying ports 9 through 16, etc.
				        Within each octet, the most significant bit represents
 				       the lowest numbered port, and the least significant bit
 				       represents the highest numbered port.  Thus, each port
 				       of the bridge is represented by a single bit within the
				        value of this object.  If that bit has a value of '1'
				        then that port is included in the set of ports; the port
				        is not included if its bit has a value of '0'."
 			      SYNTAX      OCTET STRING

	
			

	
		hwExtInterface OBJECT IDENTIFIER ::= { hwEthernet 2 }
		
		hwifXXTable OBJECT-TYPE
			SYNTAX SEQUENCE OF HwIfXXEntry
			MAX-ACCESS not-accessible
			STATUS current
			DESCRIPTION
				"接口信息扩展信息  "
			::= { hwExtInterface 1 }
		
		hwifXXEntry OBJECT-TYPE
			SYNTAX HwIfXXEntry
			MAX-ACCESS not-accessible
			STATUS current
			DESCRIPTION
				" 接口信息扩展信息  "
			INDEX { ifIndex }
			::= { hwifXXTable 1 }
		
		HwIfXXEntry ::=
			SEQUENCE { 				
				hwifAggregatePort
					INTEGER,
				hwifMirrorPort
					TruthValue,
				hwifUnknowncastControl
					INTEGER,
				hwifMcastControl
					INTEGER,
				hwifFlowControl
					TruthValue,
				hwifSrcMacControl
					TruthValue,
				hwifClearStat
					INTEGER
			 }
		
		
		hwifAggregatePort OBJECT-TYPE
			SYNTAX INTEGER
				{
				noAggregatePort(1),     	 --不是聚合端口
				masterPort(2),	        	--聚合的主端口
				subPort(3)		        --聚合的从端口
				}
			MAX-ACCESS read-only
			STATUS current
			DESCRIPTION
				" 是否是聚合接口、聚合主端口和聚合从端口 "
			::= { hwifXXEntry 1 }
		
		hwifMirrorPort OBJECT-TYPE
			SYNTAX TruthValue
			MAX-ACCESS read-write
			STATUS current
			DESCRIPTION
				" 是否是镜像接口 "
			::= { hwifXXEntry 2 }
		
		hwifUnknowncastControl	OBJECT-TYPE
			SYNTAX INTEGER(5..100)
			MAX-ACCESS read-write
			STATUS current
			DESCRIPTION
				" 未知单播抑制流量节点,取值范围（5-100）％ "
			::= { hwifXXEntry 3 }
		
		hwifMcastControl OBJECT-TYPE
			SYNTAX INTEGER (5..100)
			MAX-ACCESS read-write
			STATUS current
			DESCRIPTION
				" 广播风暴抑制 ,取值范围（5-100）％ "
			::= { hwifXXEntry 4 }
		
		hwifFlowControl OBJECT-TYPE
			SYNTAX TruthValue
			MAX-ACCESS read-write
			STATUS current
			DESCRIPTION
				" 流控状态 "
			::= { hwifXXEntry 5 }
		
		hwifSrcMacControl OBJECT-TYPE
			SYNTAX TruthValue
			MAX-ACCESS read-write
			STATUS current
			DESCRIPTION
				" 是否进行源MAC地址过滤 "
			::= { hwifXXEntry 6 }
		
		hwifClearStat OBJECT-TYPE
			SYNTAX INTEGER { clear(1) }
		        MAX-ACCESS read-write
			STATUS current
			DESCRIPTION
				" 端口统计信息清零 "
			::= { hwifXXEntry 7 }
		
		hwifAggregateTable OBJECT-TYPE
			SYNTAX SEQUENCE OF HwIfAggregateEntry
			MAX-ACCESS not-accessible
			STATUS current
			DESCRIPTION
				" 端口聚合信息表  "
			::= { hwExtInterface 2 }
		
		hwifAggregateEntry OBJECT-TYPE
			SYNTAX HwIfAggregateEntry
			MAX-ACCESS not-accessible
			STATUS current
			DESCRIPTION
				" 端口聚合信息表  "
			INDEX { hwifAggregateIndex }
			::= { hwifAggregateTable 1 }
		
		HwIfAggregateEntry ::=
			SEQUENCE { 
				hwifAggregateIndex
					InterfaceIndex,
				hwifAggregatePortName
					OCTET STRING,
				hwifAggregatePortListPorts
					PortList,
				hwifAggregateModel
					INTEGER,
				hwifAggregateRowStatus
					RowStatus
			 }

		hwifAggregateIndex	OBJECT-TYPE
			SYNTAX InterfaceIndex
			MAX-ACCESS  read-only
			STATUS current
			DESCRIPTION
				" 聚合索引号 ,支持内部自编码（参考ifIndex，不同产品提供对hwifAggregateIndex的具体解释）
"
			::= { hwifAggregateEntry 1 }
		
		hwifAggregatePortName OBJECT-TYPE
			SYNTAX OCTET STRING (SIZE (0..40))
			MAX-ACCESS read-write
			STATUS current
			DESCRIPTION
				" 聚合组名 "
			::= { hwifAggregateEntry 2 }
		
		hwifAggregatePortListPorts OBJECT-TYPE
			SYNTAX PortList
			MAX-ACCESS read-write
			STATUS current
			DESCRIPTION
				"聚合端口列表
				portlist of a aggregating."
			::= { hwifAggregateEntry 3 }
		
		hwifAggregateModel OBJECT-TYPE
			SYNTAX INTEGER
				{
				ingress(1),
				ingressEgress(2),
				roundRobin(3),
				egress(4)
				}
			MAX-ACCESS read-write
			STATUS current
			DESCRIPTION
				" 端口聚合负荷分担模式 Ingress(1) Ingress+egress(2) Round_robin(3) "
			::= { hwifAggregateEntry 4 }
		
		hwifAggregateRowStatus OBJECT-TYPE
			SYNTAX RowStatus
			MAX-ACCESS read-create
			STATUS current
			DESCRIPTION
				" 当前该行的操作状态 "
			::= { hwifAggregateEntry 5 }
		
		hwL2IfMibObject OBJECT IDENTIFIER ::= { hwEthernet 1 }
		
		hwSlotPortMax OBJECT-TYPE
			SYNTAX INTEGER
			MAX-ACCESS read-only
			STATUS current
			DESCRIPTION
				"该槽的最大端口数
				Max ports of the slots"
			::= { hwL2IfMibObject 1 }
		
		hwSwitchPortMax OBJECT-TYPE
			SYNTAX INTEGER
			MAX-ACCESS read-only
			STATUS current
			DESCRIPTION
				"
				该switch包含的最大端口数
				Max ports that this switch include"
			::= { hwL2IfMibObject 2 }
	
		hwMacExpire OBJECT-TYPE
			SYNTAX TimeTicks
			MAX-ACCESS read-write
			STATUS current
			DESCRIPTION 
			" 
			MAC地址学习老化时间,单位秒 ，默认值480秒"
			::= { hwL2IfMibObject 3 }
			
			
		
		hwEthernetTable OBJECT-TYPE
			SYNTAX SEQUENCE OF HwEthernetEntry
			MAX-ACCESS not-accessible
			STATUS current
			DESCRIPTION
				" 以太网端口属性  "
			::= { hwL2IfMibObject 4 }
		
		hwEthernetEntry OBJECT-TYPE
			SYNTAX HwEthernetEntry
			MAX-ACCESS not-accessible
			STATUS current
			DESCRIPTION
				"  以太网端口属性  "
			INDEX { ifIndex }
			::= { hwEthernetTable 1 }
		
		HwEthernetEntry ::=
			SEQUENCE { 
				hwifEthernetDuplex
					INTEGER,
				hwifEthernetMTU
					INTEGER,
				hwifEthernetSpeed
					INTEGER,
				hwifEthernetLoopback
					INTEGER,
				hwifEthernetMdi
					INTEGER,
				hwMaxMacLearn
					INTEGER,
				hwifMacAddressLearn
					INTEGER,
				hwifTag
					INTEGER,
				hwifEthernetPeerNegotiate
					TruthValue,
				hwifEthernetNegotiate
					TruthValue,
				hwifEthernetPauseFrameTag
					TruthValue,
				hwifEthernetPauseFrameSending
					TruthValue,
				hwifEthernetVlanDefault
					INTEGER,
				hwifEthernetOnlineState
					TruthValue,
				hwifEthernetLineSelfAdaptMode
				        INTEGER
			 }

		hwifEthernetDuplex OBJECT-TYPE
			SYNTAX INTEGER
				{
				full(1),
				half(2),
				auto(3)
				}
			MAX-ACCESS read-write
			STATUS current
			DESCRIPTION
				" Ethernet接口工作模式 "
			::= { hwEthernetEntry 1 }
		
		hwifEthernetMTU OBJECT-TYPE
			SYNTAX INTEGER (0..1600)
			MAX-ACCESS read-write
			STATUS current
			DESCRIPTION
				" Ethernet接口 MTU  "
			::= { hwEthernetEntry 2 }
		
		hwifEthernetSpeed OBJECT-TYPE
			SYNTAX INTEGER
				{
				auto(0),
				s10M(10),
				s100M(100),
				s1000M(1000)
				}
			MAX-ACCESS read-write
			STATUS current
			DESCRIPTION
				" Ethernet接口速度 "
			::= { hwEthernetEntry 3 }
		
		hwifEthernetLoopback OBJECT-TYPE
			SYNTAX INTEGER
				{
				noloopback(1),
				internalloopback(2),
				externalloopback(3)
				}
			MAX-ACCESS read-write
			STATUS current
			DESCRIPTION
				" 端口环回测试 Noloopback        0：不环回, Internalloopback   1：局端环回,  externalloopback   2：远端环回, "
			::= { hwEthernetEntry 4 }
		
		hwifEthernetMdi OBJECT-TYPE
			SYNTAX INTEGER
				{
				mdiII(1),
				mdiX(2),
				mdiAuto(3)
				}
			MAX-ACCESS read-write
			STATUS current
			DESCRIPTION
				" 端口所接线路类型 MDI-II（直连线）：1  MDI-X（交叉线）：2  MDI-AUTO（自适应）：3 "
			::= { hwEthernetEntry 5 }
		
		hwMaxMacLearn OBJECT-TYPE
			SYNTAX INTEGER (0..600 | 65535)
			MAX-ACCESS read-write
			STATUS current
			DESCRIPTION
				" 端口可以学习到的最多的MAC地址数 "
			::= { hwEthernetEntry 6 }
		
		hwifMacAddressLearn OBJECT-TYPE
			SYNTAX INTEGER
				{
				enabled(1),
				disabled(2)
				}
			MAX-ACCESS read-write
			STATUS current
			DESCRIPTION
				"使能接口MAC地址自学习功能 
				Status indicates if the interface is
				allowed to learn mac address. eanbled(1) means the
				interface can learn mac address, otherwise disabled(2)
				can be setted. "
			::= { hwEthernetEntry 7 }
		
		hwifTag	OBJECT-TYPE
			SYNTAX INTEGER { 
				tag(1),    
				untag(2),
				multi(3)}  -- 混合模式
			MAX-ACCESS read-write
			STATUS current
			DESCRIPTION
				"
				以太端口类型
				"
			::= { hwEthernetEntry 8 }
	
		hwifEthernetNegotiate	OBJECT-TYPE
			SYNTAX TruthValue
			MAX-ACCESS read-write
			STATUS current
			DESCRIPTION
				"
				端口自协商节点
				"
			::= { hwEthernetEntry 9 }
	
		hwifEthernetPeerNegotiate	OBJECT-TYPE
			SYNTAX TruthValue
			MAX-ACCESS read-only
			STATUS current
			DESCRIPTION
				"
				对端端口自协商节点(MA5100 V2R1 产品需求，固网其他产品实现根据本产品实际情况可选)
				"
			::= { hwEthernetEntry 10 }

		hwifEthernetPauseFrameTag OBJECT-TYPE
    			SYNTAX      TruthValue 
    			MAX-ACCESS  read-write
    			STATUS      current
    			DESCRIPTION
        		"
        		网口是否支持Pause帧流控 true支持，false不支持(MA5100 V2R1 产品需求，固网其他产品实现根据本产品实际情况可选) "
    			::={ hwEthernetEntry 11 }
		
		hwifEthernetPauseFrameSending OBJECT-TYPE
    			SYNTAX      TruthValue 
    			MAX-ACCESS  read-only
    			STATUS      current
    			DESCRIPTION
        		"
        		网口是否正发送Pause帧 (MA5100 V2R1 产品需求，固网其他产品实现根据本产品实际情况可选)"
    			::={ hwEthernetEntry 12 }


		hwifEthernetVlanDefault	OBJECT-TYPE
    			SYNTAX INTEGER
    			MAX-ACCESS  read-write
    			STATUS      current
    			DESCRIPTION
        		"
        		以太端口的默认VLAN 编号配置(MA5100 V2R1 产品需求，固网其他产品实现根据本产品实际情况可选) "
    			::={ hwEthernetEntry 13 }
    			    			
		hwifEthernetOnlineState OBJECT-TYPE
    			SYNTAX TruthValue
    			MAX-ACCESS  read-only
    			STATUS      current
    			DESCRIPTION
        		"
        		网口是否在线 (MA5100 V2R1 产品需求，固网其他产品实现根据本产品实际情况可选) "
    			::={ hwEthernetEntry 14 }
    	        
    	        hwifEthernetLineSelfAdaptMode OBJECT-TYPE
			SYNTAX INTEGER
				{
				on(1),
				off(2)
				}
			MAX-ACCESS read-write
			STATUS current
			DESCRIPTION
				" 直连/交叉网线自适应 on(1) off(2) "
			::= { hwEthernetEntry 15 }    
  			

hwifVLANTrunkStatusTable OBJECT-TYPE
			SYNTAX SEQUENCE OF HwIfVLANTrunkStatusEntry
			MAX-ACCESS not-accessible
			STATUS current
			DESCRIPTION
				"Vlan Trunk端口的Gvrp属性 "
			::= { hwL2IfMibObject 5 }
		
		hwifVLANTrunkStatusEntry OBJECT-TYPE
			SYNTAX HwIfVLANTrunkStatusEntry
			MAX-ACCESS not-accessible
			STATUS current
			DESCRIPTION
				" Vlan Trunk端口的Gvrp属性 "
			INDEX { hwifVLANTrunkIndex }
			::= { hwifVLANTrunkStatusTable 1 }
		
		HwIfVLANTrunkStatusEntry ::=
			SEQUENCE { 
				hwifVLANTrunkIndex
					InterfaceIndex,
				hwifVLANTrunkGvrpRegistration
					INTEGER,
				hwifVLANTrunkPassListLow
					OCTET STRING,
				hwifVLANTrunkPassListHigh
					OCTET STRING,
				hwifVLANTrunkAllowListLow
					OCTET STRING,
				hwifVLANTrunkAllowListHigh
					OCTET STRING
			 }

		hwifVLANTrunkIndex OBJECT-TYPE
			SYNTAX InterfaceIndex
			MAX-ACCESS  read-only
			STATUS current
			DESCRIPTION
				" VLANTrunk接口索引号 "
			::= { hwifVLANTrunkStatusEntry 1 }
		
		hwifVLANTrunkGvrpRegistration OBJECT-TYPE
			SYNTAX INTEGER
				{
				normal(1),
				fixed(2),
				forbidden(3)
				}
			MAX-ACCESS read-write
			STATUS current
			DESCRIPTION
				" GVRP注册信息
				Normal:(1)this is the default configration. Allow create, register and unretiser vlans dynamiclly at this port.
				fixed: (2)allow create and register vlan manully at this port.And prevent from unregistering vlans or registering known vlans of this port at another trunk port.
				Forbidden:(3)Unregister all vlans but vlan 1, forbid to create or register any other vlans at this port."
			::= { hwifVLANTrunkStatusEntry 2 }
		
		hwifVLANTrunkPassListLow OBJECT-TYPE
			SYNTAX OCTET STRING
			MAX-ACCESS read-only
			STATUS current
			DESCRIPTION
				" 该VLAN 端口实际通过的VLAN（低2040个VLAN（1-2040））,长度为255 "
			::= { hwifVLANTrunkStatusEntry 3 }
		
		hwifVLANTrunkPassListHigh OBJECT-TYPE
			SYNTAX OCTET STRING
			MAX-ACCESS read-only
			STATUS current
			DESCRIPTION
				" 该VLAN 端口实际通过的VLAN（高1960个VLAN（2041-4000））,长度为245 "
			::= { hwifVLANTrunkStatusEntry 4 }
		
		hwifVLANTrunkAllowListLow OBJECT-TYPE
			SYNTAX OCTET STRING
			MAX-ACCESS read-write
			STATUS current
			DESCRIPTION
				" 该VLAN 端口允许通过的VLAN（低2040个VLAN（1-2040））,长度为255 "
			::= { hwifVLANTrunkStatusEntry 5 }
		
		hwifVLANTrunkAllowListHigh OBJECT-TYPE
			SYNTAX OCTET STRING
			MAX-ACCESS read-write
			STATUS current
			DESCRIPTION
				" 该VLAN 端口允许通过的VLAN（高1960个VLAN（2041-4000））,长度为245 "
			::= { hwifVLANTrunkStatusEntry 6 }

-- hwMacToVlanTable   是MA5105 产品需求，其他产品可根据实际情况选择实现      

       hwMacToVlanTable   OBJECT-TYPE
             SYNTAX          SEQUENCE OF HwMacToVlanEntry
             MAX-ACCESS      not-accessible
             STATUS          current
             DESCRIPTION
                 "
                 根据MAC地址查询到接口(对应到端口)、VLAN以及PVC的ID的表
                 "
         ::= { hwExtInterface 3 }

         hwMacToVlanEntry   OBJECT-TYPE
             SYNTAX          HwMacToVlanEntry
             MAX-ACCESS      not-accessible
             STATUS          current
             DESCRIPTION     "An entry in hwMacToVlanTable."
             INDEX           { hwMacAddress }
         ::= { hwMacToVlanTable 1 }

         HwMacToVlanEntry ::= SEQUENCE {
             hwMacAddress	      MacAddress,
             hwInterface              INTEGER,
             hwVlanId		      INTEGER,
             hwConnectId              INTEGER
             }

         hwMacAddress OBJECT-TYPE
             SYNTAX      MacAddress
             MAX-ACCESS  read-only
             STATUS      current
             DESCRIPTION
                 "
                 学习到的MAC地址
                 "
         ::= { hwMacToVlanEntry 1 }

         hwInterface OBJECT-TYPE
             SYNTAX      INTEGER
             MAX-ACCESS  read-only
             STATUS      current
             DESCRIPTION
                 "
                 对应到端口的接口索引
                 "
         ::= { hwMacToVlanEntry 2 }

         hwVlanId OBJECT-TYPE
             SYNTAX      INTEGER
             MAX-ACCESS  read-only
             STATUS      current
             DESCRIPTION
                 "
                 MAC邦定的VLANID
                 "
         ::= { hwMacToVlanEntry 3 }
         
         hwConnectId OBJECT-TYPE
             SYNTAX      INTEGER
             MAX-ACCESS  read-only
             STATUS      current
             DESCRIPTION
                 "
                 MAC邦定到的连接号(PVC号)
                 "
         ::= { hwMacToVlanEntry 4 }
	
	
-- hwIfEthernetMirrorTable 是MA5100 产品 V2r1 需求，其他产品可根据实际情况选择实现   
		hwIfEthernetMirrorTable OBJECT-TYPE
			SYNTAX SEQUENCE OF HwIfEthernetMirrorEntry
			MAX-ACCESS not-accessible
			STATUS current
			DESCRIPTION
				"以太网端口镜相表"
			::= { hwExtInterface  4}
		
		hwIfEthernetMirrorEntry OBJECT-TYPE
			SYNTAX HwIfEthernetMirrorEntry
			MAX-ACCESS not-accessible
			STATUS current
			DESCRIPTION
				" 以太网端口镜相表"
			INDEX { hwifEthernetMirrorDstPort   }
			::= { hwIfEthernetMirrorTable 1 }
		
		HwIfEthernetMirrorEntry ::=
			SEQUENCE { 
				hwifEthernetMirrorDstPort 
					INTEGER,
				hwifEthernetMirrorSrcPort 
					PortList
			 }

		hwifEthernetMirrorDstPort  OBJECT-TYPE
			SYNTAX INTEGER
			MAX-ACCESS read-only
			STATUS current
			DESCRIPTION
				" 目的镜相端口，格式同ifIndex"
			::= { hwIfEthernetMirrorEntry 1 }
		
		hwifEthernetMirrorSrcPort  OBJECT-TYPE
			SYNTAX PortList
			MAX-ACCESS read-write
			STATUS current
			DESCRIPTION
				" 源镜相端口"
			::= { hwIfEthernetMirrorEntry 2 }
			

	
	END
