FIAL-REGISTRY-MIB DEFINITIONS ::= BEGIN

IMPORTS
    MODULE-IDENTITY,
    enterprises
        FROM SNMPv2-SMI;

fial MODULE-IDENTITY
    LAST-UPDATED "200605250000Z" -- may 25, 2006
    ORGANIZATION "Fial Incorporated"
    CONTACT-INFO
        "Postal: Fial Incorporated
                 710 Center St.
                 Oregon City, OR 97045
                 USA

            Tel: +1 (503) 607-1940
            Fax: +1 (503) 607-1945
            Web: http://www.fial.com

         E-mail: support@fial.com"

    DESCRIPTION
        "The root MIB module for Fial Incorporated.

        Copyright 2002 Fial Incorporated All rights reserved
        Reproduction of this document is authorized on the condition
        that the foregoing copyright notice is included.

        This SNMP MIB module (Specification) embodies proprietary
        intellectual property of Fial Incorporated (hereafter referred
	to as Fial). Fial retains all title and ownership in the
	Specification, including any revisions.

        Fial grants all interested parties a non-exclusive license to
        use and distribute an unmodified copy of this Specification
        in connection with management of Fial products, and without
        fee, provided this copyright notice and license appear on
        all copies.

        This Specification is supplied 'AS IS,' and Fial makes no
        warranty, either express or implied, as to the use, operation,
        condition or performance of the Specification."

    REVISION      "200212030000Z" -- dec 03, 2002
    DESCRIPTION
        "Rev 1.0    03 Dec 2002
         Initial version of MIB module FIAL-REGISTRY-MIB"

    REVISION      "200303270000Z" -- mar 27, 2003
    DESCRIPTION
        "Rev 1.1    27 Mar 2003
         Replaced root OBJECT-IDENTIFIER node for the fial enterprise
         with this MODULE-IDENTITY node in order to remove the need
         for a forward reference to fialModules"

    REVISION "200605250000Z" -- may 25, 2006
    DESCRIPTION
        "Rev 1.2    25 May 2006
         Updated Fial CONTACT INFO."

    ::= { enterprises 4822 }

    fialAdmin OBJECT IDENTIFIER ::= { fial 1 }
    -- Reserved for administratively assigned OBJECT IDENTIFIERS,
    -- i.e. those not associated with MIB objects

        fialCapabilities OBJECT IDENTIFIER ::= { fialAdmin 1 }
        -- Provides a root object identifier from which AGENT-CAPABILITIES
        -- values may be assigned.

        fialModules OBJECT IDENTIFIER ::= { fialAdmin 2 }
        -- Provides a root object identifier from which MODULE-IDENTITY
        -- values may be assigned.

        fialOva OBJECT IDENTIFIER ::= { fialAdmin 3 }
        -- Provides a root object identifier from which Object Value
        -- Assignments (OVAs) may be made.

    fialMgmt OBJECT IDENTIFIER ::= { fial 2 }
    -- Main subtree for mib modules

        fialRegistry OBJECT IDENTIFIER ::= { fialMgmt 1 }
	-- Root node for objects of this module

END
