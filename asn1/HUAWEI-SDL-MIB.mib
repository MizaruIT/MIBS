-- =================================================================
-- Copyright (C) 2003 by  HUAWEI TECHNOLOGIES. All rights reserved.
--
-- Description: Demonstrates how to maintain SDL ports
-- Reference:   None
-- Version:     V1.0
-- History:
-- liguanrong, 2003-10-28, SDL MIB first define
-- =================================================================

HUAWEI-SDL-MIB DEFINITIONS ::= BEGIN
IMPORTS
    MODULE-IDENTITY, OBJECT-TYPE, Unsigned32
        FROM SNMPv2-SMI
        
        ifIndex
                FROM IF-MIB
    huaweiUtility
                FROM HUAWEI-MIB;

    hwSDL MODULE-IDENTITY
        LAST-UPDATED
                "0310301523Z"
        ORGANIZATION
                "Huawei Technologies co.,Ltd."
        CONTACT-INFO
                "Kefa Road,
                 Fx-Net Dep, Huawei Technologies Co.,Ltd.
                 Science-Based Industrial Park,
                 Nanshan District,Shenzhen  P.R. China
                 http://www.huawei.com
                 Zip:518057"
        DESCRIPTION
            "
            The HUAWEI-SDL-MIB demonstrates how to maintain SDL ports
            "
        ::= { huaweiUtility 35 }

        hwSDLMibObjects     OBJECT IDENTIFIER   ::= { hwSDL             1 }

        sdlBoardTable OBJECT-TYPE
            SYNTAX      SEQUENCE OF SdlBoardEntry
            MAX-ACCESS  not-accessible
            STATUS      current
            DESCRIPTION
                "
                SDL单板管理表
                "
            ::= { hwSDLMibObjects 1 }

        sdlBoardEntry OBJECT-TYPE
            SYNTAX      SdlBoardEntry
            MAX-ACCESS  not-accessible
            STATUS      current
            DESCRIPTION
                "
                SDL单板管理实体
                "
            INDEX
                {
                ifIndex
                }
            ::= { sdlBoardTable 1 }

        SdlBoardEntry ::=
            SEQUENCE
                {
                hwSdlBoardRunmode
                    INTEGER,
                hwSdlClockSource
                    INTEGER,
                hwSdlHw1TsInfo
                    Unsigned32,
                hwSdlHw2TsInfo
                    Unsigned32,
                hwSdl1E1TsInfo
                    Unsigned32,
                hwSdl2E1TsInfo
                    Unsigned32,
                hwSdl3E1TsInfo
                    Unsigned32,
                hwSdl4E1TsInfo
                    Unsigned32,
                hwSdl1ShdslTsInfo
                    Unsigned32,
                hwSdl2ShdslTsInfo
                    Unsigned32,
                hwSdl3ShdslTsInfo
                    Unsigned32,
                hwSdl4ShdslTsInfo
                    Unsigned32
                }

        hwSdlBoardRunmode OBJECT-TYPE
            SYNTAX      INTEGER
                {
                hwSdlNormal(1),
                hwSdlTransport(2)
                }
            MAX-ACCESS  read-write
            STATUS      current
            DESCRIPTION
                "
                1. 正常模式
                2. 传输模式

                1.Normal
                2.Transport
                "
            ::= { sdlBoardEntry 1 }

        hwSdlClockSource OBJECT-TYPE
            SYNTAX      INTEGER
                {
                hwHWClock(1),
                hwE1PORT1(2),
                hwE1PORT2(3),
                hwE1PORT3(4),
                hwE1PORT4(5),
                hwSHDSLPORT1(6),
                hwSHDSLPORT3(7)
                }
            MAX-ACCESS  read-write
            STATUS      current
            DESCRIPTION
                "
                1. HW clock
                2. First E1 clock
                3. Second E1 clock
                4. Third E1 clock
                5. Fourth E1 clock
                6. First SHDSL clock
                7. Third SHDSL clock

                1. HW时钟
                2. 第1路FE1时钟
                3. 第2路FE1时钟
                4. 第3路FE1时钟
                5. 第4路FE1时钟
                6. 第1路SHDSL时钟
                7. 第3路SHDSL时钟
                "
            ::= { sdlBoardEntry 2 }

        hwSdlHw1TsInfo OBJECT-TYPE
            SYNTAX      Unsigned32(0..4294967295)
            MAX-ACCESS  read-only
            STATUS      current
            DESCRIPTION
                "
                Each bit figures a channel used or nor, '0' figure not used, '1' figures used

                32位的每一位代表一个时隙，0位对应0时隙; '0':时隙未使用 '1':时隙使用
                "
            ::= { sdlBoardEntry 3 }

        hwSdlHw2TsInfo OBJECT-TYPE
            SYNTAX      Unsigned32(0..4294967295)
            MAX-ACCESS  read-only
            STATUS      current
            DESCRIPTION
                "
                Each bit figures a channel used or nor, '0' figure not used, '1' figures used

                32位的每一位代表一个时隙，0位对应0时隙; '0':时隙未使用 '1':时隙使用
                "
            ::= { sdlBoardEntry 4 }

        hwSdl1E1TsInfo OBJECT-TYPE
            SYNTAX      Unsigned32(0..4294967295)
            MAX-ACCESS  read-only
            STATUS      current
            DESCRIPTION
                "
                Each bit figures a channel used or nor, '0' figure not used, '1' figures used

                32位的每一位代表一个时隙，0位对应0时隙; '0':时隙未使用 '1':时隙使用
                "
            ::= { sdlBoardEntry 5 }

        hwSdl2E1TsInfo OBJECT-TYPE
            SYNTAX      Unsigned32(0..4294967295)
            MAX-ACCESS  read-only
            STATUS      current
            DESCRIPTION
                "
                Each bit figures a channel used or nor, '0' figure not used, '1' figures used

                32位的每一位代表一个时隙，0位对应0时隙; '0':时隙未使用 '1':时隙使用
                "
            ::= { sdlBoardEntry 6 }

        hwSdl3E1TsInfo OBJECT-TYPE
            SYNTAX      Unsigned32(0..4294967295)
            MAX-ACCESS  read-only
            STATUS      current
            DESCRIPTION
                "
                Each bit figures a channel used or nor, '0' figure not used, '1' figures used

                32位的每一位代表一个时隙，0位对应0时隙; '0':时隙未使用 '1':时隙使用
                "
            ::= { sdlBoardEntry 7 }

        hwSdl4E1TsInfo OBJECT-TYPE
            SYNTAX      Unsigned32(0..4294967295)
            MAX-ACCESS  read-only
            STATUS      current
            DESCRIPTION
                "
                Each bit figures a channel used or nor, '0' figure not used, '1' figures used

                32位的每一位代表一个时隙，0位对应0时隙; '0':时隙未使用 '1':时隙使用
                "
            ::= { sdlBoardEntry 8 }

        hwSdl1ShdslTsInfo OBJECT-TYPE
            SYNTAX      Unsigned32(0..4294967295)
            MAX-ACCESS  read-only
            STATUS      current
            DESCRIPTION
                "
                Each bit figures a channel used or nor, '0' figure not used, '1' figures used

                32位的每一位代表一个时隙，0位对应0时隙; '0':时隙未使用 '1':时隙使用
                "
            ::= { sdlBoardEntry 9 }

        hwSdl2ShdslTsInfo OBJECT-TYPE
            SYNTAX      Unsigned32(0..4294967295)
            MAX-ACCESS  read-only
            STATUS      current
            DESCRIPTION
                "
                Each bit figures a channel used or nor, '0' figure not used, '1' figures used

                32位的每一位代表一个时隙，0位对应0时隙; '0':时隙未使用 '1':时隙使用
                "
            ::= { sdlBoardEntry 10 }

        hwSdl3ShdslTsInfo OBJECT-TYPE
            SYNTAX      Unsigned32(0..4294967295)
            MAX-ACCESS  read-only
            STATUS      current
            DESCRIPTION
                "
                Each bit figures a channel used or nor, '0' figure not used, '1' figures used

                32位的每一位代表一个时隙，0位对应0时隙; '0':时隙未使用 '1':时隙使用
                "
            ::= { sdlBoardEntry 11 }

        hwSdl4ShdslTsInfo OBJECT-TYPE
            SYNTAX      Unsigned32(0..4294967295)
            MAX-ACCESS  read-only
            STATUS      current
            DESCRIPTION
                "
                Each bit figures a channel used or nor, '0' figure not used, '1' figures used

                32位的每一位代表一个时隙，0位对应0时隙; '0':时隙未使用 '1':时隙使用
                "
            ::= { sdlBoardEntry 12 }

        sdlFE1PortTable OBJECT-TYPE
            SYNTAX      SEQUENCE OF SdlFE1PortEntry
            MAX-ACCESS  not-accessible
            STATUS      current
            DESCRIPTION
              "
              SDL FE1端口管理表
              "
            ::= { hwSDLMibObjects 2 }

        sdlFE1PortEntry OBJECT-TYPE
            SYNTAX      SdlFE1PortEntry
            MAX-ACCESS  not-accessible
            STATUS      current
            DESCRIPTION
                "
                SDL FE1端口管理实体
                "
            INDEX
                {
                    ifIndex
                }
            ::= { sdlFE1PortTable 1 }

        SdlFE1PortEntry ::=
            SEQUENCE
                {
                hwSdlFE1FrameType
                    INTEGER,
                hwSdlFE1UserName
                    OCTET STRING(SIZE(0..10)),
                hwSdlFE1SignalState
                    INTEGER,
                hwSdlFE1LoopState
                    INTEGER,
                hwSdlFE1OprType
                    INTEGER
                }

        hwSdlFE1FrameType OBJECT-TYPE
            SYNTAX      INTEGER
                {
                hwPCM30(1),
                hwPCM30C(2),
                hwPCM31(3),
                hwPCM31C(4),
                hwUNFRAME(5)
                }
            MAX-ACCESS  read-write
            STATUS      current
            DESCRIPTION
                "
                the frame type of the SDL E1 port:
                SDL E1端口的帧结构:
                1. PCM30
                2. PCM30C
                3. PCM31
                4. PCM31C
                5. UNFRRAMED
                "
            ::= { sdlFE1PortEntry 1 }

        hwSdlFE1UserName OBJECT-TYPE
            SYNTAX      OCTET STRING(SIZE(0..10))
            MAX-ACCESS  read-write
            STATUS      current
            DESCRIPTION
                "
                name of SDL FE1 port.

                SDL FE1端口的名称 (SIZE(0..10))
                "
            ::= { sdlFE1PortEntry 2 }

        hwSdlFE1SignalState OBJECT-TYPE
            SYNTAX      INTEGER
            MAX-ACCESS  read-only
            STATUS      current
            DESCRIPTION
                "
                 E1信号状态：相应告警位为0表示存在相应告警，全0表示信号正常
                    bit0＝LOS告警
                    bit1＝LFA告警
                    bit2＝RRA告警
                    bit3＝LMFA告警
                    bit4＝AIS告警
                    bit5＝CRC4告警
                    其它，保留为0
                "
            ::= { sdlFE1PortEntry 3 }

        hwSdlFE1LoopState OBJECT-TYPE
            SYNTAX      INTEGER
                {
                hwNoLooping(1),
                hwLocalLooping(2),
                hwRemoteLooping(3)
                }
            MAX-ACCESS  read-only
            STATUS      current
            DESCRIPTION
                "
                1. No Looping
                2. Local Looping
                3. Remote Looping

                1. 无环回
                2. 近端环回
                3. 远端环回
                "
            ::= { sdlFE1PortEntry 4 }

        hwSdlFE1OprType OBJECT-TYPE
            SYNTAX      INTEGER
                {
                hwCancelLoop(1),
                hwLocalLoop(2),
                hwRemoteLoop(3)
                }
            MAX-ACCESS  read-write
            STATUS      current
            DESCRIPTION
                "
                1. Cancel Loop
                2. Local Loop
                3. Remote Loop

                1. 取消环回
                2. 近端环回
                3. 远端环回
                "
            ::= { sdlFE1PortEntry 5 }

        sdlShdslPortTable OBJECT-TYPE
            SYNTAX      SEQUENCE OF SdlShdslPortEntry
            MAX-ACCESS  not-accessible
            STATUS      current
            DESCRIPTION
              "
              SDL SHDSL端口管理表
              "
            ::= { hwSDLMibObjects 3 }

        sdlShdslPortEntry OBJECT-TYPE
            SYNTAX      SdlShdslPortEntry
            MAX-ACCESS  not-accessible
            STATUS      current
            DESCRIPTION
                "
                SDL SHDSL端口管理实体
                "
            INDEX
                {
                ifIndex
                }
            ::= { sdlShdslPortTable 1 }

        SdlShdslPortEntry ::=
            SEQUENCE
                {
                hwSdlShdslRate
                    INTEGER,
                hwSdlShdslMode
                    INTEGER,
                hwSdlShdslUserName
                    OCTET STRING(SIZE(0..10)),
                hwSdlShdslLoopState
                    INTEGER,
                hwSdlActiveAllow
                    INTEGER,
                hwSdlShdslActiveState
                    INTEGER,
                hwSdlShdslOprType
                    INTEGER,
                hwSdltShdslSet2Or4Line
                    INTEGER
                }

        hwSdlShdslRate OBJECT-TYPE
            SYNTAX      INTEGER(3..32)
            MAX-ACCESS  read-write
            STATUS      current
            DESCRIPTION
                "
                Port rate 3-32x64K bps

                端口速率 3-32x64K bps
                "
            ::= { sdlShdslPortEntry 1 }
            
        hwSdlShdslMode OBJECT-TYPE
            SYNTAX      INTEGER
                {
                hwSdlShdslE1(1),
                hwSdlShdslV35(2)
                }
            MAX-ACCESS  read-write
            STATUS      current
            DESCRIPTION
                "
                1. SHDSL port work in E1 mode
                2. SHDSL port work in V35 mode

                1. SHDSL端口工作在E1模式
                2. SHDSL端口工作在V35模式
                "
            ::= { sdlShdslPortEntry 2 }

         hwSdlShdslUserName OBJECT-TYPE
            SYNTAX      OCTET STRING(SIZE(0..10))
            MAX-ACCESS  read-write
            STATUS      current
            DESCRIPTION
                "
                name of SDL SHDSL port, size in 10 characters.

                SDL SHDSL端口的名称 (SIZE(0..10))
                "
            ::= { sdlShdslPortEntry 3 }

        hwSdlShdslLoopState OBJECT-TYPE
            SYNTAX      INTEGER
                {
                hwNoLooping(1),
                hwLocalLooping(2),
                hwRemoteLooping(3)
                }
            MAX-ACCESS  read-only
            STATUS      current
            DESCRIPTION
                "
                1. No Looping
                2. Local Looping,
                3. Remote Looping,

                1. 无环回
                2. 近端环回
                3. 远端环回
                "
            ::= { sdlShdslPortEntry 4 }

        hwSdlActiveAllow OBJECT-TYPE
            SYNTAX      INTEGER
                {
                hwAllow(1),
                hwProhibit(2)
                }
            MAX-ACCESS  read-only
            STATUS      current
            DESCRIPTION
                "
                1. Allow active
                2. Prohibit active

                1. 允许
                2. 禁止
                "
            ::= { sdlShdslPortEntry 5 }

        hwSdlShdslActiveState OBJECT-TYPE
            SYNTAX      INTEGER
                {
                hwActive(1),
                hwDeactive(2)
                }
            MAX-ACCESS  read-only
            STATUS      current
            DESCRIPTION
                "
                1. active
                2. deactive

                1. 激活
                2. 去激活
                "
            ::= { sdlShdslPortEntry 6 }

        hwSdlShdslOprType OBJECT-TYPE
            SYNTAX      INTEGER
                {
                hwCancelLoop(1),
                hwLocalLoop(2),
                hwRemoteLoop(3),
                hwActive(4),
                hwDeactive(5)
                }
            MAX-ACCESS  read-write
            STATUS      current
            DESCRIPTION
                "
                1. Cancel Loop
                2. Local Loop
                3. Remote Loop
                4. Active
                5. Deactive

                1.取消环回
                2.近端环回
                3.远端环回
                4.激活
                5.去激活
                "
            ::= { sdlShdslPortEntry 7 }
            
       	hwSdltShdslSet2Or4Line OBJECT-TYPE
       	    SYNTAX      INTEGER
       	        {
       	        hw2line(1),
       	        hw4line(2)
       	        }
       	    MAX-ACCESS  read-write
            STATUS      current
       	    DESCRIPTION
       	    	"
       	    	1.Set 2line mode
       	    	2.Set 4line mode   
       	    	
       	    	1.设置2线模式
       	    	2.设置4线模式
       	    	"
            ::={ sdlShdslPortEntry 8 }


END
