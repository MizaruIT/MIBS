--   ============================================================================
-- Copyright (C) 2003 by  HUAWEI TECHNOLOGIES. All rights reserved.
-- 
-- Description:  
-- Reference:  
-- Version: V3.00
-- History:
-- liu chenglong 20030428 Added IPR Decriptions and updated all MIB version to V3.00
-- ============================================================================  

	HUAWEI-VPRING-MIB DEFINITIONS ::= BEGIN
 
		IMPORTS
			huaweiUtility			
				FROM HUAWEI-MIB			
			 OBJECT-TYPE, MODULE-IDENTITY, NOTIFICATION-TYPE			
				FROM SNMPv2-SMI			
			RowStatus, DisplayString, TruthValue			
				FROM SNMPv2-TC;
	
	
		hwVPRing MODULE-IDENTITY 
			LAST-UPDATED "200304280900Z"
			ORGANIZATION 
				"Fix-Net Dep, Huawei Technologies Co.,Ltd."
			CONTACT-INFO 
				"Floot 5 ,Block 4, R&D Building,
				Huawei Longgang Production Base,
				Shenzhen,  P.R.C.
				http://www.huawei.com
				Zip:518057
				"
			DESCRIPTION 
				"huawei ATM VPRING  MIb	"
			REVISION "200211290900Z"
			DESCRIPTION
				" Huawei VPRING MIB"
			::= { huaweiUtility 20 }
		
	
	
--
-- Node definitions
--
	
		hwAtmApsVpRingTable OBJECT-TYPE
			SYNTAX SEQUENCE OF HwAtmApsVpRingEntry
			MAX-ACCESS not-accessible
			STATUS current
			DESCRIPTION
				"
				VP环配置表"
			::= { hwVPRing 1 }
		
		hwAtmApsVpRingEntry OBJECT-TYPE
			SYNTAX HwAtmApsVpRingEntry
			MAX-ACCESS not-accessible
			STATUS current
			DESCRIPTION
				"
				VP环配置表实体"
			INDEX { hwAtmApsVpRingIndex }
			::= { hwAtmApsVpRingTable 1 }
		
		HwAtmApsVpRingEntry ::=
			SEQUENCE { 
				hwAtmApsVpRingIndex
					INTEGER,
				hwAtmApsVpRingPosition
					INTEGER,
				hwAtmApsVpRingFrameID1
					INTEGER,
				hwAtmApsVpRingSlotID1
					INTEGER,
				hwAtmApsVpRingPortID1
					INTEGER,
				hwAtmApsVpRingFrameID2
					INTEGER,
				hwAtmApsVpRingSlotID2
					INTEGER,
				hwAtmApsVpRingPortID2
					INTEGER,
				hwAtmApsVpRingRowStatus
					RowStatus
			 }

		
		hwAtmApsVpRingIndex OBJECT-TYPE
			SYNTAX INTEGER (0..15)
			MAX-ACCESS not-accessible
			STATUS current
			DESCRIPTION
				"
				VP环编号"
			::= { hwAtmApsVpRingEntry 1 }
		
		
		hwAtmApsVpRingPosition OBJECT-TYPE
			SYNTAX INTEGER (0..15)
			MAX-ACCESS read-create
			STATUS current
			DESCRIPTION
				"
				该节点在VP环上的位置编号"
			::= { hwAtmApsVpRingEntry 2 }
		
		
		hwAtmApsVpRingFrameID1 OBJECT-TYPE
			SYNTAX INTEGER (0..63)
			MAX-ACCESS read-create
			STATUS current
			DESCRIPTION
				"
				物理框号1"
			::= { hwAtmApsVpRingEntry 3 }
		
		
		hwAtmApsVpRingSlotID1 OBJECT-TYPE
			SYNTAX INTEGER (0..63)
			MAX-ACCESS read-create
			STATUS current
			DESCRIPTION
				"
				物理槽号1"
			::= { hwAtmApsVpRingEntry 4 }
		
		
		hwAtmApsVpRingPortID1 OBJECT-TYPE
			SYNTAX INTEGER (0..63)
			MAX-ACCESS read-create
			STATUS current
			DESCRIPTION
				"
				物理端口号1"
			::= { hwAtmApsVpRingEntry 5 }
		
		
		hwAtmApsVpRingFrameID2 OBJECT-TYPE
			SYNTAX INTEGER (0..63)
			MAX-ACCESS read-create
			STATUS current
			DESCRIPTION
				"
				物理框号2"
			::= { hwAtmApsVpRingEntry 6 }
		
		
		hwAtmApsVpRingSlotID2 OBJECT-TYPE
			SYNTAX INTEGER (0..63)
			MAX-ACCESS read-create
			STATUS current
			DESCRIPTION
				"
				物理槽号2"
			::= { hwAtmApsVpRingEntry 7 }
		
		
		hwAtmApsVpRingPortID2 OBJECT-TYPE
			SYNTAX INTEGER (0..63)
			MAX-ACCESS read-create
			STATUS current
			DESCRIPTION
				"
				物理端口号2"
			::= { hwAtmApsVpRingEntry 8 }
		
		
		hwAtmApsVpRingRowStatus OBJECT-TYPE
			SYNTAX RowStatus
			MAX-ACCESS read-create
			STATUS current
			DESCRIPTION
				"
				行状态"
			::= { hwAtmApsVpRingEntry 9 }
		
--   VPG配置表 hwAtmApsVPGConfigTable
-- 
		hwAtmApsVPGConfigTable OBJECT-TYPE
			SYNTAX SEQUENCE OF HwAtmApsVPGConfigEntry
			MAX-ACCESS not-accessible
			STATUS current
			DESCRIPTION
				"
				VPG配置表"
			::= { hwVPRing 2 }
		
		
		hwAtmApsVPGConfigEntry OBJECT-TYPE
			SYNTAX HwAtmApsVPGConfigEntry
			MAX-ACCESS not-accessible
			STATUS current
			DESCRIPTION
				"
				VPG配置表实体"
			INDEX { hwAtmApsVPGIndex }
			::= { hwAtmApsVPGConfigTable 1 }
		
		HwAtmApsVPGConfigEntry ::=
			SEQUENCE { 
				hwAtmApsVPGIndex
					INTEGER,
				hwAtmApsVPGName
					DisplayString,
				hwAtmApsVPGWorkingFrameID
					INTEGER,
				hwAtmApsVPGWorkingSlotID
					INTEGER,
				hwAtmApsVPGWorkingPhyportID
					INTEGER,
				hwAtmApsVPGProtectionFrameID
					INTEGER,
				hwAtmApsVPGProtectionSlotID
					INTEGER,
				hwAtmApsVPGProtectionPhyportID
					INTEGER,
				hwAtmApsVPGMode
					INTEGER,
				hwAtmApsVPGWTRTime
					INTEGER,
				hwAtmApsVPGExternalCommands
					INTEGER,
				hwAtmApsVPGProtectK1K2Rcv
					INTEGER,
				hwAtmApsVPGProtectK1K2Trans
					INTEGER,
				hwAtmApsVPGWorkingEntityStatus
					BITS,
				hwAtmApsVPGProtectionEntityStatus
					BITS,
				hwAtmApsVPGCurrEntity
					INTEGER,
				hwAtmApsVPGApsStatus
					INTEGER,
				hwAtmApsVPGVplIsInUse
					TruthValue,
				hwAtmApsVPGVpRingIndex
					INTEGER,
				hwAtmApsVPGRevertive
					TruthValue,
				hwAtmApsVPGRowStatus
					RowStatus
			 }

		
		hwAtmApsVPGIndex OBJECT-TYPE
			SYNTAX INTEGER (1..256)
			MAX-ACCESS accessible-for-notify
			STATUS current
			DESCRIPTION
				"
				VPG表的索引项"
			::= { hwAtmApsVPGConfigEntry 1 }
		
		
		hwAtmApsVPGName OBJECT-TYPE
			SYNTAX DisplayString (SIZE (0..51))
			MAX-ACCESS read-create
			STATUS current
			DESCRIPTION
				"
				VPG表名称，长度为52个字节"
			::= { hwAtmApsVPGConfigEntry 2 }
		
		
		hwAtmApsVPGWorkingFrameID OBJECT-TYPE
			SYNTAX INTEGER (0..63)
			MAX-ACCESS read-create
			STATUS current
			DESCRIPTION
				"
				工作实体物理框号"
			::= { hwAtmApsVPGConfigEntry 3 }
		
		
		hwAtmApsVPGWorkingSlotID OBJECT-TYPE
			SYNTAX INTEGER (0..63)
			MAX-ACCESS read-create
			STATUS current
			DESCRIPTION
				"
				工作实体物理槽号"
			::= { hwAtmApsVPGConfigEntry 4 }
		
		
		hwAtmApsVPGWorkingPhyportID OBJECT-TYPE
			SYNTAX INTEGER (0..63)
			MAX-ACCESS read-create
			STATUS current
			DESCRIPTION
				"
				工作实体物理端口号"
			::= { hwAtmApsVPGConfigEntry 5 }
		
		
		hwAtmApsVPGProtectionFrameID OBJECT-TYPE
			SYNTAX INTEGER (0..63)
			MAX-ACCESS read-create
			STATUS current
			DESCRIPTION
				"
				保护实体物理框号"
			::= { hwAtmApsVPGConfigEntry 6 }
		
		
		hwAtmApsVPGProtectionSlotID OBJECT-TYPE
			SYNTAX INTEGER (0..63)
			MAX-ACCESS read-create
			STATUS current
			DESCRIPTION
				"
				保护实体物理槽号"
			::= { hwAtmApsVPGConfigEntry 7 }
		
		
		hwAtmApsVPGProtectionPhyportID OBJECT-TYPE
			SYNTAX INTEGER (0..63)
			MAX-ACCESS read-create
			STATUS current
			DESCRIPTION
				"
				保护实体物理端口号"
			::= { hwAtmApsVPGConfigEntry 8 }
		
		
		hwAtmApsVPGMode OBJECT-TYPE
			SYNTAX INTEGER
				{
				onePlusOneUnidirection(1),
				onePlusOneBidirection(2)
				}
			MAX-ACCESS read-create
			STATUS current
			DESCRIPTION
				"
				保护模式，为可选项，默认为1＋1单向保护，分为1＋1单向和双向"
			::= { hwAtmApsVPGConfigEntry 9 }
		
		
		hwAtmApsVPGWTRTime OBJECT-TYPE
			SYNTAX INTEGER (1..30)
			MAX-ACCESS read-create
			STATUS current
			DESCRIPTION
				"
				VPG等待恢复时间，单位为分钟，缺省12分钟，
				用户可以根据需要指定，范围为1到30分钟"
			::= { hwAtmApsVPGConfigEntry 10 }
		
		
		hwAtmApsVPGExternalCommands OBJECT-TYPE
			SYNTAX INTEGER
				{
				clear(1),
				freeze(2),
				lockoutOfProtection(3),
				forcedSwitchForWorking(4),
				manualSwitchForWorking(5),
				manualSwitchForProtection(6)
				}
			MAX-ACCESS read-create
			STATUS current
			DESCRIPTION
				"
				外部命令的类型，如果设置该项，即认为是对改VPG进行对应的操作"
			::= { hwAtmApsVPGConfigEntry 11 }
		
		
		hwAtmApsVPGProtectK1K2Rcv OBJECT-TYPE
			SYNTAX INTEGER (0..65535)
			MAX-ACCESS read-only
			STATUS current
			DESCRIPTION
				"
				接收K字节，表示远端的最高请求情况，
				以及远端的桥接器或者选择器状态,默认为正常即其值为0x0010"
			::= { hwAtmApsVPGConfigEntry 12 }
		
		
		hwAtmApsVPGProtectK1K2Trans OBJECT-TYPE
			SYNTAX INTEGER (0..65535)
			MAX-ACCESS read-only
			STATUS current
			DESCRIPTION
				"
				发送K字节，表示本地请求中的最高请求，
				以及本地的桥接器和选择器状态,默认为正常即其值为0x0010"
			::= { hwAtmApsVPGConfigEntry 13 }
		
		
		hwAtmApsVPGWorkingEntityStatus OBJECT-TYPE
			SYNTAX BITS
				{
					lof(1),
                                        los(2),
                                        sd(3),
                                        rdi(4),
                                        ais(5),
                                        rsd(6)
				}
			MAX-ACCESS read-only
			STATUS current
			DESCRIPTION
				"
				表示工作实体的告警状态，每一位都代表一种告警，
				如果为1认为告警存在，如果为0表示告警不存在，
				如果整个值都为0，说明实体正常，默认实体正常				
				     0x00000002-RSD
                                     0x00000004-AIS,
                                     0x00000008-RDI,
                                     0x00000010-SD,
                                     0x00000020-LOS,
                                     0x00000040-LOF"
			::= { hwAtmApsVPGConfigEntry 14 }
		
		
		hwAtmApsVPGProtectionEntityStatus OBJECT-TYPE
			SYNTAX BITS
				{
					lof(1),
                                        los(2),
                                        sd(3),
                                        rdi(4),
                                        ais(5),
                                        rsd(6)
				}
			MAX-ACCESS read-only
			STATUS current
			DESCRIPTION
				"
				表示保护实体的告警状态，每一位都代表一种告警，
				如果为1认为告警存在，如果为0表示告警不存在，
				如果整个值都为0，说明实体正常，默认实体正常
				     0x00000002-RSD
                                     0x00000004-AIS,
                                     0x00000008-RDI,
                                     0x00000010-SD,
                                     0x00000020-LOS,
                                     0x00000040-LOF"
			::= { hwAtmApsVPGConfigEntry 15 }
		
		
		hwAtmApsVPGCurrEntity OBJECT-TYPE
			SYNTAX INTEGER
				{
				work(1),
				protect(2)
				}
			MAX-ACCESS read-only
			STATUS current
			DESCRIPTION
				"
				表示VPG的业务当前传输实体，缺省为工作实体"
			::= { hwAtmApsVPGConfigEntry 16 }
		
		
		hwAtmApsVPGApsStatus OBJECT-TYPE
			SYNTAX INTEGER
			MAX-ACCESS read-only
			STATUS current
			DESCRIPTION
				"
				记录VPG的本地告警情况，单向和双向保护模式下不一样，单向请求使用<24..31>位，双向请求使用<7..23>位
				   Bidirectional APSC:
				   0x00000080-DNR,
				   0x00000100-rsv1,
				   0x00000200-WTR,
				   0x00000400-rsv2,
				   0x00000800-MS-W,
				   0x00001000-MS-P,
				   0x00002000-rsv3,
				   0x00004000-SD-W,
				   0x00008000-SD-P,
				   0x00010000-rsv4,
				   0x00020000-SF-W,
				   0x00040000-rsv5,
				   0x00080000-FS-W,
				   0x00100000-SF-P,
				   0x00200000-LOP,
				   0x00400000-FREEZE,
				   0x00800000-CLEAR,
				   Unidirectional APSC:
				   0x01000000-WTR,
				   0x02000000-MS_P,
				   0x04000000-MS_W,
				   0x08000000-SD,
				   0x10000000-SF,
				   0x20000000-FS,
				   0x40000000-LOP,
				   0x80000000-CLEAR "
			::= { hwAtmApsVPGConfigEntry 17 }
		
		
		hwAtmApsVPGVplIsInUse OBJECT-TYPE
			SYNTAX TruthValue
			MAX-ACCESS read-write
			STATUS current
			DESCRIPTION
				"
				VPG的保护倒换使能表示，如果为2，表示没有使能，为1表示使能，
				如果将其设置为1，即认为是进行使能操作
				    enable(1),
				    disable(2)"
			::= { hwAtmApsVPGConfigEntry 18 }
		
		
		hwAtmApsVPGVpRingIndex OBJECT-TYPE
			SYNTAX INTEGER (0..15)
			MAX-ACCESS read-only
			STATUS current
			DESCRIPTION
				"
				VPG所在的VP环编号"
			::= { hwAtmApsVPGConfigEntry 19 }
		
		
		hwAtmApsVPGRevertive OBJECT-TYPE
			SYNTAX TruthValue
			MAX-ACCESS read-write
			STATUS current
			DESCRIPTION
				"
				可恢复标志，为1可恢复，为2不可恢复，缺省值2
				revertible(1),
				non-revertible(2)"
			::= { hwAtmApsVPGConfigEntry 20 }
		
		
		hwAtmApsVPGRowStatus OBJECT-TYPE
			SYNTAX RowStatus
			MAX-ACCESS read-create
			STATUS current
			DESCRIPTION
				"
				行状态"
			::= { hwAtmApsVPGConfigEntry 21 }
		
--   VP保护对配置表 hwAtmApsVPGVplTable
-- 
		hwAtmApsVPGVplTable OBJECT-TYPE
			SYNTAX SEQUENCE OF HwAtmApsVPGVplEntry
			MAX-ACCESS not-accessible
			STATUS current
			DESCRIPTION
				"
				VP保护对配置表"
			::= { hwVPRing 3 }
		
		
		hwAtmApsVPGVplEntry OBJECT-TYPE
			SYNTAX HwAtmApsVPGVplEntry
			MAX-ACCESS not-accessible
			STATUS current
			DESCRIPTION
				"
				VP保护对配置表实体"
			INDEX { hwAtmApsVPGIndex, hwAtmApsVPGVplWorkingVpi }
			::= { hwAtmApsVPGVplTable 1 }
		
		HwAtmApsVPGVplEntry ::=
			SEQUENCE { 
				hwAtmApsVPGVplWorkingVpi
					INTEGER,
				hwAtmApsVPGVplProtectionVpi
					INTEGER,
				hwAtmApsVPGVplServiceClass
					INTEGER,
				hwAtmApsVPGVplRowStaus
					RowStatus,
				hwAtmApsVPGVplTrafficTableIndex
					INTEGER
			 }

		
		hwAtmApsVPGVplWorkingVpi OBJECT-TYPE
			SYNTAX INTEGER (1..255)
			MAX-ACCESS not-accessible
			STATUS current
			DESCRIPTION
				"
				工作虚通道标识"
			::= { hwAtmApsVPGVplEntry 1 }
		
		
		hwAtmApsVPGVplProtectionVpi OBJECT-TYPE
			SYNTAX INTEGER (1..255)
			MAX-ACCESS read-create
			STATUS current
			DESCRIPTION
				"
				保护虚通道标识"
			::= { hwAtmApsVPGVplEntry 2 }
		
		hwAtmApsVPGVplServiceClass OBJECT-TYPE
			SYNTAX INTEGER
				{
				cbr(1),
				rtvbr(2),
				nrtvbr(3),
				abr(4),
				ubr(5)
				}
			MAX-ACCESS read-create
			STATUS deprecated
			DESCRIPTION
				"
				业务等级"
			::= { hwAtmApsVPGVplEntry 3 }
		
		hwAtmApsVPGVplRowStaus OBJECT-TYPE
			SYNTAX RowStatus
			MAX-ACCESS read-create
			STATUS current
			DESCRIPTION
				"
				行状态"
			::= { hwAtmApsVPGVplEntry 4 }


		hwAtmApsVPGVplTrafficTableIndex OBJECT-TYPE
			SYNTAX INTEGER (0..511)
			MAX-ACCESS read-create
			STATUS current
			DESCRIPTION
				"
				流量描述表索引"
			::= { hwAtmApsVPGVplEntry 5 }

		
--   抽样VP保护对配置表 hwAtmApsAPSChannelTable
-- 
		hwAtmApsAPSChannelTable OBJECT-TYPE
			SYNTAX SEQUENCE OF HwAtmApsAPSChannelEntry
			MAX-ACCESS not-accessible
			STATUS current
			DESCRIPTION
				"
				抽样VP保护对配置表"
			::= { hwVPRing 4 }
		
		
		hwAtmApsAPSChannelEntry OBJECT-TYPE
			SYNTAX HwAtmApsAPSChannelEntry
			MAX-ACCESS not-accessible
			STATUS current
			DESCRIPTION
				"
				抽样VP保护对配置表实体"
			INDEX { hwAtmApsAPSChannelFrameID, hwAtmApsAPSChannelSlotID, hwAtmApsAPSChannelPhyport, hwAtmApsAPSChannelVpi }
			::= { hwAtmApsAPSChannelTable 1 }
		
		HwAtmApsAPSChannelEntry ::=
			SEQUENCE { 
				hwAtmApsAPSChannelFrameID
					INTEGER,
				hwAtmApsAPSChannelSlotID
					INTEGER,
				hwAtmApsAPSChannelPhyport
					INTEGER,
				hwAtmApsAPSChannelVpi
					INTEGER,
				hwAtmApsAPSChannelGroupIndex
					INTEGER,
				hwAtmApsAPSChannelVlType
					INTEGER,
				hwAtmApsAPSChannelRowStaus
					RowStatus
			 }

		
		hwAtmApsAPSChannelFrameID OBJECT-TYPE
			SYNTAX INTEGER (0..63)
			MAX-ACCESS not-accessible
			STATUS current
			DESCRIPTION
				"
				物理框号"
			::= { hwAtmApsAPSChannelEntry 1 }
		
		
		hwAtmApsAPSChannelSlotID OBJECT-TYPE
			SYNTAX INTEGER (0..63)
			MAX-ACCESS not-accessible
			STATUS current
			DESCRIPTION
				"
				物理槽号"
			::= { hwAtmApsAPSChannelEntry 2 }
		
		
		hwAtmApsAPSChannelPhyport OBJECT-TYPE
			SYNTAX INTEGER (0..63)
			MAX-ACCESS not-accessible
			STATUS current
			DESCRIPTION
				"
				物理端口号"
			::= { hwAtmApsAPSChannelEntry 3 }
		
		
		hwAtmApsAPSChannelVpi OBJECT-TYPE
			SYNTAX INTEGER (1..255)
			MAX-ACCESS not-accessible
			STATUS current
			DESCRIPTION
				"
				虚通道标识"
			::= { hwAtmApsAPSChannelEntry 4 }
		
		
		hwAtmApsAPSChannelGroupIndex OBJECT-TYPE
			SYNTAX INTEGER (1..256)
			MAX-ACCESS read-create
			STATUS current
			DESCRIPTION
				"
				APS CHANNEL所在的VPG索引"
			::= { hwAtmApsAPSChannelEntry 5 }
		
		
		hwAtmApsAPSChannelVlType OBJECT-TYPE
			SYNTAX INTEGER
				{
				p2p(1),
				w-leaf(2),
				p-leaf(3)
				}
			MAX-ACCESS read-create
			STATUS current
			DESCRIPTION
				"
				VL类型，有P2P,W_LEAF,P_LEAF三种，P2P表示环上中间节点
				所在的CHANNEL,W_LEAF表示业务上下环点处的工作实体所在
				CHANNEL,P_LEAF则表示相应的保护CHANNEL"
			::= { hwAtmApsAPSChannelEntry 6 }
		
		
		hwAtmApsAPSChannelRowStaus OBJECT-TYPE
			SYNTAX RowStatus
			MAX-ACCESS read-create
			STATUS current
			DESCRIPTION
				"
				行状态"
			::= { hwAtmApsAPSChannelEntry 7 }
		
		hwVPRingSnmpTrapDef OBJECT IDENTIFIER ::= { hwVPRing 5 }
		
		
		hwAtmApsTraps OBJECT IDENTIFIER ::= { hwVPRingSnmpTrapDef 0 }
		
		
		hwAtmApsVPGStatusTraps NOTIFICATION-TYPE
			OBJECTS { hwAtmApsVPGIndex, hwAtmApsVPGProtectK1K2Rcv, hwAtmApsVPGProtectK1K2Trans, hwAtmApsVPGWorkingEntityStatus, hwAtmApsVPGProtectionEntityStatus, 
				hwAtmApsVPGCurrEntity, hwAtmApsVPGApsStatus }
			STATUS current
			DESCRIPTION 
				"vp group dynamic status trap:
				1:hwAtmApsVPGIndex,
				2:hwAtmApsVPGProtectK1K2Rcv,
				3:hwAtmApsVPGProtectK1K2Trans,
				4:hwAtmApsVPGWorkingEntityStatus,
				5:hwAtmApsVPGProtectionEntityStatus,
				6:hwAtmApsVPGCurrEntity,
				7:hwAtmApsVPGApsStatus
				
				VP组动态数据需要绑定的叶子:
				1:VP组编号,
				2:发送K字节,
				3:接收K字节,
				4:工作实体告警状态,
				5:保护实体告警状态,
				6:选择器状态,
				7:本地VP组请求状态                 
				"
			::= { hwAtmApsTraps 1 }
		
		
		
		
		hwAtmApsVPGProtectionSwitching NOTIFICATION-TYPE
			OBJECTS { hwAtmApsVPGWorkingFrameID, hwAtmApsVPGWorkingSlotID, hwAtmApsVPGWorkingPhyportID, hwAtmApsVPGIndex, hwAtmApsVPGProtectionSwitchingReason
				 }
			STATUS current
			DESCRIPTION 
				"alarm description:VP Channel Protection Switching
				explain： 
					1.Loss of signal,
					2.Deterioration of signal,
					3.User operation,
					4.Remote request causes switchover
				resolving method:
					1.Check if the transmission optical fiber is broken,
					2.Check if the transmission line quality is deteriorated,
					3.If it is the above 3/4 reason,no need to proceed.
				
				
				告警描述：VP通道倒换
				告警原因：
				1.信号丢失
				2.信号劣化
				3.用户下发倒换命令
				4.远端节点发生倒换
				修复建议：
				1.检查传输线路是否有断纤情况
				2.检查传输线路是否有质量劣化
				3.如果是上述3、4原因，无需操作"
			::= { hwAtmApsTraps 2 }
		
		
		hwAtmApsVPGProtectionSwitchingFail NOTIFICATION-TYPE
			OBJECTS { hwAtmApsVPGWorkingFrameID, hwAtmApsVPGWorkingSlotID, hwAtmApsVPGWorkingPhyportID, hwAtmApsVPGIndex, hwAtmApsVPGProtectionSwitchingFailReason
				 }
			STATUS current
			DESCRIPTION 
				"alarm description:VP Channel Protection Switching fails
				explain： 
					1.Command execution time out,
					2.VP group status abnormal caused by insufficient synchronization of active and standby boards
				resolving method:
					1.Check if the interface board works normally,
					2.There is no need to proceed. The VPRING data will be recovered within three minutes
				
				
				告警描述：VP通道倒换失败
				告警原因：
				1.命令执行超时
				2.主备板同步不充分引起VP组状态异常
				修复建议：
				1.检查接口板状态是否正常
				2.无需处理，等待3分钟后VPRING数据会自动恢复"
			::= { hwAtmApsTraps 3 }
		
		
		hwAtmApsVPGProtectionSwitchingClear NOTIFICATION-TYPE
			OBJECTS { hwAtmApsVPGWorkingFrameID, hwAtmApsVPGWorkingSlotID, hwAtmApsVPGWorkingPhyportID, hwAtmApsVPGIndex, hwAtmApsVPGProtectionSwitchingClearReason
				 }
			STATUS current
			DESCRIPTION 
				"alarm description:VP Channel Protection Switching is cleared
				explain： 
					1.The local/remote working channel is recovered, or there is no switchover request at present,
					2.Remote request causes switchover
				resolving method:
					1.No need to proceed
				
				
				告警描述：VP通道倒换失败
				告警原因：
				1.近端/远端工作通道恢复正常或者当前已经无倒换请求
				2.远端请求引起倒换
				修复建议：
				1.无需处理"
			::= { hwAtmApsTraps 4 }
		
		
		hwAtmApsVPGProtectionSwitchingClearFail NOTIFICATION-TYPE
			OBJECTS { hwAtmApsVPGWorkingFrameID, hwAtmApsVPGWorkingSlotID, hwAtmApsVPGWorkingPhyportID, hwAtmApsVPGIndex, hwAtmApsVPGProtectionSwitchingClearFailReason
				 }
			STATUS current
			DESCRIPTION 
				"alarm description:fail to clear VP Channel Protection Switching
				explain： 
					1.Command execution time out,
					2.VP group status abnormal caused by insufficient synchronization of active and standby boards
				resolving method:
					1.Check if the interface board works normally,
					2.There is no need to proceed. The VPRING data will be recovered within three minutes
				
				
				告警描述：VP通道倒换清除失败
				告警原因：
				1.命令执行超时
				2.主备板同步不充分引起VP组状态异常
				修复建议：
				1.检查接口板状态是否正常
				2.无需处理，等待3分钟后VPRING数据会自动恢复"
			::= { hwAtmApsTraps 5 }
		
		
		hwAtmApsVPGKByteMismatch NOTIFICATION-TYPE
			OBJECTS { hwAtmApsVPGIndex, hwAtmApsVPGProtectK1K2Rcv, hwAtmApsVPGProtectK1K2Trans, hwAtmApsVPGKByteMismatchReason }
			STATUS current
			DESCRIPTION 
				"alarm description:The received K2 byte are not the same as transmitted one
				explain： 
					1.Local and remote switchover status inconsistent,
					2.Current status of the local protection switchover is frozen
				resolving method:
					1.No need to proceed,
					2.Disable the freezing of current status of the local protection switchover
				
				
				告警描述：接收到的K2字节与发送的K2字节不一致
				告警原因：
				1.本地远端倒换状态不一致
				2.本地冻结倒换
				修复建议：
				1.无需处理
				2.取消冻结倒换"
			::= { hwAtmApsTraps 6 }
		
		
		hwAtmApsVPGStartPSFail NOTIFICATION-TYPE
			OBJECTS { hwAtmApsVPGWorkingFrameID, hwAtmApsVPGWorkingSlotID, hwAtmApsVPGWorkingPhyportID, hwAtmApsVPGIndex, hwAtmApsVPGStartPSFailReason
				 }
			STATUS current
			DESCRIPTION 
				"alarm description:fail to Start protection switching
				explain： 
					1.Command execution time out
				resolving method:
					1.Check if the interface board works normally
				
				告警描述：连续多次启动保护倒换功能失败
				告警原因：
				1.命令执行超时
				修复建议：
				1.检查接口板状态是否正常"
			::= { hwAtmApsTraps 7 }
		
		
		hwAtmApsAlmBindReason OBJECT IDENTIFIER ::= { hwVPRingSnmpTrapDef 2 }
		
		
		hwAtmApsVPGProtectionSwitchingReason OBJECT-TYPE
			SYNTAX INTEGER
				{
				lossofsignal(1),
				signaldegrade(2),
				useroperation(3),
				farProtectionSwitching(4)
				}
			MAX-ACCESS accessible-for-notify
			STATUS current
			DESCRIPTION
				"
				alarm description:VP Channel Protection Switching
					explain： 
						1.Loss of signal,
						2.Deterioration of signal,
						3.User operation,
						4.Remote request causes switchover
					resolving method:
						1.Check if the transmission optical fiber is broken,
						2.Check if the transmission line quality is deteriorated,
						3.If it is the above 3/4 reason,no need to proceed.
					
					
					告警描述：VP通道倒换
					告警原因：
					1.信号丢失
					2.信号劣化
					3.用户下发倒换命令
					4.远端节点发生倒换
					修复建议：
					1.检查传输线路是否有断纤情况
					2.检查传输线路是否有质量劣化
					3.如果是上述3、4原因，无需操作
				
				"
			::= { hwAtmApsAlmBindReason 1 }
		
		
		hwAtmApsVPGProtectionSwitchingFailReason OBJECT-TYPE
			SYNTAX INTEGER
				{
				timeout(1),
				statusabnormal(2)
				}
			MAX-ACCESS accessible-for-notify
			STATUS current
			DESCRIPTION
				"
				alarm description:VP Channel Protection Switching fails
					explain： 
						1.Command execution time out,
						2.VP group status abnormal caused by insufficient synchronization of active and standby boards
					resolving method:
						1.Check if the interface board works normally,
						2.There is no need to proceed. The VPRING data will be recovered within three minutes
					
					
					告警描述：VP通道倒换失败
					告警原因：
					1.命令执行超时
					2.主备板同步不充分引起VP组状态异常
					修复建议：
					1.检查接口板状态是否正常
					2.无需处理，等待3分钟后VPRING数据会自动恢复
				
				"
			::= { hwAtmApsAlmBindReason 2 }
		
		
		hwAtmApsVPGProtectionSwitchingClearReason OBJECT-TYPE
			SYNTAX INTEGER
				{
				farandlocalNR(1),
				farrequest(2)
				}
			MAX-ACCESS accessible-for-notify
			STATUS current
			DESCRIPTION
				"
				alarm description:VP Channel Protection Switching is cleared
					explain： 
						1.The local/remote working channel is recovered, or there is no switchover request at present,
						2.Remote request causes switchover
					resolving method:
						1.No need to proceed
					
					
					告警描述：VP通道倒换失败
					告警原因：
					1.近端/远端工作通道恢复正常或者当前已经无倒换请求
					2.远端请求引起倒换
					修复建议：
					1.无需处理
				
				"
			::= { hwAtmApsAlmBindReason 3 }
		
		
		hwAtmApsVPGProtectionSwitchingClearFailReason OBJECT-TYPE
			SYNTAX INTEGER
				{
				timeout(1),
				statusabnormal(2)
				}
			MAX-ACCESS accessible-for-notify
			STATUS current
			DESCRIPTION
				"
				alarm description:fail to clear VP Channel Protection Switching
					explain： 
						1.Command execution time out,
						2.VP group status abnormal caused by insufficient synchronization of active and standby boards
					resolving method:
						1.Check if the interface board works normally,
						2.There is no need to proceed. The VPRING data will be recovered within three minutes
					
					
					告警描述：VP通道倒换清除失败
					告警原因：
					1.命令执行超时
					2.主备板同步不充分引起VP组状态异常
					修复建议：
					1.检查接口板状态是否正常
					2.无需处理，等待3分钟后VPRING数据会自动恢复
				
				"
			::= { hwAtmApsAlmBindReason 4 }
		
		
		hwAtmApsVPGKByteMismatchReason OBJECT-TYPE
			SYNTAX INTEGER
				{
				statuserror(1),
				freezelocalswitchingstatus(2)
				}
			MAX-ACCESS accessible-for-notify
			STATUS current
			DESCRIPTION
				"
				alarm description:The received K2 byte are not the same as transmitted one
					explain： 
						1.Local and remote switchover status inconsistent,
						2.Current status of the local protection switchover is frozen
					resolving method:
						1.No need to proceed,
						2.Disable the freezing of current status of the local protection switchover
					
					
					告警描述：接收到的K2字节与发送的K2字节不一致
					告警原因：
					1.本地远端倒换状态不一致
					2.本地冻结倒换
					修复建议：
					1.无需处理
					2.取消冻结倒换
				"
			::= { hwAtmApsAlmBindReason 5 }
		
		
		hwAtmApsVPGStartPSFailReason OBJECT-TYPE
			SYNTAX INTEGER { timeout(1) }
			MAX-ACCESS accessible-for-notify
			STATUS current
			DESCRIPTION
				"
				alarm description:fail to Start protection switching
					explain： 
						1.Command execution time out
					resolving method:
						1.Check if the interface board works normally
					
					告警描述：连续多次启动保护倒换功能失败
					告警原因：
					1.命令执行超时
					修复建议：
					1.检查接口板状态是否正常
				
				"
			::= { hwAtmApsAlmBindReason 6 }
		
	
	END

--
-- HUAWEI-VPRING-MIB.my
--
