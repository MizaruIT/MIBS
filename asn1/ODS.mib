ODS-MIB DEFINITIONS ::= BEGIN



IMPORTS 





DisplayString, TruthValue					FROM SNMPv2-TC

MODULE-IDENTITY, OBJECT-TYPE, enterprises, Unsigned32		FROM SNMPv2-SMI

TRAP-TYPE							FROM RFC-1215;



opengate MODULE-IDENTITY

	LAST-UPDATED "200801100000Z"

	ORGANIZATION "Opengate Data Systems"

	CONTACT-INFO "support@opengatedata.com"

	DESCRIPTION "The MIB for Opengate Data Systems Products"

	::= { enterprises 29414 }



opengate OBJECT IDENTIFIER

	::= { enterprises 29414 }

	

ods OBJECT IDENTIFIER

	::= { opengate 1 }



deviceInfo OBJECT IDENTIFIER

	::= { ods 1 }



productTitle OBJECT-TYPE

	SYNTAX DisplayString

	MAX-ACCESS read-only

	STATUS current

	DESCRIPTION "Product name"

	::= { deviceInfo 1 }



productVersion OBJECT-TYPE

	SYNTAX DisplayString

	MAX-ACCESS read-only

	STATUS current

	DESCRIPTION "Product version"

	::= { deviceInfo 2 }



productFriendlyName OBJECT-TYPE

	SYNTAX DisplayString

	MAX-ACCESS read-only

	STATUS current

	DESCRIPTION "User-assigned name"

	::= { deviceInfo 3 }



productMacAddress OBJECT-TYPE

	SYNTAX DisplayString

	MAX-ACCESS read-only

	STATUS current

	DESCRIPTION "Product's unique MAC address"

	::= { deviceInfo 4 }



productUrl OBJECT-TYPE

	SYNTAX DisplayString

	MAX-ACCESS read-only

	STATUS current

	DESCRIPTION "Product's main URL access point"

	::= { deviceInfo 5 }



alarmTripType OBJECT-TYPE

        SYNTAX INTEGER(0..9)

        MAX-ACCESS read-only

        STATUS current

        DESCRIPTION "Type of alarm trip. 0 = None, 1 = Low, 2 = High, 3 = Unplugged"

        ::= { deviceInfo 6 }





productHardware OBJECT-TYPE

        SYNTAX DisplayString

        MAX-ACCESS read-only

        STATUS current

        DESCRIPTION "Product's hardware type"

        ::= { deviceInfo 7 }

        

sensorCountsBase OBJECT IDENTIFIER

	::= { deviceInfo 8 }

	

sensorCounts OBJECT IDENTIFIER

	::= { sensorCountsBase 1 }

	

climateCount OBJECT-TYPE

        SYNTAX INTEGER(0..16)

        MAX-ACCESS read-only

        STATUS current

        DESCRIPTION "Number of climate monitors currently plugged in"

        ::= { sensorCounts 2 }

        

powerMonitorCount OBJECT-TYPE

        SYNTAX INTEGER(0..16)

        MAX-ACCESS read-only

        STATUS current

        DESCRIPTION "Number of power monitors currently plugged in"

        ::= { sensorCounts 3 }

        

tempSensorCount OBJECT-TYPE

        SYNTAX INTEGER(0..16)

        MAX-ACCESS read-only

        STATUS current

        DESCRIPTION "Number of temperature sensors currently plugged in"

        ::= { sensorCounts 4 }

        

airflowSensorCount OBJECT-TYPE

        SYNTAX INTEGER(0..16)

        MAX-ACCESS read-only

        STATUS current

        DESCRIPTION "Number of airflow sensors currently plugged in"

        ::= { sensorCounts 5 }

        

powerOnlyCount OBJECT-TYPE

        SYNTAX INTEGER(0..16)

        MAX-ACCESS read-only

        STATUS current

        DESCRIPTION "Number of power only monitors currently plugged in"

        ::= { sensorCounts 6 }

        

doorSensorCount OBJECT-TYPE

        SYNTAX INTEGER(0..16)

        MAX-ACCESS read-only

        STATUS current

        DESCRIPTION "Number of door sensors currently plugged in"

        ::= { sensorCounts 7 }

        

waterSensorCount OBJECT-TYPE

        SYNTAX INTEGER(0..16)

        MAX-ACCESS read-only

        STATUS current

        DESCRIPTION "Number of water sensors currently plugged in"

        ::= { sensorCounts 8 }



currentSensorCount OBJECT-TYPE

        SYNTAX INTEGER(0..16)

        MAX-ACCESS read-only

        STATUS current

        DESCRIPTION "Number of current sensors currently plugged in"

        ::= { sensorCounts 9 }

        

millivoltSensorCount OBJECT-TYPE

        SYNTAX INTEGER(0..16)

        MAX-ACCESS read-only

        STATUS current

        DESCRIPTION "Number of millivolt sensors currently plugged in"

        ::= { sensorCounts 10 }

        

power3ChSensorCount OBJECT-TYPE

        SYNTAX INTEGER(0..16)

        MAX-ACCESS read-only

        STATUS current

        DESCRIPTION "Number of 3 channel power monitors currently plugged in"

        ::= { sensorCounts 11 }



outletCount OBJECT-TYPE

        SYNTAX INTEGER(0..16)

        MAX-ACCESS read-only

        STATUS current

        DESCRIPTION "Number of outlets currently plugged in"

        ::= { sensorCounts 12 }



vsfcCount OBJECT-TYPE

        SYNTAX INTEGER(0..16)

        MAX-ACCESS read-only

        STATUS current

        DESCRIPTION "Number of fan controller monitors currently plugged in"

        ::= { sensorCounts 13 }



ctrl3ChCount OBJECT-TYPE

        SYNTAX INTEGER(0..16)

        MAX-ACCESS read-only

        STATUS current

        DESCRIPTION "Number of 3 channel controllers currently plugged in"

        ::= { sensorCounts 14 }



ctrlGrpAmpsCount OBJECT-TYPE

        SYNTAX INTEGER(0..16)

        MAX-ACCESS read-only

        STATUS current

        DESCRIPTION "Number of amperage controllers currently plugged in"

        ::= { sensorCounts 15 }



ctrlOutputCount OBJECT-TYPE

        SYNTAX INTEGER(0..16)

        MAX-ACCESS read-only

        STATUS current

        DESCRIPTION "Number of output controllers currently plugged in"

        ::= { sensorCounts 16 }



dewpointSensorCount OBJECT-TYPE

        SYNTAX INTEGER(0..16)

        MAX-ACCESS read-only

        STATUS current

        DESCRIPTION "Number of dewpoint sensors currently plugged in"

        ::= { sensorCounts 17 }

        

digitalSensorCount OBJECT-TYPE

        SYNTAX INTEGER(0..16)

        MAX-ACCESS read-only

        STATUS current

        DESCRIPTION "Number of digital sensors currently plugged in"

        ::= { sensorCounts 18 }



dstsSensorCount OBJECT-TYPE

        SYNTAX INTEGER(0..16)

        MAX-ACCESS read-only

        STATUS current

        DESCRIPTION "Number of DSTS controllers currently plugged in"

        ::= { sensorCounts 19 }

        

cpmSensorCount OBJECT-TYPE

        SYNTAX INTEGER(0..16)

        MAX-ACCESS read-only

        STATUS current

        DESCRIPTION "Number of city power sensors currently plugged in"

        ::= { sensorCounts 20 }        

        

smokeAlarmSensorCount OBJECT-TYPE

        SYNTAX INTEGER(0..16)

        MAX-ACCESS read-only

        STATUS current

        DESCRIPTION "Number of smoke alarm sensors currently plugged in"

        ::= { sensorCounts 21 }

        

neg48VdcSensorCount OBJECT-TYPE

        SYNTAX INTEGER(0..16)

        MAX-ACCESS read-only

        STATUS current

        DESCRIPTION "Number of -48Vdc sensors currently plugged in"

        ::= { sensorCounts 22 }        

        

pos30VdcSensorCount OBJECT-TYPE

        SYNTAX INTEGER(0..16)

        MAX-ACCESS read-only

        STATUS current

        DESCRIPTION "Number of 30Vdc sensors currently plugged in"

        ::= { sensorCounts 23 }             



fancontrollerCount OBJECT-TYPE

        SYNTAX INTEGER(0..16)

        MAX-ACCESS read-only

        STATUS current

        DESCRIPTION "ODS EC Fan Controller"

        ::= { sensorCounts 24 }             



climateTable OBJECT-TYPE

	SYNTAX SEQUENCE OF ClimateEntry

	MAX-ACCESS  not-accessible

	STATUS current

	DESCRIPTION "Climate sensors (internal sensors for climate units)"

	::= { ods 2 }



powerMonitorTable OBJECT-TYPE

	SYNTAX SEQUENCE OF PowerMonitorEntry

	MAX-ACCESS  not-accessible

	STATUS current

	DESCRIPTION "A table of Power Monitors"

	::= { ods 3 }



tempSensorTable OBJECT-TYPE

	SYNTAX SEQUENCE OF TempSensorEntry

	MAX-ACCESS  not-accessible

	STATUS current

	DESCRIPTION "A table of temperature sensors"

	::= { ods 4 }



airFlowSensorTable OBJECT-TYPE

	SYNTAX SEQUENCE OF AirFlowSensorEntry

	MAX-ACCESS  not-accessible

	STATUS current

	DESCRIPTION "A table of airflow sensors"

	::= { ods 5 }



powerOnlyTable OBJECT-TYPE

	SYNTAX SEQUENCE OF PowerOnlyEntry

	MAX-ACCESS  not-accessible

	STATUS current

	DESCRIPTION "A table of Power-Only devices"

	::= { ods 6 }



doorSensorTable OBJECT-TYPE

	SYNTAX SEQUENCE OF DoorSensorEntry

	MAX-ACCESS  not-accessible

	STATUS current

	DESCRIPTION "A table of door sensors"

	::= { ods 7 }



waterSensorTable OBJECT-TYPE

	SYNTAX SEQUENCE OF WaterSensorEntry

	MAX-ACCESS  not-accessible

	STATUS current

	DESCRIPTION "A table of water sensors"

	::= { ods 8 }



currentMonitorTable OBJECT-TYPE

	SYNTAX SEQUENCE OF CurrentMonitorEntry

	MAX-ACCESS  not-accessible

	STATUS current

	DESCRIPTION "A table of current monitors"

	::= { ods 9 }



millivoltMonitorTable OBJECT-TYPE

	SYNTAX SEQUENCE OF MillivoltMonitorEntry

	MAX-ACCESS  not-accessible

	STATUS current

	DESCRIPTION "A table of millivolt monitors"

	::= { ods 10 }



power3ChTable OBJECT-TYPE

	SYNTAX SEQUENCE OF Power3ChEntry

	MAX-ACCESS  not-accessible

	STATUS current

	DESCRIPTION "A table of Power Monitor 3 Channel"

	::= { ods 11 }



outletTable OBJECT-TYPE

	SYNTAX SEQUENCE OF OutletEntry

	MAX-ACCESS  not-accessible

	STATUS current

	DESCRIPTION "A table of outlets"

	::= { ods 12 }



vsfcTable OBJECT-TYPE

	SYNTAX SEQUENCE OF VsfcEntry

	MAX-ACCESS  not-accessible

	STATUS current

	DESCRIPTION "VSFC sensors (internal sensors for VSFC units)"

	::= { ods 13 }



ctrl3ChTable OBJECT-TYPE

	SYNTAX SEQUENCE OF Ctrl3ChEntry

	MAX-ACCESS  not-accessible

	STATUS current

	DESCRIPTION "A table of a 3 phase outlet control"

	::= { ods 14 }



ctrlGrpAmpsTable OBJECT-TYPE

	SYNTAX SEQUENCE OF CtrlGrpAmpsEntry

	MAX-ACCESS  not-accessible

	STATUS current

	DESCRIPTION "A table of Control Group Amp readings"

	::= { ods 15 }



ctrlOutletTable OBJECT-TYPE

	SYNTAX SEQUENCE OF CtrlOutletEntry

	MAX-ACCESS  not-accessible

	STATUS current

	DESCRIPTION "A table of outlet information"

	::= { ods 16 }



dewPointSensorTable OBJECT-TYPE

	SYNTAX SEQUENCE OF DewPointSensorEntry

	MAX-ACCESS  not-accessible

	STATUS current

	DESCRIPTION "A table of dew point sensors"

	::= { ods 17 }



digitalSensorTable OBJECT-TYPE

	SYNTAX SEQUENCE OF DigitalSensorEntry

	MAX-ACCESS  not-accessible

	STATUS current

	DESCRIPTION "A table of digital sensors"

	::= { ods 18 }



dstsTable OBJECT-TYPE

	SYNTAX SEQUENCE OF DstsEntry

	MAX-ACCESS  not-accessible

	STATUS current

	DESCRIPTION "Digital Static Transfer Switch status"

	::= { ods 19 }



cpmSensorTable OBJECT-TYPE

	SYNTAX SEQUENCE OF CpmSensorEntry

	MAX-ACCESS  not-accessible

	STATUS current

	DESCRIPTION "A table of city power sensors"

	::= { ods 20 }



smokeAlarmTable OBJECT-TYPE

	SYNTAX SEQUENCE OF SmokeAlarmEntry

	MAX-ACCESS  not-accessible

	STATUS current

	DESCRIPTION "A table of smoke alarm sensors"

	::= { ods 21 }



neg48VdcSensorTable OBJECT-TYPE

	SYNTAX SEQUENCE OF Neg48VdcSensorEntry

	MAX-ACCESS  not-accessible

	STATUS current

	DESCRIPTION "A table of -48Vdc sensors"

	::= { ods 22 }



pos30VdcSensorTable OBJECT-TYPE

	SYNTAX SEQUENCE OF Pos30VdcSensorEntry

	MAX-ACCESS  not-accessible

	STATUS current

	DESCRIPTION "A table of 30Vdc sensors"

	::= { ods 23 }



fancontrolTable OBJECT-TYPE

	SYNTAX SEQUENCE OF FancontrolEntry

	MAX-ACCESS  not-accessible

	STATUS current

	DESCRIPTION "ODS EC Fan Controller status"

	::= { ods 24 }



climateEntry OBJECT-TYPE

	SYNTAX  ClimateEntry

	MAX-ACCESS  not-accessible

	STATUS current

	DESCRIPTION 

		"Entry in the climate table: each entry contains

an index (climateIndex) and other details"

	INDEX { climateIndex }

	::= { climateTable 1 }



ClimateEntry ::= SEQUENCE {

	climateIndex		INTEGER(1..1),

	climateSerial		DisplayString,

	climateName		DisplayString,

	climateAvail		Unsigned32,

	climateTempC		INTEGER(-50..100),

	climateTempF		INTEGER(-58..212),

	climateHumidity		INTEGER(0..100),

	climateLight		INTEGER(0..100),

	climateAirflow		INTEGER(0..100),

	climateSound		INTEGER(0..100),

	climateIO1		INTEGER(0..100),

	climateIO2		INTEGER(0..100),

	climateIO3		INTEGER(0..100)

}



climateIndex OBJECT-TYPE

	SYNTAX  INTEGER(1..1)

	MAX-ACCESS  not-accessible

	STATUS current

	DESCRIPTION "Table entry index value"

	::= { climateEntry  1 }

	

climateSerial OBJECT-TYPE

	SYNTAX  DisplayString

	MAX-ACCESS  read-only

	STATUS current

	DESCRIPTION "Serial Number"

	::= { climateEntry  2 }

	

climateName OBJECT-TYPE

	SYNTAX  DisplayString

	MAX-ACCESS  read-only

	STATUS current

	DESCRIPTION "Friendly Name"

	::= { climateEntry  3 }

	

climateAvail OBJECT-TYPE

	SYNTAX  Unsigned32

	MAX-ACCESS  read-only

	STATUS current

	DESCRIPTION "Is device currently plugged in?"

	::= { climateEntry  4 }

	

climateTempC OBJECT-TYPE

	SYNTAX  INTEGER(-50..100)

	MAX-ACCESS  read-only

	STATUS current

	DESCRIPTION "Current reading for Temperature (C)"

	::= { climateEntry  5 }

	

climateTempF OBJECT-TYPE

	SYNTAX  INTEGER(-58..212)

	MAX-ACCESS  read-only

	STATUS current

	DESCRIPTION "Current reading for Temperature (F)"

	::= { climateEntry  6 }

	

climateHumidity OBJECT-TYPE

	SYNTAX  INTEGER(0..100)

	MAX-ACCESS  read-only

	STATUS current

	DESCRIPTION "Current reading for Humidity"

	::= { climateEntry  7 }

	

climateLight OBJECT-TYPE

	SYNTAX  INTEGER(0..100)

	MAX-ACCESS  read-only

	STATUS current

	DESCRIPTION "Current reading for Ambient Light"

	::= { climateEntry  8 }

	

climateAirflow OBJECT-TYPE

	SYNTAX  INTEGER(0..100)

	MAX-ACCESS  read-only

	STATUS current

	DESCRIPTION "Current reading for Airflow"

	::= { climateEntry  9 }

	

climateSound OBJECT-TYPE

	SYNTAX  INTEGER(0..100)

	MAX-ACCESS  read-only

	STATUS current

	DESCRIPTION "Current reading for Sound"

	::= { climateEntry  10 }

	

climateIO1 OBJECT-TYPE

	SYNTAX  INTEGER(0..100)

	MAX-ACCESS  read-only

	STATUS current

	DESCRIPTION "Current reading for Analog Input 1"

	::= { climateEntry  11 }

	

climateIO2 OBJECT-TYPE

	SYNTAX  INTEGER(0..100)

	MAX-ACCESS  read-only

	STATUS current

	DESCRIPTION "Current reading for Analog Input 2"

	::= { climateEntry  12 }

	

climateIO3 OBJECT-TYPE

	SYNTAX  INTEGER(0..100)

	MAX-ACCESS  read-only

	STATUS current

	DESCRIPTION "Current reading for Analog Input 3"

	::= { climateEntry  13 }

	

powerMonitorEntry OBJECT-TYPE

	SYNTAX  PowerMonitorEntry

	MAX-ACCESS  not-accessible

	STATUS current

	DESCRIPTION 

		"Entry in the power monitor table: each entry contains

an index (powMonIndex) and other power monitoring details"

	INDEX { powMonIndex }

	::= { powerMonitorTable 1 }



PowerMonitorEntry ::= SEQUENCE {

	powMonIndex		INTEGER(1..100),

	powMonSerial		DisplayString,

	powMonName		DisplayString,

	powMonAvail		Unsigned32,

	powMonKWattHrs		Unsigned32,

	powMonVolts		Unsigned32,

	powMonVoltMax		Unsigned32,

	powMonVoltMin		Unsigned32,

	powMonVoltPk		Unsigned32,

	powMonAmpsX10		Unsigned32,

	powMonRealPow		Unsigned32,

	powMonAppPow		Unsigned32,

	powMonPwrFact		INTEGER(0..100),

	powMonOutlet1		INTEGER(0..100),

	powMonOutlet2		INTEGER(0..100)

}



powMonIndex OBJECT-TYPE

	SYNTAX  INTEGER(1..100)

	MAX-ACCESS  not-accessible

	STATUS current

	DESCRIPTION "Table entry index value"

	::= { powerMonitorEntry  1 }

	

powMonSerial OBJECT-TYPE

	SYNTAX  DisplayString

	MAX-ACCESS  read-only

	STATUS current

	DESCRIPTION "Serial Number"

	::= { powerMonitorEntry  2 }

	

powMonName OBJECT-TYPE

	SYNTAX  DisplayString

	MAX-ACCESS  read-only

	STATUS current

	DESCRIPTION "Friendly Name"

	::= { powerMonitorEntry  3 }

	

powMonAvail OBJECT-TYPE

	SYNTAX  Unsigned32

	MAX-ACCESS  read-only

	STATUS current

	DESCRIPTION "Is device currently plugged in?"

	::= { powerMonitorEntry  4 }

	

powMonKWattHrs OBJECT-TYPE

	SYNTAX  Unsigned32

	MAX-ACCESS  read-only

	STATUS current

	DESCRIPTION "KWatt-Hours"

	::= { powerMonitorEntry  5 }

	

powMonVolts OBJECT-TYPE

	SYNTAX  Unsigned32

	MAX-ACCESS  read-only

	STATUS current

	DESCRIPTION "Volts"

	::= { powerMonitorEntry  6 }

	

powMonVoltMax OBJECT-TYPE

	SYNTAX  Unsigned32

	MAX-ACCESS  read-only

	STATUS current

	DESCRIPTION "Volts (Max)"

	::= { powerMonitorEntry  7 }

	

powMonVoltMin OBJECT-TYPE

	SYNTAX  Unsigned32

	MAX-ACCESS  read-only

	STATUS current

	DESCRIPTION "Volts (Min)"

	::= { powerMonitorEntry  8 }

	

powMonVoltPk OBJECT-TYPE

	SYNTAX  Unsigned32

	MAX-ACCESS  read-only

	STATUS current

	DESCRIPTION "Volts (Peak)"

	::= { powerMonitorEntry  9 }

	

powMonAmpsX10 OBJECT-TYPE

	SYNTAX  Unsigned32

	MAX-ACCESS  read-only

	STATUS current

	DESCRIPTION "Amps x 10"

	::= { powerMonitorEntry  10 }

	

powMonRealPow OBJECT-TYPE

	SYNTAX  Unsigned32

	MAX-ACCESS  read-only

	STATUS current

	DESCRIPTION "Real Power"

	::= { powerMonitorEntry  11 }

	

powMonAppPow OBJECT-TYPE

	SYNTAX  Unsigned32

	MAX-ACCESS  read-only

	STATUS current

	DESCRIPTION "Apparent Power"

	::= { powerMonitorEntry  12 }

	

powMonPwrFact OBJECT-TYPE

	SYNTAX  INTEGER(0..100)

	MAX-ACCESS  read-only

	STATUS current

	DESCRIPTION "Power Factor"

	::= { powerMonitorEntry  13 }

	

powMonOutlet1 OBJECT-TYPE

	SYNTAX  INTEGER(0..100)

	MAX-ACCESS  read-only

	STATUS current

	DESCRIPTION "Outlet 1"

	::= { powerMonitorEntry  14 }

	

powMonOutlet2 OBJECT-TYPE

	SYNTAX  INTEGER(0..100)

	MAX-ACCESS  read-only

	STATUS current

	DESCRIPTION "Outlet 2"

	::= { powerMonitorEntry  15 }

	

tempSensorEntry OBJECT-TYPE

	SYNTAX  TempSensorEntry

	MAX-ACCESS  not-accessible

	STATUS current

	DESCRIPTION 

		"Entry in the temperature sensor table: each entry contains

an index (tempIndex) and other sensor details"

	INDEX { tempSensorIndex }

	::= { tempSensorTable 1 }



TempSensorEntry ::= SEQUENCE {

	tempSensorIndex		INTEGER(1..100),

	tempSensorSerial		DisplayString,

	tempSensorName		DisplayString,

	tempSensorAvail		Unsigned32,

	tempSensorTempC		INTEGER(-50..100),

	tempSensorTempF		INTEGER(-58..212)

}



tempSensorIndex OBJECT-TYPE

	SYNTAX  INTEGER(1..100)

	MAX-ACCESS  not-accessible

	STATUS current

	DESCRIPTION "Table entry index value"

	::= { tempSensorEntry  1 }

	

tempSensorSerial OBJECT-TYPE

	SYNTAX  DisplayString

	MAX-ACCESS  read-only

	STATUS current

	DESCRIPTION "Serial Number"

	::= { tempSensorEntry  2 }

	

tempSensorName OBJECT-TYPE

	SYNTAX  DisplayString

	MAX-ACCESS  read-only

	STATUS current

	DESCRIPTION "Friendly Name"

	::= { tempSensorEntry  3 }

	

tempSensorAvail OBJECT-TYPE

	SYNTAX  Unsigned32

	MAX-ACCESS  read-only

	STATUS current

	DESCRIPTION "Is device currently plugged in?"

	::= { tempSensorEntry  4 }

	

tempSensorTempC OBJECT-TYPE

	SYNTAX  INTEGER(-50..100)

	MAX-ACCESS  read-only

	STATUS current

	DESCRIPTION "Temperature in Celsius"

	::= { tempSensorEntry  5 }

	

tempSensorTempF OBJECT-TYPE

	SYNTAX  INTEGER(-58..212)

	MAX-ACCESS  read-only

	STATUS current

	DESCRIPTION "Temperature in Fahrenheit"

	::= { tempSensorEntry  6 }

	

airFlowSensorEntry OBJECT-TYPE

	SYNTAX  AirFlowSensorEntry

	MAX-ACCESS  not-accessible

	STATUS current

	DESCRIPTION 

		"Entry in the air flow sensor table: each entry contains

an index (airFlowSensorIndex) and other sensor details"

	INDEX { airFlowSensorIndex }

	::= { airFlowSensorTable 1 }



AirFlowSensorEntry ::= SEQUENCE {

	airFlowSensorIndex		INTEGER(1..100),

	airFlowSensorSerial		DisplayString,

	airFlowSensorName		DisplayString,

	airFlowSensorAvail		Unsigned32,

	airFlowSensorFlow		INTEGER(0..100),

	airFlowSensorTempC		INTEGER(-50..100),

	airFlowSensorTempF		INTEGER(-58..212),

	airFlowSensorHumidity		INTEGER(0..100)

}



airFlowSensorIndex OBJECT-TYPE

	SYNTAX  INTEGER(1..100)

	MAX-ACCESS  not-accessible

	STATUS current

	DESCRIPTION "Table entry index value"

	::= { airFlowSensorEntry  1 }

	

airFlowSensorSerial OBJECT-TYPE

	SYNTAX  DisplayString

	MAX-ACCESS  read-only

	STATUS current

	DESCRIPTION "Serial Number"

	::= { airFlowSensorEntry  2 }

	

airFlowSensorName OBJECT-TYPE

	SYNTAX  DisplayString

	MAX-ACCESS  read-only

	STATUS current

	DESCRIPTION "Friendly Name"

	::= { airFlowSensorEntry  3 }

	

airFlowSensorAvail OBJECT-TYPE

	SYNTAX  Unsigned32

	MAX-ACCESS  read-only

	STATUS current

	DESCRIPTION "Is device currently plugged in?"

	::= { airFlowSensorEntry  4 }

	

airFlowSensorFlow OBJECT-TYPE

	SYNTAX  INTEGER(0..100)

	MAX-ACCESS  read-only

	STATUS current

	DESCRIPTION "Air flow reading"

	::= { airFlowSensorEntry  5 }

	

airFlowSensorTempC OBJECT-TYPE

	SYNTAX  INTEGER(-50..100)

	MAX-ACCESS  read-only

	STATUS current

	DESCRIPTION "Temperature reading in C"

	::= { airFlowSensorEntry  6 }

	

airFlowSensorTempF OBJECT-TYPE

	SYNTAX  INTEGER(-58..212)

	MAX-ACCESS  read-only

	STATUS current

	DESCRIPTION "Temperature reading in F"

	::= { airFlowSensorEntry  7 }

	

airFlowSensorHumidity OBJECT-TYPE

	SYNTAX  INTEGER(0..100)

	MAX-ACCESS  read-only

	STATUS current

	DESCRIPTION "Humidity reading"

	::= { airFlowSensorEntry  8 }

	

powerOnlyEntry OBJECT-TYPE

	SYNTAX  PowerOnlyEntry

	MAX-ACCESS  not-accessible

	STATUS current

	DESCRIPTION 

		"Entry in the power-only device table: each entry contains

an index (powerIndex) and other power details"

	INDEX { powerIndex }

	::= { powerOnlyTable 1 }



PowerOnlyEntry ::= SEQUENCE {

	powerIndex		INTEGER(1..100),

	powerSerial		DisplayString,

	powerName		DisplayString,

	powerAvail		Unsigned32,

	powerVolts		Unsigned32,

	powerAmps		Unsigned32,

	powerRealPow		Unsigned32,

	powerAppPow		Unsigned32,

	powerPwrFactor		INTEGER(0..100)

}



powerIndex OBJECT-TYPE

	SYNTAX  INTEGER(1..100)

	MAX-ACCESS  not-accessible

	STATUS current

	DESCRIPTION "Table entry index value"

	::= { powerOnlyEntry  1 }

	

powerSerial OBJECT-TYPE

	SYNTAX  DisplayString

	MAX-ACCESS  read-only

	STATUS current

	DESCRIPTION "Serial Number"

	::= { powerOnlyEntry  2 }

	

powerName OBJECT-TYPE

	SYNTAX  DisplayString

	MAX-ACCESS  read-only

	STATUS current

	DESCRIPTION "Friendly Name"

	::= { powerOnlyEntry  3 }

	

powerAvail OBJECT-TYPE

	SYNTAX  Unsigned32

	MAX-ACCESS  read-only

	STATUS current

	DESCRIPTION "Is device currently plugged in?"

	::= { powerOnlyEntry  4 }

	

powerVolts OBJECT-TYPE

	SYNTAX  Unsigned32

	MAX-ACCESS  read-only

	STATUS current

	DESCRIPTION "Volts"

	::= { powerOnlyEntry  5 }

	

powerAmps OBJECT-TYPE

	SYNTAX  Unsigned32

	MAX-ACCESS  read-only

	STATUS current

	DESCRIPTION "Amps"

	::= { powerOnlyEntry  6 }

	

powerRealPow OBJECT-TYPE

	SYNTAX  Unsigned32

	MAX-ACCESS  read-only

	STATUS current

	DESCRIPTION "Real Power"

	::= { powerOnlyEntry  7 }

	

powerAppPow OBJECT-TYPE

	SYNTAX  Unsigned32

	MAX-ACCESS  read-only

	STATUS current

	DESCRIPTION "Apparent Power"

	::= { powerOnlyEntry  8 }

	

powerPwrFactor OBJECT-TYPE

	SYNTAX  INTEGER(0..100)

	MAX-ACCESS  read-only

	STATUS current

	DESCRIPTION "Power Factor"

	::= { powerOnlyEntry  9 }

	

doorSensorEntry OBJECT-TYPE

	SYNTAX  DoorSensorEntry

	MAX-ACCESS  not-accessible

	STATUS current

	DESCRIPTION 

		"Entry in the door sensor table: each entry contains

an index (doorSensorIndex) and other sensor details"

	INDEX { doorSensorIndex }

	::= { doorSensorTable 1 }



DoorSensorEntry ::= SEQUENCE {

	doorSensorIndex		INTEGER(1..100),

	doorSensorSerial		DisplayString,

	doorSensorName		DisplayString,

	doorSensorAvail		Unsigned32,

	doorSensorStatus		INTEGER(0..100)

}



doorSensorIndex OBJECT-TYPE

	SYNTAX  INTEGER(1..100)

	MAX-ACCESS  not-accessible

	STATUS current

	DESCRIPTION "Table entry index value"

	::= { doorSensorEntry  1 }

	

doorSensorSerial OBJECT-TYPE

	SYNTAX  DisplayString

	MAX-ACCESS  read-only

	STATUS current

	DESCRIPTION "Serial Number"

	::= { doorSensorEntry  2 }

	

doorSensorName OBJECT-TYPE

	SYNTAX  DisplayString

	MAX-ACCESS  read-only

	STATUS current

	DESCRIPTION "Friendly Name"

	::= { doorSensorEntry  3 }

	

doorSensorAvail OBJECT-TYPE

	SYNTAX  Unsigned32

	MAX-ACCESS  read-only

	STATUS current

	DESCRIPTION "Is device currently plugged in?"

	::= { doorSensorEntry  4 }

	

doorSensorStatus OBJECT-TYPE

	SYNTAX  INTEGER(0..100)

	MAX-ACCESS  read-only

	STATUS current

	DESCRIPTION "Door sensor status"

	::= { doorSensorEntry  5 }

	

waterSensorEntry OBJECT-TYPE

	SYNTAX  WaterSensorEntry

	MAX-ACCESS  not-accessible

	STATUS current

	DESCRIPTION 

		"Entry in the water sensor table: each entry contains

an index (waterSensorIndex) and other sensor details"

	INDEX { waterSensorIndex }

	::= { waterSensorTable 1 }



WaterSensorEntry ::= SEQUENCE {

	waterSensorIndex		INTEGER(1..100),

	waterSensorSerial		DisplayString,

	waterSensorName		DisplayString,

	waterSensorAvail		Unsigned32,

	waterSensorDampness		INTEGER(0..100)

}



waterSensorIndex OBJECT-TYPE

	SYNTAX  INTEGER(1..100)

	MAX-ACCESS  not-accessible

	STATUS current

	DESCRIPTION "Table entry index value"

	::= { waterSensorEntry  1 }

	

waterSensorSerial OBJECT-TYPE

	SYNTAX  DisplayString

	MAX-ACCESS  read-only

	STATUS current

	DESCRIPTION "Serial Number"

	::= { waterSensorEntry  2 }

	

waterSensorName OBJECT-TYPE

	SYNTAX  DisplayString

	MAX-ACCESS  read-only

	STATUS current

	DESCRIPTION "Friendly Name"

	::= { waterSensorEntry  3 }

	

waterSensorAvail OBJECT-TYPE

	SYNTAX  Unsigned32

	MAX-ACCESS  read-only

	STATUS current

	DESCRIPTION "Is device currently plugged in?"

	::= { waterSensorEntry  4 }

	

waterSensorDampness OBJECT-TYPE

	SYNTAX  INTEGER(0..100)

	MAX-ACCESS  read-only

	STATUS current

	DESCRIPTION "Dampness of the water sensor"

	::= { waterSensorEntry  5 }

	

currentMonitorEntry OBJECT-TYPE

	SYNTAX  CurrentMonitorEntry

	MAX-ACCESS  not-accessible

	STATUS current

	DESCRIPTION 

		"Entry in the current monitor table: each entry contains

an index (currentMonitorIndex) and other sensor details"

	INDEX { currentMonitorIndex }

	::= { currentMonitorTable 1 }



CurrentMonitorEntry ::= SEQUENCE {

	currentMonitorIndex		INTEGER(1..100),

	currentMonitorSerial		DisplayString,

	currentMonitorName		DisplayString,

	currentMonitorAvail		Unsigned32,

	currentMonitorAmps		INTEGER(0..30)

}



currentMonitorIndex OBJECT-TYPE

	SYNTAX  INTEGER(1..100)

	MAX-ACCESS  not-accessible

	STATUS current

	DESCRIPTION "Table entry index value"

	::= { currentMonitorEntry  1 }

	

currentMonitorSerial OBJECT-TYPE

	SYNTAX  DisplayString

	MAX-ACCESS  read-only

	STATUS current

	DESCRIPTION "Serial Number"

	::= { currentMonitorEntry  2 }

	

currentMonitorName OBJECT-TYPE

	SYNTAX  DisplayString

	MAX-ACCESS  read-only

	STATUS current

	DESCRIPTION "Friendly Name"

	::= { currentMonitorEntry  3 }

	

currentMonitorAvail OBJECT-TYPE

	SYNTAX  Unsigned32

	MAX-ACCESS  read-only

	STATUS current

	DESCRIPTION "Is device currently plugged in?"

	::= { currentMonitorEntry  4 }

	

currentMonitorAmps OBJECT-TYPE

	SYNTAX  INTEGER(0..30)

	MAX-ACCESS  read-only

	STATUS current

	DESCRIPTION "Current in amps"

	::= { currentMonitorEntry  5 }

	

millivoltMonitorEntry OBJECT-TYPE

	SYNTAX  MillivoltMonitorEntry

	MAX-ACCESS  not-accessible

	STATUS current

	DESCRIPTION 

		"Entry in the millivolt monitor table: each entry contains

an index (millivoltMonitorIndex) and other sensor details"

	INDEX { millivoltMonitorIndex }

	::= { millivoltMonitorTable 1 }



MillivoltMonitorEntry ::= SEQUENCE {

	millivoltMonitorIndex		INTEGER(1..100),

	millivoltMonitorSerial		DisplayString,

	millivoltMonitorName		DisplayString,

	millivoltMonitorAvail		Unsigned32,

	millivoltMonitorMV		INTEGER(0..5000)

}



millivoltMonitorIndex OBJECT-TYPE

	SYNTAX  INTEGER(1..100)

	MAX-ACCESS  not-accessible

	STATUS current

	DESCRIPTION "Table entry index value"

	::= { millivoltMonitorEntry  1 }

	

millivoltMonitorSerial OBJECT-TYPE

	SYNTAX  DisplayString

	MAX-ACCESS  read-only

	STATUS current

	DESCRIPTION "Serial Number"

	::= { millivoltMonitorEntry  2 }

	

millivoltMonitorName OBJECT-TYPE

	SYNTAX  DisplayString

	MAX-ACCESS  read-only

	STATUS current

	DESCRIPTION "Friendly Name"

	::= { millivoltMonitorEntry  3 }

	

millivoltMonitorAvail OBJECT-TYPE

	SYNTAX  Unsigned32

	MAX-ACCESS  read-only

	STATUS current

	DESCRIPTION "Is device currently plugged in?"

	::= { millivoltMonitorEntry  4 }

	

millivoltMonitorMV OBJECT-TYPE

	SYNTAX  INTEGER(0..5000)

	MAX-ACCESS  read-only

	STATUS current

	DESCRIPTION "millivolts"

	::= { millivoltMonitorEntry  5 }

	

power3ChEntry OBJECT-TYPE

	SYNTAX  Power3ChEntry

	MAX-ACCESS  not-accessible

	STATUS current

	DESCRIPTION 

		"Entry in the power monitor 3 channel table: each entry contains

an index (pow3ChIndex) and other power monitoring details"

	INDEX { pow3ChIndex }

	::= { power3ChTable 1 }



Power3ChEntry ::= SEQUENCE {

	pow3ChIndex		INTEGER(1..100),

	pow3ChSerial		DisplayString,

	pow3ChName		DisplayString,

	pow3ChAvail		Unsigned32,

	pow3ChKWattHrsA		Unsigned32,

	pow3ChVoltsA		Unsigned32,

	pow3ChVoltMaxA		Unsigned32,

	pow3ChVoltMinA		Unsigned32,

	pow3ChVoltPkA		Unsigned32,

	pow3ChAmpsX10A		Unsigned32,

	pow3ChRealPowA		Unsigned32,

	pow3ChAppPowA		Unsigned32,

	pow3ChPwrFactA		INTEGER(0..100),

	pow3ChKWattHrsB		Unsigned32,

	pow3ChVoltsB		Unsigned32,

	pow3ChVoltMaxB		Unsigned32,

	pow3ChVoltMinB		Unsigned32,

	pow3ChVoltPkB		Unsigned32,

	pow3ChAmpsX10B		Unsigned32,

	pow3ChRealPowB		Unsigned32,

	pow3ChAppPowB		Unsigned32,

	pow3ChPwrFactB		INTEGER(0..100),

	pow3ChKWattHrsC		Unsigned32,

	pow3ChVoltsC		Unsigned32,

	pow3ChVoltMaxC		Unsigned32,

	pow3ChVoltMinC		Unsigned32,

	pow3ChVoltPkC		Unsigned32,

	pow3ChAmpsX10C		Unsigned32,

	pow3ChRealPowC		Unsigned32,

	pow3ChAppPowC		Unsigned32,

	pow3ChPwrFactC		INTEGER(0..100)

}



pow3ChIndex OBJECT-TYPE

	SYNTAX  INTEGER(1..100)

	MAX-ACCESS  not-accessible

	STATUS current

	DESCRIPTION "Table entry index value"

	::= { power3ChEntry  1 }

	

pow3ChSerial OBJECT-TYPE

	SYNTAX  DisplayString

	MAX-ACCESS  read-only

	STATUS current

	DESCRIPTION "Serial Number"

	::= { power3ChEntry  2 }

	

pow3ChName OBJECT-TYPE

	SYNTAX  DisplayString

	MAX-ACCESS  read-only

	STATUS current

	DESCRIPTION "Friendly Name"

	::= { power3ChEntry  3 }

	

pow3ChAvail OBJECT-TYPE

	SYNTAX  Unsigned32

	MAX-ACCESS  read-only

	STATUS current

	DESCRIPTION "Is device currently plugged in?"

	::= { power3ChEntry  4 }

	

pow3ChKWattHrsA OBJECT-TYPE

	SYNTAX  Unsigned32

	MAX-ACCESS  read-only

	STATUS current

	DESCRIPTION "KWatt-Hours A"

	::= { power3ChEntry  5 }

	

pow3ChVoltsA OBJECT-TYPE

	SYNTAX  Unsigned32

	MAX-ACCESS  read-only

	STATUS current

	DESCRIPTION "Volts A"

	::= { power3ChEntry  6 }

	

pow3ChVoltMaxA OBJECT-TYPE

	SYNTAX  Unsigned32

	MAX-ACCESS  read-only

	STATUS current

	DESCRIPTION "Volts (Max) A"

	::= { power3ChEntry  7 }

	

pow3ChVoltMinA OBJECT-TYPE

	SYNTAX  Unsigned32

	MAX-ACCESS  read-only

	STATUS current

	DESCRIPTION "Volts (Min) A"

	::= { power3ChEntry  8 }

	

pow3ChVoltPkA OBJECT-TYPE

	SYNTAX  Unsigned32

	MAX-ACCESS  read-only

	STATUS current

	DESCRIPTION "Volts (Peak) A"

	::= { power3ChEntry  9 }

	

pow3ChAmpsX10A OBJECT-TYPE

	SYNTAX  Unsigned32

	MAX-ACCESS  read-only

	STATUS current

	DESCRIPTION "Amps x 10 A"

	::= { power3ChEntry  10 }

	

pow3ChRealPowA OBJECT-TYPE

	SYNTAX  Unsigned32

	MAX-ACCESS  read-only

	STATUS current

	DESCRIPTION "Real Power A"

	::= { power3ChEntry  11 }

	

pow3ChAppPowA OBJECT-TYPE

	SYNTAX  Unsigned32

	MAX-ACCESS  read-only

	STATUS current

	DESCRIPTION "Apparent Power A"

	::= { power3ChEntry  12 }

	

pow3ChPwrFactA OBJECT-TYPE

	SYNTAX  INTEGER(0..100)

	MAX-ACCESS  read-only

	STATUS current

	DESCRIPTION "Power Factor A"

	::= { power3ChEntry  13 }

	

pow3ChKWattHrsB OBJECT-TYPE

	SYNTAX  Unsigned32

	MAX-ACCESS  read-only

	STATUS current

	DESCRIPTION "KWatt-Hours B"

	::= { power3ChEntry  14 }

	

pow3ChVoltsB OBJECT-TYPE

	SYNTAX  Unsigned32

	MAX-ACCESS  read-only

	STATUS current

	DESCRIPTION "Volts B"

	::= { power3ChEntry  15 }

	

pow3ChVoltMaxB OBJECT-TYPE

	SYNTAX  Unsigned32

	MAX-ACCESS  read-only

	STATUS current

	DESCRIPTION "Volts (Max) B"

	::= { power3ChEntry  16 }

	

pow3ChVoltMinB OBJECT-TYPE

	SYNTAX  Unsigned32

	MAX-ACCESS  read-only

	STATUS current

	DESCRIPTION "Volts (Min) B"

	::= { power3ChEntry  17 }

	

pow3ChVoltPkB OBJECT-TYPE

	SYNTAX  Unsigned32

	MAX-ACCESS  read-only

	STATUS current

	DESCRIPTION "Volts (Peak) B"

	::= { power3ChEntry  18 }

	

pow3ChAmpsX10B OBJECT-TYPE

	SYNTAX  Unsigned32

	MAX-ACCESS  read-only

	STATUS current

	DESCRIPTION "Amps x 10 B"

	::= { power3ChEntry  19 }

	

pow3ChRealPowB OBJECT-TYPE

	SYNTAX  Unsigned32

	MAX-ACCESS  read-only

	STATUS current

	DESCRIPTION "Real Power B"

	::= { power3ChEntry  20 }

	

pow3ChAppPowB OBJECT-TYPE

	SYNTAX  Unsigned32

	MAX-ACCESS  read-only

	STATUS current

	DESCRIPTION "Apparent Power B"

	::= { power3ChEntry  21 }

	

pow3ChPwrFactB OBJECT-TYPE

	SYNTAX  INTEGER(0..100)

	MAX-ACCESS  read-only

	STATUS current

	DESCRIPTION "Power Factor B"

	::= { power3ChEntry  22 }

	

pow3ChKWattHrsC OBJECT-TYPE

	SYNTAX  Unsigned32

	MAX-ACCESS  read-only

	STATUS current

	DESCRIPTION "KWatt-Hours C"

	::= { power3ChEntry  23 }

	

pow3ChVoltsC OBJECT-TYPE

	SYNTAX  Unsigned32

	MAX-ACCESS  read-only

	STATUS current

	DESCRIPTION "Volts C"

	::= { power3ChEntry  24 }

	

pow3ChVoltMaxC OBJECT-TYPE

	SYNTAX  Unsigned32

	MAX-ACCESS  read-only

	STATUS current

	DESCRIPTION "Volts (Max) C"

	::= { power3ChEntry  25 }

	

pow3ChVoltMinC OBJECT-TYPE

	SYNTAX  Unsigned32

	MAX-ACCESS  read-only

	STATUS current

	DESCRIPTION "Volts (Min) C"

	::= { power3ChEntry  26 }

	

pow3ChVoltPkC OBJECT-TYPE

	SYNTAX  Unsigned32

	MAX-ACCESS  read-only

	STATUS current

	DESCRIPTION "Volts (Peak) C"

	::= { power3ChEntry  27 }

	

pow3ChAmpsX10C OBJECT-TYPE

	SYNTAX  Unsigned32

	MAX-ACCESS  read-only

	STATUS current

	DESCRIPTION "Amps x 10 C"

	::= { power3ChEntry  28 }

	

pow3ChRealPowC OBJECT-TYPE

	SYNTAX  Unsigned32

	MAX-ACCESS  read-only

	STATUS current

	DESCRIPTION "Real Power C"

	::= { power3ChEntry  29 }

	

pow3ChAppPowC OBJECT-TYPE

	SYNTAX  Unsigned32

	MAX-ACCESS  read-only

	STATUS current

	DESCRIPTION "Apparent Power C"

	::= { power3ChEntry  30 }

	

pow3ChPwrFactC OBJECT-TYPE

	SYNTAX  INTEGER(0..100)

	MAX-ACCESS  read-only

	STATUS current

	DESCRIPTION "Power Factor C"

	::= { power3ChEntry  31 }

	

outletEntry OBJECT-TYPE

	SYNTAX  OutletEntry

	MAX-ACCESS  not-accessible

	STATUS current

	DESCRIPTION 

		"Entry in the outlet table: each entry contains

an index (outletIndex) and other sensor details"

	INDEX { outletIndex }

	::= { outletTable 1 }



OutletEntry ::= SEQUENCE {

	outletIndex		INTEGER(1..100),

	outletSerial		DisplayString,

	outletName		DisplayString,

	outletAvail		Unsigned32,

	outlet1Status		INTEGER(0..100),

	outlet2Status		INTEGER(0..100)

}



outletIndex OBJECT-TYPE

	SYNTAX  INTEGER(1..100)

	MAX-ACCESS  not-accessible

	STATUS current

	DESCRIPTION "Table entry index value"

	::= { outletEntry  1 }

	

outletSerial OBJECT-TYPE

	SYNTAX  DisplayString

	MAX-ACCESS  read-only

	STATUS current

	DESCRIPTION "Serial Number"

	::= { outletEntry  2 }

	

outletName OBJECT-TYPE

	SYNTAX  DisplayString

	MAX-ACCESS  read-only

	STATUS current

	DESCRIPTION "Friendly Name"

	::= { outletEntry  3 }

	

outletAvail OBJECT-TYPE

	SYNTAX  Unsigned32

	MAX-ACCESS  read-only

	STATUS current

	DESCRIPTION "Is device currently plugged in?"

	::= { outletEntry  4 }

	

outlet1Status OBJECT-TYPE

	SYNTAX  INTEGER(0..100)

	MAX-ACCESS  read-only

	STATUS current

	DESCRIPTION "Outlet 1 status"

	::= { outletEntry  5 }

	

outlet2Status OBJECT-TYPE

	SYNTAX  INTEGER(0..100)

	MAX-ACCESS  read-only

	STATUS current

	DESCRIPTION "Outlet 2 status"

	::= { outletEntry  6 }

	

vsfcEntry OBJECT-TYPE

	SYNTAX  VsfcEntry

	MAX-ACCESS  not-accessible

	STATUS current

	DESCRIPTION 

		"Entry in the vsfc table: each entry contains

an index (vsfcIndex) and other details"

	INDEX { vsfcIndex }

	::= { vsfcTable 1 }



VsfcEntry ::= SEQUENCE {

	vsfcIndex		INTEGER(1..1),

	vsfcSerial		DisplayString,

	vsfcName		DisplayString,

	vsfcAvail		Unsigned32,

	vsfcSetPointC		INTEGER(18..38),

	vsfcSetPointF		INTEGER(64..100),

	vsfcIntTempC		INTEGER(-20..50),

	vsfcIntTempF		INTEGER(-4..122),

	vsfcExt1TempC		INTEGER(-20..50),

	vsfcExt1TempF		INTEGER(-20..122),

	vsfcExt2TempC		INTEGER(-20..50),

	vsfcExt2TempF		INTEGER(-20..122),

	vsfcExt3TempC		INTEGER(-20..50),

	vsfcExt3TempF		INTEGER(-20..122),

	vsfcExt4TempC		INTEGER(-20..50),

	vsfcExt4TempF		INTEGER(-20..122),

	vsfcFanSpeed		INTEGER(0..100)

}



vsfcIndex OBJECT-TYPE

	SYNTAX  INTEGER(1..1)

	MAX-ACCESS  not-accessible

	STATUS current

	DESCRIPTION "Table entry index value"

	::= { vsfcEntry  1 }

	

vsfcSerial OBJECT-TYPE

	SYNTAX  DisplayString

	MAX-ACCESS  read-only

	STATUS current

	DESCRIPTION "Serial Number"

	::= { vsfcEntry  2 }

	

vsfcName OBJECT-TYPE

	SYNTAX  DisplayString

	MAX-ACCESS  read-only

	STATUS current

	DESCRIPTION "Friendly Name"

	::= { vsfcEntry  3 }

	

vsfcAvail OBJECT-TYPE

	SYNTAX  Unsigned32

	MAX-ACCESS  read-only

	STATUS current

	DESCRIPTION "Is device currently plugged in?"

	::= { vsfcEntry  4 }

	

vsfcSetPointC OBJECT-TYPE

	SYNTAX  INTEGER(18..38)

	MAX-ACCESS  read-only

	STATUS current

	DESCRIPTION "Current temperature set point in C"

	::= { vsfcEntry  5 }

	

vsfcSetPointF OBJECT-TYPE

	SYNTAX  INTEGER(64..100)

	MAX-ACCESS  read-only

	STATUS current

	DESCRIPTION "Current temperature set point in F"

	::= { vsfcEntry  6 }

	

vsfcIntTempC OBJECT-TYPE

	SYNTAX  INTEGER(-20..50)

	MAX-ACCESS  read-only

	STATUS current

	DESCRIPTION "Current internal temperature reading in C"

	::= { vsfcEntry  7 }

	

vsfcIntTempF OBJECT-TYPE

	SYNTAX  INTEGER(-4..122)

	MAX-ACCESS  read-only

	STATUS current

	DESCRIPTION "Current internal temperature reading in F"

	::= { vsfcEntry  8 }

	

vsfcExt1TempC OBJECT-TYPE

	SYNTAX  INTEGER(-20..50)

	MAX-ACCESS  read-only

	STATUS current

	DESCRIPTION "Current reading for external temp 1 in C"

	::= { vsfcEntry  9 }

	

vsfcExt1TempF OBJECT-TYPE

	SYNTAX  INTEGER(-20..122)

	MAX-ACCESS  read-only

	STATUS current

	DESCRIPTION "Current reading for external temp 1 in F"

	::= { vsfcEntry  10 }

	

vsfcExt2TempC OBJECT-TYPE

	SYNTAX  INTEGER(-20..50)

	MAX-ACCESS  read-only

	STATUS current

	DESCRIPTION "Current reading for external temp 2 in C"

	::= { vsfcEntry  11 }

	

vsfcExt2TempF OBJECT-TYPE

	SYNTAX  INTEGER(-20..122)

	MAX-ACCESS  read-only

	STATUS current

	DESCRIPTION "Current reading for external temp 2 in F"

	::= { vsfcEntry  12 }

	

vsfcExt3TempC OBJECT-TYPE

	SYNTAX  INTEGER(-20..50)

	MAX-ACCESS  read-only

	STATUS current

	DESCRIPTION "Current reading for external temp 3 in C"

	::= { vsfcEntry  13 }

	

vsfcExt3TempF OBJECT-TYPE

	SYNTAX  INTEGER(-20..122)

	MAX-ACCESS  read-only

	STATUS current

	DESCRIPTION "Current reading for external temp 3 in F"

	::= { vsfcEntry  14 }

	

vsfcExt4TempC OBJECT-TYPE

	SYNTAX  INTEGER(-20..50)

	MAX-ACCESS  read-only

	STATUS current

	DESCRIPTION "Current reading for external temp 4 in C"

	::= { vsfcEntry  15 }

	

vsfcExt4TempF OBJECT-TYPE

	SYNTAX  INTEGER(-20..122)

	MAX-ACCESS  read-only

	STATUS current

	DESCRIPTION "Current reading for external temp 4 in F"

	::= { vsfcEntry  16 }

	

vsfcFanSpeed OBJECT-TYPE

	SYNTAX  INTEGER(0..100)

	MAX-ACCESS  read-only

	STATUS current

	DESCRIPTION "Current reading for Fan Speed"

	::= { vsfcEntry  17 }

	

ctrl3ChEntry OBJECT-TYPE

	SYNTAX  Ctrl3ChEntry

	MAX-ACCESS  not-accessible

	STATUS current

	DESCRIPTION 

		"Entry in the 3 phase outlet control table: each entry contains

an index (ctrl3ChIndex) and other outlet control monitoring details"

	INDEX { ctrl3ChIndex }

	::= { ctrl3ChTable 1 }



Ctrl3ChEntry ::= SEQUENCE {

	ctrl3ChIndex		INTEGER(1..1),

	ctrl3ChSerial		DisplayString,

	ctrl3ChName		DisplayString,

	ctrl3ChAvail		Unsigned32,

	ctrl3ChVoltsA		Unsigned32,

	ctrl3ChVoltPkA		Unsigned32,

	ctrl3ChAmpsA		Unsigned32,

	ctrl3ChAmpPkA		Unsigned32,

	ctrl3ChRealPowA		Unsigned32,

	ctrl3ChAppPowA		Unsigned32,

	ctrl3ChPwrFactA		INTEGER(0..100),

	ctrl3ChVoltsB		Unsigned32,

	ctrl3ChVoltPkB		Unsigned32,

	ctrl3ChAmpsB		Unsigned32,

	ctrl3ChAmpPkB		Unsigned32,

	ctrl3ChRealPowB		Unsigned32,

	ctrl3ChAppPowB		Unsigned32,

	ctrl3ChPwrFactB		INTEGER(0..100),

	ctrl3ChVoltsC		Unsigned32,

	ctrl3ChVoltPkC		Unsigned32,

	ctrl3ChAmpsC		Unsigned32,

	ctrl3ChAmpPkC		Unsigned32,

	ctrl3ChRealPowC		Unsigned32,

	ctrl3ChAppPowC		Unsigned32,

	ctrl3ChPwrFactC		INTEGER(0..100)

}



ctrl3ChIndex OBJECT-TYPE

	SYNTAX  INTEGER(1..1)

	MAX-ACCESS  not-accessible

	STATUS current

	DESCRIPTION "Table entry index value"

	::= { ctrl3ChEntry  1 }

	

ctrl3ChSerial OBJECT-TYPE

	SYNTAX  DisplayString

	MAX-ACCESS  read-only

	STATUS current

	DESCRIPTION "Serial Number"

	::= { ctrl3ChEntry  2 }

	

ctrl3ChName OBJECT-TYPE

	SYNTAX  DisplayString

	MAX-ACCESS  read-only

	STATUS current

	DESCRIPTION "Friendly Name"

	::= { ctrl3ChEntry  3 }

	

ctrl3ChAvail OBJECT-TYPE

	SYNTAX  Unsigned32

	MAX-ACCESS  read-only

	STATUS current

	DESCRIPTION "Is device currently plugged in?"

	::= { ctrl3ChEntry  4 }

	

ctrl3ChVoltsA OBJECT-TYPE

	SYNTAX  Unsigned32

	MAX-ACCESS  read-only

	STATUS current

	DESCRIPTION "Volts A"

	::= { ctrl3ChEntry  5 }

	

ctrl3ChVoltPkA OBJECT-TYPE

	SYNTAX  Unsigned32

	MAX-ACCESS  read-only

	STATUS current

	DESCRIPTION "Volts (Peak) A"

	::= { ctrl3ChEntry  6 }

	

ctrl3ChAmpsA OBJECT-TYPE

	SYNTAX  Unsigned32

	MAX-ACCESS  read-only

	STATUS current

	DESCRIPTION "Amps A"

	::= { ctrl3ChEntry  7 }

	

ctrl3ChAmpPkA OBJECT-TYPE

	SYNTAX  Unsigned32

	MAX-ACCESS  read-only

	STATUS current

	DESCRIPTION "Amps Peak A"

	::= { ctrl3ChEntry  8 }

	

ctrl3ChRealPowA OBJECT-TYPE

	SYNTAX  Unsigned32

	MAX-ACCESS  read-only

	STATUS current

	DESCRIPTION "Real Power A"

	::= { ctrl3ChEntry  9 }

	

ctrl3ChAppPowA OBJECT-TYPE

	SYNTAX  Unsigned32

	MAX-ACCESS  read-only

	STATUS current

	DESCRIPTION "Apparent Power A"

	::= { ctrl3ChEntry  10 }

	

ctrl3ChPwrFactA OBJECT-TYPE

	SYNTAX  INTEGER(0..100)

	MAX-ACCESS  read-only

	STATUS current

	DESCRIPTION "Power Factor A"

	::= { ctrl3ChEntry  11 }

	

ctrl3ChVoltsB OBJECT-TYPE

	SYNTAX  Unsigned32

	MAX-ACCESS  read-only

	STATUS current

	DESCRIPTION "Volts B"

	::= { ctrl3ChEntry  12 }

	

ctrl3ChVoltPkB OBJECT-TYPE

	SYNTAX  Unsigned32

	MAX-ACCESS  read-only

	STATUS current

	DESCRIPTION "Volts (Peak) B"

	::= { ctrl3ChEntry  13 }

	

ctrl3ChAmpsB OBJECT-TYPE

	SYNTAX  Unsigned32

	MAX-ACCESS  read-only

	STATUS current

	DESCRIPTION "Amps B"

	::= { ctrl3ChEntry  14 }

	

ctrl3ChAmpPkB OBJECT-TYPE

	SYNTAX  Unsigned32

	MAX-ACCESS  read-only

	STATUS current

	DESCRIPTION "Amps Peak B"

	::= { ctrl3ChEntry  15 }

	

ctrl3ChRealPowB OBJECT-TYPE

	SYNTAX  Unsigned32

	MAX-ACCESS  read-only

	STATUS current

	DESCRIPTION "Real Power B"

	::= { ctrl3ChEntry  16 }

	

ctrl3ChAppPowB OBJECT-TYPE

	SYNTAX  Unsigned32

	MAX-ACCESS  read-only

	STATUS current

	DESCRIPTION "Apparent Power B"

	::= { ctrl3ChEntry  17 }

	

ctrl3ChPwrFactB OBJECT-TYPE

	SYNTAX  INTEGER(0..100)

	MAX-ACCESS  read-only

	STATUS current

	DESCRIPTION "Power Factor B"

	::= { ctrl3ChEntry  18 }

	

ctrl3ChVoltsC OBJECT-TYPE

	SYNTAX  Unsigned32

	MAX-ACCESS  read-only

	STATUS current

	DESCRIPTION "Volts C"

	::= { ctrl3ChEntry  19 }

	

ctrl3ChVoltPkC OBJECT-TYPE

	SYNTAX  Unsigned32

	MAX-ACCESS  read-only

	STATUS current

	DESCRIPTION "Volts (Peak) C"

	::= { ctrl3ChEntry  20 }

	

ctrl3ChAmpsC OBJECT-TYPE

	SYNTAX  Unsigned32

	MAX-ACCESS  read-only

	STATUS current

	DESCRIPTION "Amps C"

	::= { ctrl3ChEntry  21 }

	

ctrl3ChAmpPkC OBJECT-TYPE

	SYNTAX  Unsigned32

	MAX-ACCESS  read-only

	STATUS current

	DESCRIPTION "Amps Peak C"

	::= { ctrl3ChEntry  22 }

	

ctrl3ChRealPowC OBJECT-TYPE

	SYNTAX  Unsigned32

	MAX-ACCESS  read-only

	STATUS current

	DESCRIPTION "Real Power C"

	::= { ctrl3ChEntry  23 }

	

ctrl3ChAppPowC OBJECT-TYPE

	SYNTAX  Unsigned32

	MAX-ACCESS  read-only

	STATUS current

	DESCRIPTION "Apparent Power C"

	::= { ctrl3ChEntry  24 }

	

ctrl3ChPwrFactC OBJECT-TYPE

	SYNTAX  INTEGER(0..100)

	MAX-ACCESS  read-only

	STATUS current

	DESCRIPTION "Power Factor C"

	::= { ctrl3ChEntry  25 }

	

ctrlGrpAmpsEntry OBJECT-TYPE

	SYNTAX  CtrlGrpAmpsEntry

	MAX-ACCESS  not-accessible

	STATUS current

	DESCRIPTION 

		"Entry in the Control Group Amps table: each entry contains

an index (ctrlGrpAmpsIndex) and other sensor details"

	INDEX { ctrlGrpAmpsIndex }

	::= { ctrlGrpAmpsTable 1 }



CtrlGrpAmpsEntry ::= SEQUENCE {

	ctrlGrpAmpsIndex		INTEGER(1..1),

	ctrlGrpAmpsSerial		DisplayString,

	ctrlGrpAmpsName		DisplayString,

	ctrlGrpAmpsAvail		Unsigned32,

	ctrlGrpAmpsA		Unsigned32,

	ctrlGrpAmpsB		Unsigned32,

	ctrlGrpAmpsC		Unsigned32,

	ctrlGrpAmpsD		Unsigned32,

	ctrlGrpAmpsE		Unsigned32,

	ctrlGrpAmpsF		Unsigned32

}



ctrlGrpAmpsIndex OBJECT-TYPE

	SYNTAX  INTEGER(1..1)

	MAX-ACCESS  not-accessible

	STATUS current

	DESCRIPTION "Table entry index value"

	::= { ctrlGrpAmpsEntry  1 }

	

ctrlGrpAmpsSerial OBJECT-TYPE

	SYNTAX  DisplayString

	MAX-ACCESS  read-only

	STATUS current

	DESCRIPTION "Serial Number"

	::= { ctrlGrpAmpsEntry  2 }

	

ctrlGrpAmpsName OBJECT-TYPE

	SYNTAX  DisplayString

	MAX-ACCESS  read-only

	STATUS current

	DESCRIPTION "Friendly Name"

	::= { ctrlGrpAmpsEntry  3 }

	

ctrlGrpAmpsAvail OBJECT-TYPE

	SYNTAX  Unsigned32

	MAX-ACCESS  read-only

	STATUS current

	DESCRIPTION "Is device currently plugged in?"

	::= { ctrlGrpAmpsEntry  4 }

	

ctrlGrpAmpsA OBJECT-TYPE

	SYNTAX  Unsigned32

	MAX-ACCESS  read-only

	STATUS current

	DESCRIPTION "Amps Group A"

	::= { ctrlGrpAmpsEntry  5 }

	

ctrlGrpAmpsB OBJECT-TYPE

	SYNTAX  Unsigned32

	MAX-ACCESS  read-only

	STATUS current

	DESCRIPTION "Amps Group B"

	::= { ctrlGrpAmpsEntry  6 }

	

ctrlGrpAmpsC OBJECT-TYPE

	SYNTAX  Unsigned32

	MAX-ACCESS  read-only

	STATUS current

	DESCRIPTION "Amps Group C"

	::= { ctrlGrpAmpsEntry  7 }

	

ctrlGrpAmpsD OBJECT-TYPE

	SYNTAX  Unsigned32

	MAX-ACCESS  read-only

	STATUS current

	DESCRIPTION "Amps Group D"

	::= { ctrlGrpAmpsEntry  8 }

	

ctrlGrpAmpsE OBJECT-TYPE

	SYNTAX  Unsigned32

	MAX-ACCESS  read-only

	STATUS current

	DESCRIPTION "Amps Group E"

	::= { ctrlGrpAmpsEntry  9 }

	

ctrlGrpAmpsF OBJECT-TYPE

	SYNTAX  Unsigned32

	MAX-ACCESS  read-only

	STATUS current

	DESCRIPTION "Amps Group F"

	::= { ctrlGrpAmpsEntry  10 }

	

ctrlOutletEntry OBJECT-TYPE

	SYNTAX  CtrlOutletEntry

	MAX-ACCESS  not-accessible

	STATUS current

	DESCRIPTION 

		"Entry in the control outlet table: each entry contains

an index (ctrlOutletIndex) and other sensor details"

	INDEX { ctrlOutletIndex }

	::= { ctrlOutletTable 1 }



CtrlOutletEntry ::= SEQUENCE {

	ctrlOutletIndex		INTEGER(1..100),

	ctrlOutletName		DisplayString,

	ctrlOutletStatus		Unsigned32,

	ctrlOutletFeedback		Unsigned32,

	ctrlOutletPending		Unsigned32,

	ctrlOutletAmps		Unsigned32,

	ctrlOutletGroup		DisplayString,

	ctrlOutletUpDelay		Unsigned32,

	ctrlOutletDwnDelay		Unsigned32,

	ctrlOutletRbtDelay		Unsigned32,

	ctrlOutletURL		DisplayString

}



ctrlOutletIndex OBJECT-TYPE

	SYNTAX  INTEGER(1..100)

	MAX-ACCESS  not-accessible

	STATUS current

	DESCRIPTION "Outlet Number"

	::= { ctrlOutletEntry  1 }

	

ctrlOutletName OBJECT-TYPE

	SYNTAX  DisplayString

	MAX-ACCESS  read-only

	STATUS current

	DESCRIPTION "Outlet Friendly Name"

	::= { ctrlOutletEntry  2 }

	

ctrlOutletStatus OBJECT-TYPE

	SYNTAX  Unsigned32

	MAX-ACCESS  read-only

	STATUS current

	DESCRIPTION "Current Outlet Status"

	::= { ctrlOutletEntry  3 }

	

ctrlOutletFeedback OBJECT-TYPE

	SYNTAX  Unsigned32

	MAX-ACCESS  read-only

	STATUS current

	DESCRIPTION "Outlet Feedback Value, should be equal to status"

	::= { ctrlOutletEntry  4 }

	

ctrlOutletPending OBJECT-TYPE

	SYNTAX  Unsigned32

	MAX-ACCESS  read-only

	STATUS current

	DESCRIPTION "Outlet Status to be set to"

	::= { ctrlOutletEntry  5 }

	

ctrlOutletAmps OBJECT-TYPE

	SYNTAX  Unsigned32

	MAX-ACCESS  read-only

	STATUS current

	DESCRIPTION "Outlet Amps readings"

	::= { ctrlOutletEntry  6 }

	

ctrlOutletGroup OBJECT-TYPE

	SYNTAX  DisplayString

	MAX-ACCESS  read-only

	STATUS current

	DESCRIPTION "Outlet Group"

	::= { ctrlOutletEntry  7 }

	

ctrlOutletUpDelay OBJECT-TYPE

	SYNTAX  Unsigned32

	MAX-ACCESS  read-only

	STATUS current

	DESCRIPTION "Outlet Power Up Delay"

	::= { ctrlOutletEntry  8 }

	

ctrlOutletDwnDelay OBJECT-TYPE

	SYNTAX  Unsigned32

	MAX-ACCESS  read-only

	STATUS current

	DESCRIPTION "Outlet Power Down Delay"

	::= { ctrlOutletEntry  9 }

	

ctrlOutletRbtDelay OBJECT-TYPE

	SYNTAX  Unsigned32

	MAX-ACCESS  read-only

	STATUS current

	DESCRIPTION "Outlet Reboot Delay"

	::= { ctrlOutletEntry  10 }

	

ctrlOutletURL OBJECT-TYPE

	SYNTAX  DisplayString

	MAX-ACCESS  read-only

	STATUS current

	DESCRIPTION "Outlet URL"

	::= { ctrlOutletEntry  11 }

	

dewPointSensorEntry OBJECT-TYPE

	SYNTAX  DewPointSensorEntry

	MAX-ACCESS  not-accessible

	STATUS current

	DESCRIPTION 

		"Entry in the dew point sensor table: each entry contains

an index (dewPointSensorIndex) and other sensor details"

	INDEX { dewPointSensorIndex }

	::= { dewPointSensorTable 1 }



DewPointSensorEntry ::= SEQUENCE {

	dewPointSensorIndex		INTEGER(1..100),

	dewPointSensorSerial		DisplayString,

	dewPointSensorName		DisplayString,

	dewPointSensorAvail		Unsigned32,

	dewPointSensorDewPointC		INTEGER(-50..100),

	dewPointSensorDewPointF		INTEGER(-58..212),

	dewPointSensorTempC		INTEGER(-50..100),

	dewPointSensorTempF		INTEGER(-58..212),

	dewPointSensorHumidity		INTEGER(0..100)

}



dewPointSensorIndex OBJECT-TYPE

	SYNTAX  INTEGER(1..100)

	MAX-ACCESS  not-accessible

	STATUS current

	DESCRIPTION "Table entry index value"

	::= { dewPointSensorEntry  1 }

	

dewPointSensorSerial OBJECT-TYPE

	SYNTAX  DisplayString

	MAX-ACCESS  read-only

	STATUS current

	DESCRIPTION "Serial Number"

	::= { dewPointSensorEntry  2 }

	

dewPointSensorName OBJECT-TYPE

	SYNTAX  DisplayString

	MAX-ACCESS  read-only

	STATUS current

	DESCRIPTION "Friendly Name"

	::= { dewPointSensorEntry  3 }

	

dewPointSensorAvail OBJECT-TYPE

	SYNTAX  Unsigned32

	MAX-ACCESS  read-only

	STATUS current

	DESCRIPTION "Is device currently plugged in?"

	::= { dewPointSensorEntry  4 }

	

dewPointSensorDewPointC OBJECT-TYPE

	SYNTAX  INTEGER(-50..100)

	MAX-ACCESS  read-only

	STATUS current

	DESCRIPTION "Dew point reading in C"

	::= { dewPointSensorEntry  5 }

	

dewPointSensorDewPointF OBJECT-TYPE

	SYNTAX  INTEGER(-58..212)

	MAX-ACCESS  read-only

	STATUS current

	DESCRIPTION "Dew point reading in F"

	::= { dewPointSensorEntry  6 }

	

dewPointSensorTempC OBJECT-TYPE

	SYNTAX  INTEGER(-50..100)

	MAX-ACCESS  read-only

	STATUS current

	DESCRIPTION "Temperature reading in C"

	::= { dewPointSensorEntry  7 }

	

dewPointSensorTempF OBJECT-TYPE

	SYNTAX  INTEGER(-58..212)

	MAX-ACCESS  read-only

	STATUS current

	DESCRIPTION "Temperature reading in F"

	::= { dewPointSensorEntry  8 }

	

dewPointSensorHumidity OBJECT-TYPE

	SYNTAX  INTEGER(0..100)

	MAX-ACCESS  read-only

	STATUS current

	DESCRIPTION "Humidity reading"

	::= { dewPointSensorEntry  9 }

	

digitalSensorEntry OBJECT-TYPE

	SYNTAX  DigitalSensorEntry

	MAX-ACCESS  not-accessible

	STATUS current

	DESCRIPTION 

		"Entry in the digital sensor table: each entry contains

an index (digitalSensorIndex) and other sensor details"

	INDEX { digitalSensorIndex }

	::= { digitalSensorTable 1 }



DigitalSensorEntry ::= SEQUENCE {

	digitalSensorIndex		INTEGER(1..100),

	digitalSensorSerial		DisplayString,

	digitalSensorName		DisplayString,

	digitalSensorAvail		Unsigned32,

	digitalSensorDigital		INTEGER(0..100)

}



digitalSensorIndex OBJECT-TYPE

	SYNTAX  INTEGER(1..100)

	MAX-ACCESS  not-accessible

	STATUS current

	DESCRIPTION "Table entry index value"

	::= { digitalSensorEntry  1 }

	

digitalSensorSerial OBJECT-TYPE

	SYNTAX  DisplayString

	MAX-ACCESS  read-only

	STATUS current

	DESCRIPTION "Serial Number"

	::= { digitalSensorEntry  2 }

	

digitalSensorName OBJECT-TYPE

	SYNTAX  DisplayString

	MAX-ACCESS  read-only

	STATUS current

	DESCRIPTION "Friendly Name"

	::= { digitalSensorEntry  3 }

	

digitalSensorAvail OBJECT-TYPE

	SYNTAX  Unsigned32

	MAX-ACCESS  read-only

	STATUS current

	DESCRIPTION "Is device currently plugged in?"

	::= { digitalSensorEntry  4 }

	

digitalSensorDigital OBJECT-TYPE

	SYNTAX  INTEGER(0..100)

	MAX-ACCESS  read-only

	STATUS current

	DESCRIPTION "Digital sensor status"

	::= { digitalSensorEntry  5 }

	

dstsEntry OBJECT-TYPE

	SYNTAX  DstsEntry

	MAX-ACCESS  not-accessible

	STATUS current

	DESCRIPTION 

		"Entry in the DSTS table: each entry contains

an index (dstsIndex) and other details"

	INDEX { dstsIndex }

	::= { dstsTable 1 }



DstsEntry ::= SEQUENCE {

	dstsIndex		INTEGER(1..1),

	dstsSerial		DisplayString,

	dstsName		DisplayString,

	dstsAvail		Unsigned32,

	dstsVoltsA		Unsigned32,

	dstsAmpsA		Unsigned32,

	dstsVoltsB		Unsigned32,

	dstsAmpsB		Unsigned32,

	dstsSourceAActive		Unsigned32,

	dstsSourceBActive		Unsigned32,

	dstsPowerStatusA		Unsigned32,

	dstsPowerStatusB		Unsigned32,

	dstsSourceATempC		INTEGER(-20..50),

	dstsSourceBTempC		INTEGER(-20..50)

}



dstsIndex OBJECT-TYPE

	SYNTAX  INTEGER(1..1)

	MAX-ACCESS  not-accessible

	STATUS current

	DESCRIPTION "Table entry index value"

	::= { dstsEntry  1 }

	

dstsSerial OBJECT-TYPE

	SYNTAX  DisplayString

	MAX-ACCESS  read-only

	STATUS current

	DESCRIPTION "Serial Number"

	::= { dstsEntry  2 }

	

dstsName OBJECT-TYPE

	SYNTAX  DisplayString

	MAX-ACCESS  read-only

	STATUS current

	DESCRIPTION "Friendly Name"

	::= { dstsEntry  3 }

	

dstsAvail OBJECT-TYPE

	SYNTAX  Unsigned32

	MAX-ACCESS  read-only

	STATUS current

	DESCRIPTION "Is device currently plugged in?"

	::= { dstsEntry  4 }

	

dstsVoltsA OBJECT-TYPE

	SYNTAX  Unsigned32

	MAX-ACCESS  read-only

	STATUS current

	DESCRIPTION "RMS Voltage of Side A"

	::= { dstsEntry  5 }

	

dstsAmpsA OBJECT-TYPE

	SYNTAX  Unsigned32

	MAX-ACCESS  read-only

	STATUS current

	DESCRIPTION "RMS Current of Side A"

	::= { dstsEntry  6 }

	

dstsVoltsB OBJECT-TYPE

	SYNTAX  Unsigned32

	MAX-ACCESS  read-only

	STATUS current

	DESCRIPTION "RMS Voltage of Side B"

	::= { dstsEntry  7 }

	

dstsAmpsB OBJECT-TYPE

	SYNTAX  Unsigned32

	MAX-ACCESS  read-only

	STATUS current

	DESCRIPTION "RMS Current of Side B"

	::= { dstsEntry  8 }

	

dstsSourceAActive OBJECT-TYPE

	SYNTAX  Unsigned32

	MAX-ACCESS  read-only

	STATUS current

	DESCRIPTION "If 99, source A active"

	::= { dstsEntry  9 }

	

dstsSourceBActive OBJECT-TYPE

	SYNTAX  Unsigned32

	MAX-ACCESS  read-only

	STATUS current

	DESCRIPTION "If 99, source B active"

	::= { dstsEntry  10 }

	

dstsPowerStatusA OBJECT-TYPE

	SYNTAX  Unsigned32

	MAX-ACCESS  read-only

	STATUS current

	DESCRIPTION "Power Quality of source A"

	::= { dstsEntry  11 }

	

dstsPowerStatusB OBJECT-TYPE

	SYNTAX  Unsigned32

	MAX-ACCESS  read-only

	STATUS current

	DESCRIPTION "Power Quality of Source B"

	::= { dstsEntry  12 }

	

dstsSourceATempC OBJECT-TYPE

	SYNTAX  INTEGER(-20..50)

	MAX-ACCESS  read-only

	STATUS current

	DESCRIPTION "Current reading for Source A temp in C"

	::= { dstsEntry  13 }

	

dstsSourceBTempC OBJECT-TYPE

	SYNTAX  INTEGER(-20..50)

	MAX-ACCESS  read-only

	STATUS current

	DESCRIPTION "Current reading for Source B temp in C"

	::= { dstsEntry  14 }

	

cpmSensorEntry OBJECT-TYPE

	SYNTAX  CpmSensorEntry

	MAX-ACCESS  not-accessible

	STATUS current

	DESCRIPTION 

		"Entry in the city power sensor table: each entry contains

an index (cpmSensorIndex) and other sensor details"

	INDEX { cpmSensorIndex }

	::= { cpmSensorTable 1 }



CpmSensorEntry ::= SEQUENCE {

	cpmSensorIndex		INTEGER(1..100),

	cpmSensorSerial		DisplayString,

	cpmSensorName		DisplayString,

	cpmSensorAvail		Unsigned32,

	cpmSensorStatus		INTEGER(0..100)

}



cpmSensorIndex OBJECT-TYPE

	SYNTAX  INTEGER(1..100)

	MAX-ACCESS  not-accessible

	STATUS current

	DESCRIPTION "Table entry index value"

	::= { cpmSensorEntry  1 }

	

cpmSensorSerial OBJECT-TYPE

	SYNTAX  DisplayString

	MAX-ACCESS  read-only

	STATUS current

	DESCRIPTION "Serial Number"

	::= { cpmSensorEntry  2 }

	

cpmSensorName OBJECT-TYPE

	SYNTAX  DisplayString

	MAX-ACCESS  read-only

	STATUS current

	DESCRIPTION "Friendly Name"

	::= { cpmSensorEntry  3 }

	

cpmSensorAvail OBJECT-TYPE

	SYNTAX  Unsigned32

	MAX-ACCESS  read-only

	STATUS current

	DESCRIPTION "Is device currently plugged in?"

	::= { cpmSensorEntry  4 }

	

cpmSensorStatus OBJECT-TYPE

	SYNTAX  INTEGER(0..100)

	MAX-ACCESS  read-only

	STATUS current

	DESCRIPTION "City Power sensor status"

	::= { cpmSensorEntry  5 }

	

smokeAlarmEntry OBJECT-TYPE

	SYNTAX  SmokeAlarmEntry

	MAX-ACCESS  not-accessible

	STATUS current

	DESCRIPTION 

		"Entry in the smoke alarm sensor table: each entry contains

an index (smokeAlarmIndex) and other sensor details"

	INDEX { smokeAlarmIndex }

	::= { smokeAlarmTable 1 }



SmokeAlarmEntry ::= SEQUENCE {

	smokeAlarmIndex		INTEGER(1..100),

	smokeAlarmSerial		DisplayString,

	smokeAlarmName		DisplayString,

	smokeAlarmAvail		Unsigned32,

	smokeAlarmStatus		INTEGER(0..100)

}



smokeAlarmIndex OBJECT-TYPE

	SYNTAX  INTEGER(1..100)

	MAX-ACCESS  not-accessible

	STATUS current

	DESCRIPTION "Table entry index value"

	::= { smokeAlarmEntry  1 }

	

smokeAlarmSerial OBJECT-TYPE

	SYNTAX  DisplayString

	MAX-ACCESS  read-only

	STATUS current

	DESCRIPTION "Serial Number"

	::= { smokeAlarmEntry  2 }

	

smokeAlarmName OBJECT-TYPE

	SYNTAX  DisplayString

	MAX-ACCESS  read-only

	STATUS current

	DESCRIPTION "Friendly Name"

	::= { smokeAlarmEntry  3 }

	

smokeAlarmAvail OBJECT-TYPE

	SYNTAX  Unsigned32

	MAX-ACCESS  read-only

	STATUS current

	DESCRIPTION "Is device currently plugged in?"

	::= { smokeAlarmEntry  4 }

	

smokeAlarmStatus OBJECT-TYPE

	SYNTAX  INTEGER(0..100)

	MAX-ACCESS  read-only

	STATUS current

	DESCRIPTION "Smoke alarm status"

	::= { smokeAlarmEntry  5 }

	

neg48VdcSensorEntry OBJECT-TYPE

	SYNTAX  Neg48VdcSensorEntry

	MAX-ACCESS  not-accessible

	STATUS current

	DESCRIPTION 

		"Entry in the -48Vdc sensor table: each entry contains

an index (neg48VdcSensorIndex) and other sensor details"

	INDEX { neg48VdcSensorIndex }

	::= { neg48VdcSensorTable 1 }



Neg48VdcSensorEntry ::= SEQUENCE {

	neg48VdcSensorIndex		INTEGER(1..100),

	neg48VdcSensorSerial		DisplayString,

	neg48VdcSensorName		DisplayString,

	neg48VdcSensorAvail		Unsigned32,

	neg48VdcSensorVoltage		INTEGER(-100..10)

}



neg48VdcSensorIndex OBJECT-TYPE

	SYNTAX  INTEGER(1..100)

	MAX-ACCESS  not-accessible

	STATUS current

	DESCRIPTION "Table entry index value"

	::= { neg48VdcSensorEntry  1 }

	

neg48VdcSensorSerial OBJECT-TYPE

	SYNTAX  DisplayString

	MAX-ACCESS  read-only

	STATUS current

	DESCRIPTION "Serial Number"

	::= { neg48VdcSensorEntry  2 }

	

neg48VdcSensorName OBJECT-TYPE

	SYNTAX  DisplayString

	MAX-ACCESS  read-only

	STATUS current

	DESCRIPTION "Friendly Name"

	::= { neg48VdcSensorEntry  3 }

	

neg48VdcSensorAvail OBJECT-TYPE

	SYNTAX  Unsigned32

	MAX-ACCESS  read-only

	STATUS current

	DESCRIPTION "Is device currently plugged in?"

	::= { neg48VdcSensorEntry  4 }

	

neg48VdcSensorVoltage OBJECT-TYPE

	SYNTAX  INTEGER(-100..10)

	MAX-ACCESS  read-only

	STATUS current

	DESCRIPTION "-48Vdc Sensor value"

	::= { neg48VdcSensorEntry  5 }

	

pos30VdcSensorEntry OBJECT-TYPE

	SYNTAX  Pos30VdcSensorEntry

	MAX-ACCESS  not-accessible

	STATUS current

	DESCRIPTION 

		"Entry in the 30Vdc sensor table: each entry contains

an index (pos30VdcSensorIndex) and other sensor details"

	INDEX { pos30VdcSensorIndex }

	::= { pos30VdcSensorTable 1 }



Pos30VdcSensorEntry ::= SEQUENCE {

	pos30VdcSensorIndex		INTEGER(1..100),

	pos30VdcSensorSerial		DisplayString,

	pos30VdcSensorName		DisplayString,

	pos30VdcSensorAvail		Unsigned32,

	pos30VdcSensorVoltage		INTEGER(-10..100)

}



pos30VdcSensorIndex OBJECT-TYPE

	SYNTAX  INTEGER(1..100)

	MAX-ACCESS  not-accessible

	STATUS current

	DESCRIPTION "Table entry index value"

	::= { pos30VdcSensorEntry  1 }

	

pos30VdcSensorSerial OBJECT-TYPE

	SYNTAX  DisplayString

	MAX-ACCESS  read-only

	STATUS current

	DESCRIPTION "Serial Number"

	::= { pos30VdcSensorEntry  2 }

	

pos30VdcSensorName OBJECT-TYPE

	SYNTAX  DisplayString

	MAX-ACCESS  read-only

	STATUS current

	DESCRIPTION "Friendly Name"

	::= { pos30VdcSensorEntry  3 }

	

pos30VdcSensorAvail OBJECT-TYPE

	SYNTAX  Unsigned32

	MAX-ACCESS  read-only

	STATUS current

	DESCRIPTION "Is device currently plugged in?"

	::= { pos30VdcSensorEntry  4 }

	

pos30VdcSensorVoltage OBJECT-TYPE

	SYNTAX  INTEGER(-10..100)

	MAX-ACCESS  read-only

	STATUS current

	DESCRIPTION "30Vdc Sensor value"

	::= { pos30VdcSensorEntry  5 }

	

fancontrolEntry OBJECT-TYPE

	SYNTAX  FancontrolEntry

	MAX-ACCESS  not-accessible

	STATUS current

	DESCRIPTION 

		"Entry in the ODS EC table: each entry contains

an index (fancontroller) and other details"

	INDEX { fancontrolIndex }

	::= { fancontrolTable 1 }



FancontrolEntry ::= SEQUENCE {

	fancontrolIndex		INTEGER(1..1),

	fancontrolSerial		DisplayString,

	fancontrolName		DisplayString,

	fancontrolAvail		Unsigned32,

	fancontrolTempCreturnA		INTEGER(-40..100),

	fancontrolTempFreturnA		INTEGER(-40..212),

	fancontrolTempCreturnB		INTEGER(-40..100),

	fancontrolTempFreturnB		INTEGER(-40..212),

	fancontrolRpmFanA		Unsigned32,

	fancontrolRpmFanB		Unsigned32,

	fancontrolCapacityA		INTEGER(0..100),

	fancontrolCapacityB		INTEGER(0..100),

	fancontrolPressErr		INTEGER(0..100),

	fancontrolPressDiff		Unsigned32,

	fancontrolSetPoint		Unsigned32,

	fancontrolCFM		Unsigned32,

	fancontrolTempCreturn		INTEGER(-40..100),

	fancontrolTempFreturn		INTEGER(-40..212),

	fancontrolCapacity		INTEGER(0..100),

	fancontrolFanMissing		Unsigned32,

	fancontrolFanRegulate		Unsigned32,

	fancontrolFanComm		Unsigned32,

	fancontrolTempBus1		Unsigned32,

	fancontrolPowerFeed		Unsigned32,

	fancontrolFanTypeMismatch		Unsigned32,

	fancontrolBadPressureSensor		Unsigned32,

	fancontrolFanEndofLife		Unsigned32,

	fancontrolRackDoorOpen		Unsigned32

}



fancontrolIndex OBJECT-TYPE

	SYNTAX  INTEGER(1..1)

	MAX-ACCESS  not-accessible

	STATUS current

	DESCRIPTION "Table entry index value"

	::= { fancontrolEntry  1 }

	

fancontrolSerial OBJECT-TYPE

	SYNTAX  DisplayString

	MAX-ACCESS  read-only

	STATUS current

	DESCRIPTION "Serial Number"

	::= { fancontrolEntry  2 }

	

fancontrolName OBJECT-TYPE

	SYNTAX  DisplayString

	MAX-ACCESS  read-only

	STATUS current

	DESCRIPTION "Friendly Name"

	::= { fancontrolEntry  3 }

	

fancontrolAvail OBJECT-TYPE

	SYNTAX  Unsigned32

	MAX-ACCESS  read-only

	STATUS current

	DESCRIPTION "Is device currently plugged in?"

	::= { fancontrolEntry  4 }

	

fancontrolTempCreturnA OBJECT-TYPE

	SYNTAX  INTEGER(-40..100)

	MAX-ACCESS  read-only

	STATUS current

	DESCRIPTION "Celsius temperature of return air on fan A"

	::= { fancontrolEntry  5 }

	

fancontrolTempFreturnA OBJECT-TYPE

	SYNTAX  INTEGER(-40..212)

	MAX-ACCESS  read-only

	STATUS current

	DESCRIPTION "Fahrenheit temperature of return air on fan A"

	::= { fancontrolEntry  6 }

	

fancontrolTempCreturnB OBJECT-TYPE

	SYNTAX  INTEGER(-40..100)

	MAX-ACCESS  read-only

	STATUS current

	DESCRIPTION "Celsius temperature of return air on fan B"

	::= { fancontrolEntry  7 }

	

fancontrolTempFreturnB OBJECT-TYPE

	SYNTAX  INTEGER(-40..212)

	MAX-ACCESS  read-only

	STATUS current

	DESCRIPTION "Fahrenheit temperature of return air on fan B"

	::= { fancontrolEntry  8 }

	

fancontrolRpmFanA OBJECT-TYPE

	SYNTAX  Unsigned32

	MAX-ACCESS  read-only

	STATUS current

	DESCRIPTION "RPM of fan A"

	::= { fancontrolEntry  9 }

	

fancontrolRpmFanB OBJECT-TYPE

	SYNTAX  Unsigned32

	MAX-ACCESS  read-only

	STATUS current

	DESCRIPTION "RPM of fan B"

	::= { fancontrolEntry  10 }

	

fancontrolCapacityA OBJECT-TYPE

	SYNTAX  INTEGER(0..100)

	MAX-ACCESS  read-only

	STATUS current

	DESCRIPTION "Capacity of fan A"

	::= { fancontrolEntry  11 }

	

fancontrolCapacityB OBJECT-TYPE

	SYNTAX  INTEGER(0..100)

	MAX-ACCESS  read-only

	STATUS current

	DESCRIPTION "Capacity of fan B"

	::= { fancontrolEntry  12 }

	

fancontrolPressErr OBJECT-TYPE

	SYNTAX  INTEGER(0..100)

	MAX-ACCESS  read-only

	STATUS current

	DESCRIPTION "Pressure error"

	::= { fancontrolEntry  13 }

	

fancontrolPressDiff OBJECT-TYPE

	SYNTAX  Unsigned32

	MAX-ACCESS  read-only

	STATUS current

	DESCRIPTION "Pressure Difference"

	::= { fancontrolEntry  14 }

	

fancontrolSetPoint OBJECT-TYPE

	SYNTAX  Unsigned32

	MAX-ACCESS  read-only

	STATUS current

	DESCRIPTION "Pressure Set Point"

	::= { fancontrolEntry  15 }

	

fancontrolCFM OBJECT-TYPE

	SYNTAX  Unsigned32

	MAX-ACCESS  read-only

	STATUS current

	DESCRIPTION "Cubic Feet per minute of system air"

	::= { fancontrolEntry  16 }

	

fancontrolTempCreturn OBJECT-TYPE

	SYNTAX  INTEGER(-40..100)

	MAX-ACCESS  read-only

	STATUS current

	DESCRIPTION "Higher temp of fan A or B"

	::= { fancontrolEntry  17 }

	

fancontrolTempFreturn OBJECT-TYPE

	SYNTAX  INTEGER(-40..212)

	MAX-ACCESS  read-only

	STATUS current

	DESCRIPTION "Higher temp of fan A or B"

	::= { fancontrolEntry  18 }

	

fancontrolCapacity OBJECT-TYPE

	SYNTAX  INTEGER(0..100)

	MAX-ACCESS  read-only

	STATUS current

	DESCRIPTION "Total Capacity"

	::= { fancontrolEntry  19 }

	

fancontrolFanMissing OBJECT-TYPE

	SYNTAX  Unsigned32

	MAX-ACCESS  read-only

	STATUS current

	DESCRIPTION "Fan Unit Error"

	::= { fancontrolEntry  20 }

	

fancontrolFanRegulate OBJECT-TYPE

	SYNTAX  Unsigned32

	MAX-ACCESS  read-only

	STATUS current

	DESCRIPTION "Fan Regulation Error"

	::= { fancontrolEntry  21 }

	

fancontrolFanComm OBJECT-TYPE

	SYNTAX  Unsigned32

	MAX-ACCESS  read-only

	STATUS current

	DESCRIPTION "Fan Communications Error"

	::= { fancontrolEntry  22 }

	

fancontrolTempBus1 OBJECT-TYPE

	SYNTAX  Unsigned32

	MAX-ACCESS  read-only

	STATUS current

	DESCRIPTION "Disconnected External Sensor"

	::= { fancontrolEntry  23 }

	

fancontrolPowerFeed OBJECT-TYPE

	SYNTAX  Unsigned32

	MAX-ACCESS  read-only

	STATUS current

	DESCRIPTION "A/B Feed Error"

	::= { fancontrolEntry  24 }

	

fancontrolFanTypeMismatch OBJECT-TYPE

	SYNTAX  Unsigned32

	MAX-ACCESS  read-only

	STATUS current

	DESCRIPTION "Fan Types Not Compatible"

	::= { fancontrolEntry  25 }

	

fancontrolBadPressureSensor OBJECT-TYPE

	SYNTAX  Unsigned32

	MAX-ACCESS  read-only

	STATUS current

	DESCRIPTION "Bad Pressure Sensor"

	::= { fancontrolEntry  26 }

	

fancontrolFanEndofLife OBJECT-TYPE

	SYNTAX  Unsigned32

	MAX-ACCESS  read-only

	STATUS current

	DESCRIPTION "Fan End of Life"

	::= { fancontrolEntry  27 }

	

fancontrolRackDoorOpen OBJECT-TYPE

	SYNTAX  Unsigned32

	MAX-ACCESS  read-only

	STATUS current

	DESCRIPTION "Rack Door Open"

	::= { fancontrolEntry  28 }

	

odsTestTRAP TRAP-TYPE

	ENTERPRISE opengate

	DESCRIPTION "Test SNMP Trap"

	::= 10101

	

odsClimateTempCTRAP TRAP-TYPE

ENTERPRISE opengate

VARIABLES { climateTempC, climateName, productFriendlyName, alarmTripType }

DESCRIPTION "Climate Temperature Sensor Trap"

::= 10205



odsClimateTempFTRAP TRAP-TYPE

ENTERPRISE opengate

VARIABLES { climateTempF, climateName, productFriendlyName, alarmTripType }

DESCRIPTION "Climate Temperature Sensor Trap"

::= 10206



odsClimateHumidityTRAP TRAP-TYPE

ENTERPRISE opengate

VARIABLES { climateHumidity, climateName, productFriendlyName, alarmTripType }

DESCRIPTION "Climate Humidity Sensor Trap"

::= 10207



odsClimateLightTRAP TRAP-TYPE

ENTERPRISE opengate

VARIABLES { climateLight, climateName, productFriendlyName, alarmTripType }

DESCRIPTION "Climate Light Sensor Trap"

::= 10208



odsClimateAirflowTRAP TRAP-TYPE

ENTERPRISE opengate

VARIABLES { climateAirflow, climateName, productFriendlyName, alarmTripType }

DESCRIPTION "Climate Air Flow Sensor Trap"

::= 10209



odsClimateSoundTRAP TRAP-TYPE

ENTERPRISE opengate

VARIABLES { climateSound, climateName, productFriendlyName, alarmTripType }

DESCRIPTION "Climate Sound Sensor Trap"

::= 10210



odsClimateIO1TRAP TRAP-TYPE

ENTERPRISE opengate

VARIABLES { climateIO1, climateName, productFriendlyName, alarmTripType }

DESCRIPTION "Climate IO1 Sensor Trap"

::= 10211



odsClimateIO2TRAP TRAP-TYPE

ENTERPRISE opengate

VARIABLES { climateIO2, climateName, productFriendlyName, alarmTripType }

DESCRIPTION "Climate IO2 Sensor Trap"

::= 10212



odsClimateIO3TRAP TRAP-TYPE

ENTERPRISE opengate

VARIABLES { climateIO3, climateName, productFriendlyName, alarmTripType }

DESCRIPTION "Climate IO3 Sensor Trap"

::= 10213



odsPowMonKWattHrsTRAP TRAP-TYPE

ENTERPRISE opengate

VARIABLES { powMonKWattHrs, powMonName, productFriendlyName, alarmTripType }

DESCRIPTION "Kilo Watt Hours Trap"

::= 10305



odsPowMonVoltsTRAP TRAP-TYPE

ENTERPRISE opengate

VARIABLES { powMonVolts, powMonName, productFriendlyName, alarmTripType }

DESCRIPTION "Volts Trap"

::= 10306



odsPowMonVoltMaxTRAP TRAP-TYPE

ENTERPRISE opengate

VARIABLES { powMonVoltMax, powMonName, productFriendlyName, alarmTripType }

DESCRIPTION "Volts Max Trap"

::= 10307



odsPowMonVoltMinTRAP TRAP-TYPE

ENTERPRISE opengate

VARIABLES { powMonVoltMin, powMonName, productFriendlyName, alarmTripType }

DESCRIPTION "Volts Min Trap"

::= 10308



odsPowMonVoltPkTRAP TRAP-TYPE

ENTERPRISE opengate

VARIABLES { powMonVoltPk, powMonName, productFriendlyName, alarmTripType }

DESCRIPTION "Volt Peak Trap"

::= 10309



odsPowMonAmpsX10TRAP TRAP-TYPE

ENTERPRISE opengate

VARIABLES { powMonAmpsX10, powMonName, productFriendlyName, alarmTripType }

DESCRIPTION "Amps x 10 Trap"

::= 10310



odsPowMonRealPowTRAP TRAP-TYPE

ENTERPRISE opengate

VARIABLES { powMonRealPow, powMonName, productFriendlyName, alarmTripType }

DESCRIPTION "Real Power Trap"

::= 10311



odsPowMonAppPowTRAP TRAP-TYPE

ENTERPRISE opengate

VARIABLES { powMonAppPow, powMonName, productFriendlyName, alarmTripType }

DESCRIPTION "Apparent Power Trap"

::= 10312



odsPowMonPwrFactTRAP TRAP-TYPE

ENTERPRISE opengate

VARIABLES { powMonPwrFact, powMonName, productFriendlyName, alarmTripType }

DESCRIPTION "Power Factor Trap"

::= 10313



odsPowMonOutlet1TRAP TRAP-TYPE

ENTERPRISE opengate

VARIABLES { powMonOutlet1, powMonName, productFriendlyName, alarmTripType }

DESCRIPTION "Outlet 1 Trap"

::= 10314



odsPowMonOutlet2TRAP TRAP-TYPE

ENTERPRISE opengate

VARIABLES { powMonOutlet2, powMonName, productFriendlyName, alarmTripType }

DESCRIPTION "Outlet 2 Trap"

::= 10315



odsTempSensorTempCTRAP TRAP-TYPE

ENTERPRISE opengate

VARIABLES { tempSensorTempC, tempSensorName, productFriendlyName, alarmTripType }

DESCRIPTION "Remote Temp Sensor - Temperature Trap"

::= 10405



odsTempSensorTempFTRAP TRAP-TYPE

ENTERPRISE opengate

VARIABLES { tempSensorTempF, tempSensorName, productFriendlyName, alarmTripType }

DESCRIPTION "Remote Temp Sensor - Temperature Trap"

::= 10406



odsAirFlowSensorFlowTRAP TRAP-TYPE

ENTERPRISE opengate

VARIABLES { airFlowSensorFlow, airFlowSensorName, productFriendlyName, alarmTripType }

DESCRIPTION "Remote Air Flow Sensor - Air Flow Trap"

::= 10505



odsAirFlowSensorTempCTRAP TRAP-TYPE

ENTERPRISE opengate

VARIABLES { airFlowSensorTempC, airFlowSensorName, productFriendlyName, alarmTripType }

DESCRIPTION "Remote Air Flow Sensor - Temperature Trap"

::= 10506



odsAirFlowSensorTempFTRAP TRAP-TYPE

ENTERPRISE opengate

VARIABLES { airFlowSensorTempF, airFlowSensorName, productFriendlyName, alarmTripType }

DESCRIPTION "Remote Air Flow Sensor - Temperature Trap"

::= 10507



odsAirFlowSensorHumidityTRAP TRAP-TYPE

ENTERPRISE opengate

VARIABLES { airFlowSensorHumidity, airFlowSensorName, productFriendlyName, alarmTripType }

DESCRIPTION "Remote Air Flow Sensor - Humidity"

::= 10508



odsPowerVoltsTRAP TRAP-TYPE

ENTERPRISE opengate

VARIABLES { powerVolts, powerName, productFriendlyName, alarmTripType }

DESCRIPTION "Power-Only Volts Trap"

::= 10605



odsPowerAmpsTRAP TRAP-TYPE

ENTERPRISE opengate

VARIABLES { powerAmps, powerName, productFriendlyName, alarmTripType }

DESCRIPTION "Power-Only Amps Trap"

::= 10606



odsPowerRealPowTRAP TRAP-TYPE

ENTERPRISE opengate

VARIABLES { powerRealPow, powerName, productFriendlyName, alarmTripType }

DESCRIPTION "Power-Only Watts Trap"

::= 10607



odsPowerAppPowTRAP TRAP-TYPE

ENTERPRISE opengate

VARIABLES { powerAppPow, powerName, productFriendlyName, alarmTripType }

DESCRIPTION "Power-Only Volt Amps Trap"

::= 10608



odsPowerPwrFactorTRAP TRAP-TYPE

ENTERPRISE opengate

VARIABLES { powerPwrFactor, powerName, productFriendlyName, alarmTripType }

DESCRIPTION "Power-Only Power Factor Trap"

::= 10609



odsDoorSensorStatusTRAP TRAP-TYPE

ENTERPRISE opengate

VARIABLES { doorSensorStatus, doorSensorName, productFriendlyName, alarmTripType }

DESCRIPTION "Door sensor Trap"

::= 10705



odsWaterSensorDampnessTRAP TRAP-TYPE

ENTERPRISE opengate

VARIABLES { waterSensorDampness, waterSensorName, productFriendlyName, alarmTripType }

DESCRIPTION "Water sensor Trap"

::= 10805



odsCurrentMonitorAmpsTRAP TRAP-TYPE

ENTERPRISE opengate

VARIABLES { currentMonitorAmps, currentMonitorName, productFriendlyName, alarmTripType }

DESCRIPTION "Current Monitor Amps Trap"

::= 10905



odsMillivoltMonitorMVTRAP TRAP-TYPE

ENTERPRISE opengate

VARIABLES { millivoltMonitorMV, millivoltMonitorName, productFriendlyName, alarmTripType }

DESCRIPTION "Millivolt Monitor Trap"

::= 11005



odsPow3ChKWattHrsATRAP TRAP-TYPE

ENTERPRISE opengate

VARIABLES { pow3ChKWattHrsA, pow3ChName, productFriendlyName, alarmTripType }

DESCRIPTION "Kilo Watt Hours A Trap"

::= 11105



odsPow3ChVoltsATRAP TRAP-TYPE

ENTERPRISE opengate

VARIABLES { pow3ChVoltsA, pow3ChName, productFriendlyName, alarmTripType }

DESCRIPTION "Volts A Trap"

::= 11106



odsPow3ChVoltMaxATRAP TRAP-TYPE

ENTERPRISE opengate

VARIABLES { pow3ChVoltMaxA, pow3ChName, productFriendlyName, alarmTripType }

DESCRIPTION "Volts Max A Trap"

::= 11107



odsPow3ChVoltMinATRAP TRAP-TYPE

ENTERPRISE opengate

VARIABLES { pow3ChVoltMinA, pow3ChName, productFriendlyName, alarmTripType }

DESCRIPTION "Volts Min A Trap"

::= 11108



odsPow3ChVoltPkATRAP TRAP-TYPE

ENTERPRISE opengate

VARIABLES { pow3ChVoltPkA, pow3ChName, productFriendlyName, alarmTripType }

DESCRIPTION "Volt Peak A Trap"

::= 11109



odsPow3ChAmpsX10ATRAP TRAP-TYPE

ENTERPRISE opengate

VARIABLES { pow3ChAmpsX10A, pow3ChName, productFriendlyName, alarmTripType }

DESCRIPTION "Amps x 10 A Trap"

::= 11110



odsPow3ChRealPowATRAP TRAP-TYPE

ENTERPRISE opengate

VARIABLES { pow3ChRealPowA, pow3ChName, productFriendlyName, alarmTripType }

DESCRIPTION "Real Power A Trap"

::= 11111



odsPow3ChAppPowATRAP TRAP-TYPE

ENTERPRISE opengate

VARIABLES { pow3ChAppPowA, pow3ChName, productFriendlyName, alarmTripType }

DESCRIPTION "Apparent Power A Trap"

::= 11112



odsPow3ChPwrFactATRAP TRAP-TYPE

ENTERPRISE opengate

VARIABLES { pow3ChPwrFactA, pow3ChName, productFriendlyName, alarmTripType }

DESCRIPTION "Power Factor A Trap"

::= 11113



odsPow3ChKWattHrsBTRAP TRAP-TYPE

ENTERPRISE opengate

VARIABLES { pow3ChKWattHrsB, pow3ChName, productFriendlyName, alarmTripType }

DESCRIPTION "Kilo Watt Hours B Trap"

::= 11114



odsPow3ChVoltsBTRAP TRAP-TYPE

ENTERPRISE opengate

VARIABLES { pow3ChVoltsB, pow3ChName, productFriendlyName, alarmTripType }

DESCRIPTION "Volts B Trap"

::= 11115



odsPow3ChVoltMaxBTRAP TRAP-TYPE

ENTERPRISE opengate

VARIABLES { pow3ChVoltMaxB, pow3ChName, productFriendlyName, alarmTripType }

DESCRIPTION "Volts Max B Trap"

::= 11116



odsPow3ChVoltMinBTRAP TRAP-TYPE

ENTERPRISE opengate

VARIABLES { pow3ChVoltMinB, pow3ChName, productFriendlyName, alarmTripType }

DESCRIPTION "Volts Min B Trap"

::= 11117



odsPow3ChVoltPkBTRAP TRAP-TYPE

ENTERPRISE opengate

VARIABLES { pow3ChVoltPkB, pow3ChName, productFriendlyName, alarmTripType }

DESCRIPTION "Volt Peak B Trap"

::= 11118



odsPow3ChAmpsX10BTRAP TRAP-TYPE

ENTERPRISE opengate

VARIABLES { pow3ChAmpsX10B, pow3ChName, productFriendlyName, alarmTripType }

DESCRIPTION "Amps x 10 B Trap"

::= 11119



odsPow3ChRealPowBTRAP TRAP-TYPE

ENTERPRISE opengate

VARIABLES { pow3ChRealPowB, pow3ChName, productFriendlyName, alarmTripType }

DESCRIPTION "Real Power B Trap"

::= 11120



odsPow3ChAppPowBTRAP TRAP-TYPE

ENTERPRISE opengate

VARIABLES { pow3ChAppPowB, pow3ChName, productFriendlyName, alarmTripType }

DESCRIPTION "Apparent Power B Trap"

::= 11121



odsPow3ChPwrFactBTRAP TRAP-TYPE

ENTERPRISE opengate

VARIABLES { pow3ChPwrFactB, pow3ChName, productFriendlyName, alarmTripType }

DESCRIPTION "Power Factor B Trap"

::= 11122



odsPow3ChKWattHrsCTRAP TRAP-TYPE

ENTERPRISE opengate

VARIABLES { pow3ChKWattHrsC, pow3ChName, productFriendlyName, alarmTripType }

DESCRIPTION "Kilo Watt Hours C Trap"

::= 11123



odsPow3ChVoltsCTRAP TRAP-TYPE

ENTERPRISE opengate

VARIABLES { pow3ChVoltsC, pow3ChName, productFriendlyName, alarmTripType }

DESCRIPTION "Volts C Trap"

::= 11124



odsPow3ChVoltMaxCTRAP TRAP-TYPE

ENTERPRISE opengate

VARIABLES { pow3ChVoltMaxC, pow3ChName, productFriendlyName, alarmTripType }

DESCRIPTION "Volts Max C Trap"

::= 11125



odsPow3ChVoltMinCTRAP TRAP-TYPE

ENTERPRISE opengate

VARIABLES { pow3ChVoltMinC, pow3ChName, productFriendlyName, alarmTripType }

DESCRIPTION "Volts Min C Trap"

::= 11126



odsPow3ChVoltPkCTRAP TRAP-TYPE

ENTERPRISE opengate

VARIABLES { pow3ChVoltPkC, pow3ChName, productFriendlyName, alarmTripType }

DESCRIPTION "Volt Peak C Trap"

::= 11127



odsPow3ChAmpsX10CTRAP TRAP-TYPE

ENTERPRISE opengate

VARIABLES { pow3ChAmpsX10C, pow3ChName, productFriendlyName, alarmTripType }

DESCRIPTION "Amps x 10 C Trap"

::= 11128



odsPow3ChRealPowCTRAP TRAP-TYPE

ENTERPRISE opengate

VARIABLES { pow3ChRealPowC, pow3ChName, productFriendlyName, alarmTripType }

DESCRIPTION "Real Power C Trap"

::= 11129



odsPow3ChAppPowCTRAP TRAP-TYPE

ENTERPRISE opengate

VARIABLES { pow3ChAppPowC, pow3ChName, productFriendlyName, alarmTripType }

DESCRIPTION "Apparent Power C Trap"

::= 11130



odsPow3ChPwrFactCTRAP TRAP-TYPE

ENTERPRISE opengate

VARIABLES { pow3ChPwrFactC, pow3ChName, productFriendlyName, alarmTripType }

DESCRIPTION "Power Factor C Trap"

::= 11131



odsOutlet1StatusTRAP TRAP-TYPE

ENTERPRISE opengate

VARIABLES { outlet1Status, outletName, productFriendlyName, alarmTripType }

DESCRIPTION "Outlet 1 Status Trap"

::= 11205



odsOutlet2StatusTRAP TRAP-TYPE

ENTERPRISE opengate

VARIABLES { outlet2Status, outletName, productFriendlyName, alarmTripType }

DESCRIPTION "Outlet 2 Status Trap"

::= 11206



odsVsfcSetPointCTRAP TRAP-TYPE

ENTERPRISE opengate

VARIABLES { vsfcSetPointC, vsfcName, productFriendlyName, alarmTripType }

DESCRIPTION "Vsfc Temp Set Point Sensor Trap"

::= 11305



odsVsfcSetPointFTRAP TRAP-TYPE

ENTERPRISE opengate

VARIABLES { vsfcSetPointF, vsfcName, productFriendlyName, alarmTripType }

DESCRIPTION "Vsfc Temp Set Point Sensor Trap"

::= 11306



odsVsfcIntTempCTRAP TRAP-TYPE

ENTERPRISE opengate

VARIABLES { vsfcIntTempC, vsfcName, productFriendlyName, alarmTripType }

DESCRIPTION "Vsfc Internal Temp Sensor Trap"

::= 11307



odsVsfcIntTempFTRAP TRAP-TYPE

ENTERPRISE opengate

VARIABLES { vsfcIntTempF, vsfcName, productFriendlyName, alarmTripType }

DESCRIPTION "Vsfc Internal Temp Sensor Trap"

::= 11308



odsVsfcExt1TempCTRAP TRAP-TYPE

ENTERPRISE opengate

VARIABLES { vsfcExt1TempC, vsfcName, productFriendlyName, alarmTripType }

DESCRIPTION "Vsfc External Temp 1 Sensor Trap"

::= 11309



odsVsfcExt1TempFTRAP TRAP-TYPE

ENTERPRISE opengate

VARIABLES { vsfcExt1TempF, vsfcName, productFriendlyName, alarmTripType }

DESCRIPTION "Vsfc External Temp 1 Sensor Trap"

::= 11310



odsVsfcExt2TempCTRAP TRAP-TYPE

ENTERPRISE opengate

VARIABLES { vsfcExt2TempC, vsfcName, productFriendlyName, alarmTripType }

DESCRIPTION "Vsfc External Temp 2 Sensor Trap"

::= 11311



odsVsfcExt2TempFTRAP TRAP-TYPE

ENTERPRISE opengate

VARIABLES { vsfcExt2TempF, vsfcName, productFriendlyName, alarmTripType }

DESCRIPTION "Vsfc External Temp 2 Sensor Trap"

::= 11312



odsVsfcExt3TempCTRAP TRAP-TYPE

ENTERPRISE opengate

VARIABLES { vsfcExt3TempC, vsfcName, productFriendlyName, alarmTripType }

DESCRIPTION "Vsfc External Temp 3 Sensor Trap"

::= 11313



odsVsfcExt3TempFTRAP TRAP-TYPE

ENTERPRISE opengate

VARIABLES { vsfcExt3TempF, vsfcName, productFriendlyName, alarmTripType }

DESCRIPTION "Vsfc External Temp 3 Sensor Trap"

::= 11314



odsVsfcExt4TempCTRAP TRAP-TYPE

ENTERPRISE opengate

VARIABLES { vsfcExt4TempC, vsfcName, productFriendlyName, alarmTripType }

DESCRIPTION "Vsfc External Temp 4 Sensor Trap"

::= 11315



odsVsfcExt4TempFTRAP TRAP-TYPE

ENTERPRISE opengate

VARIABLES { vsfcExt4TempF, vsfcName, productFriendlyName, alarmTripType }

DESCRIPTION "Vsfc External Temp 4 Sensor Trap"

::= 11316



odsVsfcFanSpeedTRAP TRAP-TYPE

ENTERPRISE opengate

VARIABLES { vsfcFanSpeed, vsfcName, productFriendlyName, alarmTripType }

DESCRIPTION "Vsfc Fan Speed Sensor Trap"

::= 11317



odsCtrl3ChVoltsATRAP TRAP-TYPE

ENTERPRISE opengate

VARIABLES { ctrl3ChVoltsA, ctrl3ChName, productFriendlyName, alarmTripType }

DESCRIPTION "Volts A Trap"

::= 11405



odsCtrl3ChVoltPkATRAP TRAP-TYPE

ENTERPRISE opengate

VARIABLES { ctrl3ChVoltPkA, ctrl3ChName, productFriendlyName, alarmTripType }

DESCRIPTION "Volt Peak A Trap"

::= 11406



odsCtrl3ChAmpsATRAP TRAP-TYPE

ENTERPRISE opengate

VARIABLES { ctrl3ChAmpsA, ctrl3ChName, productFriendlyName, alarmTripType }

DESCRIPTION "Amps A Trap"

::= 11407



odsCtrl3ChAmpPkATRAP TRAP-TYPE

ENTERPRISE opengate

VARIABLES { ctrl3ChAmpPkA, ctrl3ChName, productFriendlyName, alarmTripType }

DESCRIPTION "Amps Peak A Trap"

::= 11408



odsCtrl3ChRealPowATRAP TRAP-TYPE

ENTERPRISE opengate

VARIABLES { ctrl3ChRealPowA, ctrl3ChName, productFriendlyName, alarmTripType }

DESCRIPTION "Real Power A Trap"

::= 11409



odsCtrl3ChAppPowATRAP TRAP-TYPE

ENTERPRISE opengate

VARIABLES { ctrl3ChAppPowA, ctrl3ChName, productFriendlyName, alarmTripType }

DESCRIPTION "Apparent Power A Trap"

::= 11410



odsCtrl3ChPwrFactATRAP TRAP-TYPE

ENTERPRISE opengate

VARIABLES { ctrl3ChPwrFactA, ctrl3ChName, productFriendlyName, alarmTripType }

DESCRIPTION "Power Factor A Trap"

::= 11411



odsCtrl3ChVoltsBTRAP TRAP-TYPE

ENTERPRISE opengate

VARIABLES { ctrl3ChVoltsB, ctrl3ChName, productFriendlyName, alarmTripType }

DESCRIPTION "Volts B Trap"

::= 11412



odsCtrl3ChVoltPkBTRAP TRAP-TYPE

ENTERPRISE opengate

VARIABLES { ctrl3ChVoltPkB, ctrl3ChName, productFriendlyName, alarmTripType }

DESCRIPTION "Volt Peak B Trap"

::= 11413



odsCtrl3ChAmpsBTRAP TRAP-TYPE

ENTERPRISE opengate

VARIABLES { ctrl3ChAmpsB, ctrl3ChName, productFriendlyName, alarmTripType }

DESCRIPTION "Amps B Trap"

::= 11414



odsCtrl3ChAmpPkBTRAP TRAP-TYPE

ENTERPRISE opengate

VARIABLES { ctrl3ChAmpPkB, ctrl3ChName, productFriendlyName, alarmTripType }

DESCRIPTION "Amps Peak B Trap"

::= 11415



odsCtrl3ChRealPowBTRAP TRAP-TYPE

ENTERPRISE opengate

VARIABLES { ctrl3ChRealPowB, ctrl3ChName, productFriendlyName, alarmTripType }

DESCRIPTION "Real Power B Trap"

::= 11416



odsCtrl3ChAppPowBTRAP TRAP-TYPE

ENTERPRISE opengate

VARIABLES { ctrl3ChAppPowB, ctrl3ChName, productFriendlyName, alarmTripType }

DESCRIPTION "Apparent Power B Trap"

::= 11417



odsCtrl3ChPwrFactBTRAP TRAP-TYPE

ENTERPRISE opengate

VARIABLES { ctrl3ChPwrFactB, ctrl3ChName, productFriendlyName, alarmTripType }

DESCRIPTION "Power Factor B Trap"

::= 11418



odsCtrl3ChVoltsCTRAP TRAP-TYPE

ENTERPRISE opengate

VARIABLES { ctrl3ChVoltsC, ctrl3ChName, productFriendlyName, alarmTripType }

DESCRIPTION "Volts C Trap"

::= 11419



odsCtrl3ChVoltPkCTRAP TRAP-TYPE

ENTERPRISE opengate

VARIABLES { ctrl3ChVoltPkC, ctrl3ChName, productFriendlyName, alarmTripType }

DESCRIPTION "Volt Peak C Trap"

::= 11420



odsCtrl3ChAmpsCTRAP TRAP-TYPE

ENTERPRISE opengate

VARIABLES { ctrl3ChAmpsC, ctrl3ChName, productFriendlyName, alarmTripType }

DESCRIPTION "Amps C Trap"

::= 11421



odsCtrl3ChAmpPkCTRAP TRAP-TYPE

ENTERPRISE opengate

VARIABLES { ctrl3ChAmpPkC, ctrl3ChName, productFriendlyName, alarmTripType }

DESCRIPTION "Amps Peak C Trap"

::= 11422



odsCtrl3ChRealPowCTRAP TRAP-TYPE

ENTERPRISE opengate

VARIABLES { ctrl3ChRealPowC, ctrl3ChName, productFriendlyName, alarmTripType }

DESCRIPTION "Real Power C Trap"

::= 11423



odsCtrl3ChAppPowCTRAP TRAP-TYPE

ENTERPRISE opengate

VARIABLES { ctrl3ChAppPowC, ctrl3ChName, productFriendlyName, alarmTripType }

DESCRIPTION "Apparent Power C Trap"

::= 11424



odsCtrl3ChPwrFactCTRAP TRAP-TYPE

ENTERPRISE opengate

VARIABLES { ctrl3ChPwrFactC, ctrl3ChName, productFriendlyName, alarmTripType }

DESCRIPTION "Power Factor C Trap"

::= 11425



odsCtrlGrpAmpsATRAP TRAP-TYPE

ENTERPRISE opengate

VARIABLES { ctrlGrpAmpsA, ctrlGrpAmpsName, productFriendlyName, alarmTripType }

DESCRIPTION "Group A Amps Trap"

::= 11505



odsCtrlGrpAmpsBTRAP TRAP-TYPE

ENTERPRISE opengate

VARIABLES { ctrlGrpAmpsB, ctrlGrpAmpsName, productFriendlyName, alarmTripType }

DESCRIPTION "Group B Amps Trap"

::= 11506



odsCtrlGrpAmpsCTRAP TRAP-TYPE

ENTERPRISE opengate

VARIABLES { ctrlGrpAmpsC, ctrlGrpAmpsName, productFriendlyName, alarmTripType }

DESCRIPTION "Group C Amps Trap"

::= 11507



odsCtrlGrpAmpsDTRAP TRAP-TYPE

ENTERPRISE opengate

VARIABLES { ctrlGrpAmpsD, ctrlGrpAmpsName, productFriendlyName, alarmTripType }

DESCRIPTION "Group D Amps Trap"

::= 11508



odsCtrlGrpAmpsETRAP TRAP-TYPE

ENTERPRISE opengate

VARIABLES { ctrlGrpAmpsE, ctrlGrpAmpsName, productFriendlyName, alarmTripType }

DESCRIPTION "Group E Amps Trap"

::= 11509



odsCtrlGrpAmpsFTRAP TRAP-TYPE

ENTERPRISE opengate

VARIABLES { ctrlGrpAmpsF, ctrlGrpAmpsName, productFriendlyName, alarmTripType }

DESCRIPTION "Group F Amps Trap"

::= 11510



odsDewPointSensorDewPointCTRAP TRAP-TYPE

ENTERPRISE opengate

VARIABLES { dewPointSensorDewPointC, dewPointSensorName, productFriendlyName, alarmTripType }

DESCRIPTION "Remote Dew Point Sensor - Dew Point Trap"

::= 11705



odsDewPointSensorDewPointFTRAP TRAP-TYPE

ENTERPRISE opengate

VARIABLES { dewPointSensorDewPointF, dewPointSensorName, productFriendlyName, alarmTripType }

DESCRIPTION "Remote Dew Point Sensor - Dew Point Trap"

::= 11706



odsDewPointSensorTempCTRAP TRAP-TYPE

ENTERPRISE opengate

VARIABLES { dewPointSensorTempC, dewPointSensorName, productFriendlyName, alarmTripType }

DESCRIPTION "Remote Dew Point Sensor - Temperature Trap"

::= 11707



odsDewPointSensorTempFTRAP TRAP-TYPE

ENTERPRISE opengate

VARIABLES { dewPointSensorTempF, dewPointSensorName, productFriendlyName, alarmTripType }

DESCRIPTION "Remote Dew Point Sensor - Temperature Trap"

::= 11708



odsDewPointSensorHumidityTRAP TRAP-TYPE

ENTERPRISE opengate

VARIABLES { dewPointSensorHumidity, dewPointSensorName, productFriendlyName, alarmTripType }

DESCRIPTION "Remote Dew Point Sensor - Humidity"

::= 11709



odsDigitalSensorDigitalTRAP TRAP-TYPE

ENTERPRISE opengate

VARIABLES { digitalSensorDigital, digitalSensorName, productFriendlyName, alarmTripType }

DESCRIPTION "Digital sensor Trap"

::= 11805



odsDstsVoltsATRAP TRAP-TYPE

ENTERPRISE opengate

VARIABLES { dstsVoltsA, dstsName, productFriendlyName, alarmTripType }

DESCRIPTION "RMS Voltage of Side A Set Point Sensor Trap"

::= 11905



odsDstsAmpsATRAP TRAP-TYPE

ENTERPRISE opengate

VARIABLES { dstsAmpsA, dstsName, productFriendlyName, alarmTripType }

DESCRIPTION "RMS Current of Side A Set Point Sensor Trap"

::= 11906



odsDstsVoltsBTRAP TRAP-TYPE

ENTERPRISE opengate

VARIABLES { dstsVoltsB, dstsName, productFriendlyName, alarmTripType }

DESCRIPTION "RMS Voltage of Side B Set Point Sensor Trap"

::= 11907



odsDstsAmpsBTRAP TRAP-TYPE

ENTERPRISE opengate

VARIABLES { dstsAmpsB, dstsName, productFriendlyName, alarmTripType }

DESCRIPTION "RMS Current of Side B Set Point Sensor Trap"

::= 11908



odsDstsSourceAActiveTRAP TRAP-TYPE

ENTERPRISE opengate

VARIABLES { dstsSourceAActive, dstsName, productFriendlyName, alarmTripType }

DESCRIPTION "Source A Active Set Point Sensor Trap"

::= 11909



odsDstsSourceBActiveTRAP TRAP-TYPE

ENTERPRISE opengate

VARIABLES { dstsSourceBActive, dstsName, productFriendlyName, alarmTripType }

DESCRIPTION "Source B Active Set Point Sensor Trap"

::= 11910



odsDstsPowerStatusATRAP TRAP-TYPE

ENTERPRISE opengate

VARIABLES { dstsPowerStatusA, dstsName, productFriendlyName, alarmTripType }

DESCRIPTION "Source A Power Qualilty Active Set Point Sensor Trap"

::= 11911



odsDstsPowerStatusBTRAP TRAP-TYPE

ENTERPRISE opengate

VARIABLES { dstsPowerStatusB, dstsName, productFriendlyName, alarmTripType }

DESCRIPTION "Source B Power Qualilty Active Set Point Sensor Trap"

::= 11912



odsDstsSourceATempCTRAP TRAP-TYPE

ENTERPRISE opengate

VARIABLES { dstsSourceATempC, dstsName, productFriendlyName, alarmTripType }

DESCRIPTION "Source A Temp Sensor Trap"

::= 11913



odsDstsSourceBTempCTRAP TRAP-TYPE

ENTERPRISE opengate

VARIABLES { dstsSourceBTempC, dstsName, productFriendlyName, alarmTripType }

DESCRIPTION "Source B Temp Sensor Trap"

::= 11914



odsCpmSensorStatusTRAP TRAP-TYPE

ENTERPRISE opengate

VARIABLES { cpmSensorStatus, cpmSensorName, productFriendlyName, alarmTripType }

DESCRIPTION "City Power sensor Trap"

::= 12005



odsSmokeAlarmStatusTRAP TRAP-TYPE

ENTERPRISE opengate

VARIABLES { smokeAlarmStatus, smokeAlarmName, productFriendlyName, alarmTripType }

DESCRIPTION "Smoke alarm Trap"

::= 12105



odsNeg48VdcSensorVoltageTRAP TRAP-TYPE

ENTERPRISE opengate

VARIABLES { neg48VdcSensorVoltage, neg48VdcSensorName, productFriendlyName, alarmTripType }

DESCRIPTION "-48Vdc Sensor Trap"

::= 12205



odsPos30VdcSensorVoltageTRAP TRAP-TYPE

ENTERPRISE opengate

VARIABLES { pos30VdcSensorVoltage, pos30VdcSensorName, productFriendlyName, alarmTripType }

DESCRIPTION "30Vdc Sensor Trap"

::= 12305



odsFancontrolTempCreturnATRAP TRAP-TYPE

ENTERPRISE opengate

VARIABLES { fancontrolTempCreturnA, fancontrolName, productFriendlyName, alarmTripType }

DESCRIPTION "TempCreturnA Active Set Point Sensor Trap"

::= 12405



odsFancontrolTempFreturnATRAP TRAP-TYPE

ENTERPRISE opengate

VARIABLES { fancontrolTempFreturnA, fancontrolName, productFriendlyName, alarmTripType }

DESCRIPTION "TempFreturnA Active Set Point Sensor Trap"

::= 12406



odsFancontrolTempCreturnBTRAP TRAP-TYPE

ENTERPRISE opengate

VARIABLES { fancontrolTempCreturnB, fancontrolName, productFriendlyName, alarmTripType }

DESCRIPTION "TempCreturnB Active Set Point Sensor Trap"

::= 12407



odsFancontrolTempFreturnBTRAP TRAP-TYPE

ENTERPRISE opengate

VARIABLES { fancontrolTempFreturnB, fancontrolName, productFriendlyName, alarmTripType }

DESCRIPTION "TempFreturnB Active Set Point Sensor Trap"

::= 12408



odsFancontrolRpmFanATRAP TRAP-TYPE

ENTERPRISE opengate

VARIABLES { fancontrolRpmFanA, fancontrolName, productFriendlyName, alarmTripType }

DESCRIPTION "RpmFanA Active Set Point Sensor Trap"

::= 12409



odsFancontrolRpmFanBTRAP TRAP-TYPE

ENTERPRISE opengate

VARIABLES { fancontrolRpmFanB, fancontrolName, productFriendlyName, alarmTripType }

DESCRIPTION "RpmFanB Active Set Point Sensor Trap"

::= 12410



odsFancontrolCapacityATRAP TRAP-TYPE

ENTERPRISE opengate

VARIABLES { fancontrolCapacityA, fancontrolName, productFriendlyName, alarmTripType }

DESCRIPTION "CapacityA Active Set Point Sensor Trap"

::= 12411



odsFancontrolCapacityBTRAP TRAP-TYPE

ENTERPRISE opengate

VARIABLES { fancontrolCapacityB, fancontrolName, productFriendlyName, alarmTripType }

DESCRIPTION "CapacityB Active Set Point Sensor Trap"

::= 12412



odsFancontrolPressErrTRAP TRAP-TYPE

ENTERPRISE opengate

VARIABLES { fancontrolPressErr, fancontrolName, productFriendlyName, alarmTripType }

DESCRIPTION "PressErr Active Set Point Sensor Trap"

::= 12413



odsFancontrolPressDiffTRAP TRAP-TYPE

ENTERPRISE opengate

VARIABLES { fancontrolPressDiff, fancontrolName, productFriendlyName, alarmTripType }

DESCRIPTION "PressDiff Active Set Point Sensor Trap"

::= 12414



odsFancontrolSetPointTRAP TRAP-TYPE

ENTERPRISE opengate

VARIABLES { fancontrolSetPoint, fancontrolName, productFriendlyName, alarmTripType }

DESCRIPTION "SetPoint Active Set Point Sensor Trap"

::= 12415



odsFancontrolCFMTRAP TRAP-TYPE

ENTERPRISE opengate

VARIABLES { fancontrolCFM, fancontrolName, productFriendlyName, alarmTripType }

DESCRIPTION "CFM Active Set Point Sensor Trap"

::= 12416



odsFancontrolTempCreturnTRAP TRAP-TYPE

ENTERPRISE opengate

VARIABLES { fancontrolTempCreturn, fancontrolName, productFriendlyName, alarmTripType }

DESCRIPTION "TempCreturn Active Set Point Sensor Trap"

::= 12417



odsFancontrolTempFreturnTRAP TRAP-TYPE

ENTERPRISE opengate

VARIABLES { fancontrolTempFreturn, fancontrolName, productFriendlyName, alarmTripType }

DESCRIPTION "TempCreturn Active Set Point Sensor Trap"

::= 12418



odsFancontrolCapacityTRAP TRAP-TYPE

ENTERPRISE opengate

VARIABLES { fancontrolCapacity, fancontrolName, productFriendlyName, alarmTripType }

DESCRIPTION "Capacity Active Set Point Sensor Trap"

::= 12419



odsFancontrolFanMissingTRAP TRAP-TYPE

ENTERPRISE opengate

VARIABLES { fancontrolFanMissing, fancontrolName, productFriendlyName, alarmTripType }

DESCRIPTION "FanMissing Active Set Point Sensor Trap"

::= 12420



odsFancontrolFanRegulateTRAP TRAP-TYPE

ENTERPRISE opengate

VARIABLES { fancontrolFanRegulate, fancontrolName, productFriendlyName, alarmTripType }

DESCRIPTION "FanRegulate Active Set Point Sensor Trap"

::= 12421



odsFancontrolFanCommTRAP TRAP-TYPE

ENTERPRISE opengate

VARIABLES { fancontrolFanComm, fancontrolName, productFriendlyName, alarmTripType }

DESCRIPTION "FanComm Active Set Point Sensor Trap"

::= 12422



odsFancontrolTempBus1TRAP TRAP-TYPE

ENTERPRISE opengate

VARIABLES { fancontrolTempBus1, fancontrolName, productFriendlyName, alarmTripType }

DESCRIPTION "TempBus1 Active Set Point Sensor Trap"

::= 12423



odsFancontrolPowerFeedTRAP TRAP-TYPE

ENTERPRISE opengate

VARIABLES { fancontrolPowerFeed, fancontrolName, productFriendlyName, alarmTripType }

DESCRIPTION "PowerFeed Active Set Point Sensor Trap"

::= 12424



odsFancontrolFanTypeMismatchTRAP TRAP-TYPE

ENTERPRISE opengate

VARIABLES { fancontrolFanTypeMismatch, fancontrolName, productFriendlyName, alarmTripType }

DESCRIPTION "FanTypeMismatch Active Set Point Sensor Trap"

::= 12425



odsFancontrolBadPressureSensorTRAP TRAP-TYPE

ENTERPRISE opengate

VARIABLES { fancontrolBadPressureSensor, fancontrolName, productFriendlyName, alarmTripType }

DESCRIPTION "BadPressureSensor Active Set Point Sensor Trap"

::= 12426



odsFancontrolFanEndofLifeTRAP TRAP-TYPE

ENTERPRISE opengate

VARIABLES { fancontrolFanEndofLife, fancontrolName, productFriendlyName, alarmTripType }

DESCRIPTION "FanEndofLife Active Set Point Sensor Trap"

::= 12427



odsFancontrolRackDoorOpenTRAP TRAP-TYPE

ENTERPRISE opengate

VARIABLES { fancontrolRackDoorOpen, fancontrolName, productFriendlyName, alarmTripType }

DESCRIPTION "RackDoorOpen Active Set Point Sensor Trap"

::= 12428



odsClimateTempCCLEAR TRAP-TYPE

ENTERPRISE opengate

VARIABLES { climateTempC, climateName, productFriendlyName, alarmTripType }

DESCRIPTION "Climate Temperature Sensor Clear Trap"

::= 20205



odsClimateTempFCLEAR TRAP-TYPE

ENTERPRISE opengate

VARIABLES { climateTempF, climateName, productFriendlyName, alarmTripType }

DESCRIPTION "Climate Temperature Sensor Clear Trap"

::= 20206



odsClimateHumidityCLEAR TRAP-TYPE

ENTERPRISE opengate

VARIABLES { climateHumidity, climateName, productFriendlyName, alarmTripType }

DESCRIPTION "Climate Humidity Sensor Clear Trap"

::= 20207



odsClimateLightCLEAR TRAP-TYPE

ENTERPRISE opengate

VARIABLES { climateLight, climateName, productFriendlyName, alarmTripType }

DESCRIPTION "Climate Light Sensor Clear Trap"

::= 20208



odsClimateAirflowCLEAR TRAP-TYPE

ENTERPRISE opengate

VARIABLES { climateAirflow, climateName, productFriendlyName, alarmTripType }

DESCRIPTION "Climate Air Flow Sensor Clear Trap"

::= 20209



odsClimateSoundCLEAR TRAP-TYPE

ENTERPRISE opengate

VARIABLES { climateSound, climateName, productFriendlyName, alarmTripType }

DESCRIPTION "Climate Sound Sensor Clear Trap"

::= 20210



odsClimateIO1CLEAR TRAP-TYPE

ENTERPRISE opengate

VARIABLES { climateIO1, climateName, productFriendlyName, alarmTripType }

DESCRIPTION "Climate IO1 Sensor Clear Trap"

::= 20211



odsClimateIO2CLEAR TRAP-TYPE

ENTERPRISE opengate

VARIABLES { climateIO2, climateName, productFriendlyName, alarmTripType }

DESCRIPTION "Climate IO2 Sensor Clear Trap"

::= 20212



odsClimateIO3CLEAR TRAP-TYPE

ENTERPRISE opengate

VARIABLES { climateIO3, climateName, productFriendlyName, alarmTripType }

DESCRIPTION "Climate IO3 Sensor Clear Trap"

::= 20213



odsPowMonKWattHrsCLEAR TRAP-TYPE

ENTERPRISE opengate

VARIABLES { powMonKWattHrs, powMonName, productFriendlyName, alarmTripType }

DESCRIPTION "Kilo Watt Hours Clear Trap"

::= 20305



odsPowMonVoltsCLEAR TRAP-TYPE

ENTERPRISE opengate

VARIABLES { powMonVolts, powMonName, productFriendlyName, alarmTripType }

DESCRIPTION "Volts Clear Trap"

::= 20306



odsPowMonVoltMaxCLEAR TRAP-TYPE

ENTERPRISE opengate

VARIABLES { powMonVoltMax, powMonName, productFriendlyName, alarmTripType }

DESCRIPTION "Volts Max Clear Trap"

::= 20307



odsPowMonVoltMinCLEAR TRAP-TYPE

ENTERPRISE opengate

VARIABLES { powMonVoltMin, powMonName, productFriendlyName, alarmTripType }

DESCRIPTION "Volts Min Clear Trap"

::= 20308



odsPowMonVoltPkCLEAR TRAP-TYPE

ENTERPRISE opengate

VARIABLES { powMonVoltPk, powMonName, productFriendlyName, alarmTripType }

DESCRIPTION "Volt Peak Clear Trap"

::= 20309



odsPowMonAmpsX10CLEAR TRAP-TYPE

ENTERPRISE opengate

VARIABLES { powMonAmpsX10, powMonName, productFriendlyName, alarmTripType }

DESCRIPTION "Amps x 10 Clear Trap"

::= 20310



odsPowMonRealPowCLEAR TRAP-TYPE

ENTERPRISE opengate

VARIABLES { powMonRealPow, powMonName, productFriendlyName, alarmTripType }

DESCRIPTION "Real Power Clear Trap"

::= 20311



odsPowMonAppPowCLEAR TRAP-TYPE

ENTERPRISE opengate

VARIABLES { powMonAppPow, powMonName, productFriendlyName, alarmTripType }

DESCRIPTION "Apparent Power Clear Trap"

::= 20312



odsPowMonPwrFactCLEAR TRAP-TYPE

ENTERPRISE opengate

VARIABLES { powMonPwrFact, powMonName, productFriendlyName, alarmTripType }

DESCRIPTION "Power Factor Clear Trap"

::= 20313



odsPowMonOutlet1CLEAR TRAP-TYPE

ENTERPRISE opengate

VARIABLES { powMonOutlet1, powMonName, productFriendlyName, alarmTripType }

DESCRIPTION "Outlet 1 Clear Trap"

::= 20314



odsPowMonOutlet2CLEAR TRAP-TYPE

ENTERPRISE opengate

VARIABLES { powMonOutlet2, powMonName, productFriendlyName, alarmTripType }

DESCRIPTION "Outlet 2 Clear Trap"

::= 20315



odsTempSensorTempCCLEAR TRAP-TYPE

ENTERPRISE opengate

VARIABLES { tempSensorTempC, tempSensorName, productFriendlyName, alarmTripType }

DESCRIPTION "Remote Temp Sensor - Temperature Clear Trap"

::= 20405



odsTempSensorTempFCLEAR TRAP-TYPE

ENTERPRISE opengate

VARIABLES { tempSensorTempF, tempSensorName, productFriendlyName, alarmTripType }

DESCRIPTION "Remote Temp Sensor - Temperature Clear Trap"

::= 20406



odsAirFlowSensorFlowCLEAR TRAP-TYPE

ENTERPRISE opengate

VARIABLES { airFlowSensorFlow, airFlowSensorName, productFriendlyName, alarmTripType }

DESCRIPTION "Remote Air Flow Sensor - Air Flow Clear Trap"

::= 20505



odsAirFlowSensorTempCCLEAR TRAP-TYPE

ENTERPRISE opengate

VARIABLES { airFlowSensorTempC, airFlowSensorName, productFriendlyName, alarmTripType }

DESCRIPTION "Remote Air Flow Sensor - Temperature Clear Trap"

::= 20506



odsAirFlowSensorTempFCLEAR TRAP-TYPE

ENTERPRISE opengate

VARIABLES { airFlowSensorTempF, airFlowSensorName, productFriendlyName, alarmTripType }

DESCRIPTION "Remote Air Flow Sensor - Temperature Clear Trap"

::= 20507



odsAirFlowSensorHumidityCLEAR TRAP-TYPE

ENTERPRISE opengate

VARIABLES { airFlowSensorHumidity, airFlowSensorName, productFriendlyName, alarmTripType }

DESCRIPTION "Remote Air Flow Sensor - Humidity Clear Trap"

::= 20508



odsPowerVoltsCLEAR TRAP-TYPE

ENTERPRISE opengate

VARIABLES { powerVolts, powerName, productFriendlyName, alarmTripType }

DESCRIPTION "Power-Only Volts Clear Trap"

::= 20605



odsPowerAmpsCLEAR TRAP-TYPE

ENTERPRISE opengate

VARIABLES { powerAmps, powerName, productFriendlyName, alarmTripType }

DESCRIPTION "Power-Only Amps Clear Trap"

::= 20606



odsPowerRealPowCLEAR TRAP-TYPE

ENTERPRISE opengate

VARIABLES { powerRealPow, powerName, productFriendlyName, alarmTripType }

DESCRIPTION "Power-Only Watts Clear Trap"

::= 20607



odsPowerAppPowCLEAR TRAP-TYPE

ENTERPRISE opengate

VARIABLES { powerAppPow, powerName, productFriendlyName, alarmTripType }

DESCRIPTION "Power-Only Volt Amps Clear Trap"

::= 20608



odsPowerPwrFactorCLEAR TRAP-TYPE

ENTERPRISE opengate

VARIABLES { powerPwrFactor, powerName, productFriendlyName, alarmTripType }

DESCRIPTION "Power-Only Power Factor Clear Trap"

::= 20609



odsDoorSensorStatusCLEAR TRAP-TYPE

ENTERPRISE opengate

VARIABLES { doorSensorStatus, doorSensorName, productFriendlyName, alarmTripType }

DESCRIPTION "Door sensor Clear Trap"

::= 20705



odsWaterSensorDampnessCLEAR TRAP-TYPE

ENTERPRISE opengate

VARIABLES { waterSensorDampness, waterSensorName, productFriendlyName, alarmTripType }

DESCRIPTION "Water sensor Clear Trap"

::= 20805



odsCurrentMonitorAmpsCLEAR TRAP-TYPE

ENTERPRISE opengate

VARIABLES { currentMonitorAmps, currentMonitorName, productFriendlyName, alarmTripType }

DESCRIPTION "Current Monitor Amps Clear Trap"

::= 20905



odsMillivoltMonitorMVCLEAR TRAP-TYPE

ENTERPRISE opengate

VARIABLES { millivoltMonitorMV, millivoltMonitorName, productFriendlyName, alarmTripType }

DESCRIPTION "Millivolt Monitor Clear Trap"

::= 21005



odsPow3ChKWattHrsACLEAR TRAP-TYPE

ENTERPRISE opengate

VARIABLES { pow3ChKWattHrsA, pow3ChName, productFriendlyName, alarmTripType }

DESCRIPTION "Kilo Watt Hours A Clear Trap"

::= 21105



odsPow3ChVoltsACLEAR TRAP-TYPE

ENTERPRISE opengate

VARIABLES { pow3ChVoltsA, pow3ChName, productFriendlyName, alarmTripType }

DESCRIPTION "Volts A Clear Trap"

::= 21106



odsPow3ChVoltMaxACLEAR TRAP-TYPE

ENTERPRISE opengate

VARIABLES { pow3ChVoltMaxA, pow3ChName, productFriendlyName, alarmTripType }

DESCRIPTION "Volts Max A Clear Trap"

::= 21107



odsPow3ChVoltMinACLEAR TRAP-TYPE

ENTERPRISE opengate

VARIABLES { pow3ChVoltMinA, pow3ChName, productFriendlyName, alarmTripType }

DESCRIPTION "Volts Min A Clear Trap"

::= 21108



odsPow3ChVoltPkACLEAR TRAP-TYPE

ENTERPRISE opengate

VARIABLES { pow3ChVoltPkA, pow3ChName, productFriendlyName, alarmTripType }

DESCRIPTION "Volt Peak A Clear Trap"

::= 21109



odsPow3ChAmpsX10ACLEAR TRAP-TYPE

ENTERPRISE opengate

VARIABLES { pow3ChAmpsX10A, pow3ChName, productFriendlyName, alarmTripType }

DESCRIPTION "Amps x 10 A Clear Trap"

::= 21110



odsPow3ChRealPowACLEAR TRAP-TYPE

ENTERPRISE opengate

VARIABLES { pow3ChRealPowA, pow3ChName, productFriendlyName, alarmTripType }

DESCRIPTION "Real Power A Clear Trap"

::= 21111



odsPow3ChAppPowACLEAR TRAP-TYPE

ENTERPRISE opengate

VARIABLES { pow3ChAppPowA, pow3ChName, productFriendlyName, alarmTripType }

DESCRIPTION "Apparent Power A Clear Trap"

::= 21112



odsPow3ChPwrFactACLEAR TRAP-TYPE

ENTERPRISE opengate

VARIABLES { pow3ChPwrFactA, pow3ChName, productFriendlyName, alarmTripType }

DESCRIPTION "Power Factor A Clear Trap"

::= 21113



odsPow3ChKWattHrsBCLEAR TRAP-TYPE

ENTERPRISE opengate

VARIABLES { pow3ChKWattHrsB, pow3ChName, productFriendlyName, alarmTripType }

DESCRIPTION "Kilo Watt Hours B Clear Trap"

::= 21114



odsPow3ChVoltsBCLEAR TRAP-TYPE

ENTERPRISE opengate

VARIABLES { pow3ChVoltsB, pow3ChName, productFriendlyName, alarmTripType }

DESCRIPTION "Volts B Clear Trap"

::= 21115



odsPow3ChVoltMaxBCLEAR TRAP-TYPE

ENTERPRISE opengate

VARIABLES { pow3ChVoltMaxB, pow3ChName, productFriendlyName, alarmTripType }

DESCRIPTION "Volts Max B Clear Trap"

::= 21116



odsPow3ChVoltMinBCLEAR TRAP-TYPE

ENTERPRISE opengate

VARIABLES { pow3ChVoltMinB, pow3ChName, productFriendlyName, alarmTripType }

DESCRIPTION "Volts Min B Clear Trap"

::= 21117



odsPow3ChVoltPkBCLEAR TRAP-TYPE

ENTERPRISE opengate

VARIABLES { pow3ChVoltPkB, pow3ChName, productFriendlyName, alarmTripType }

DESCRIPTION "Volt Peak B Clear Trap"

::= 21118



odsPow3ChAmpsX10BCLEAR TRAP-TYPE

ENTERPRISE opengate

VARIABLES { pow3ChAmpsX10B, pow3ChName, productFriendlyName, alarmTripType }

DESCRIPTION "Amps x 10 B Clear Trap"

::= 21119



odsPow3ChRealPowBCLEAR TRAP-TYPE

ENTERPRISE opengate

VARIABLES { pow3ChRealPowB, pow3ChName, productFriendlyName, alarmTripType }

DESCRIPTION "Real Power B Clear Trap"

::= 21120



odsPow3ChAppPowBCLEAR TRAP-TYPE

ENTERPRISE opengate

VARIABLES { pow3ChAppPowB, pow3ChName, productFriendlyName, alarmTripType }

DESCRIPTION "Apparent Power B Clear Trap"

::= 21121



odsPow3ChPwrFactBCLEAR TRAP-TYPE

ENTERPRISE opengate

VARIABLES { pow3ChPwrFactB, pow3ChName, productFriendlyName, alarmTripType }

DESCRIPTION "Power Factor B Clear Trap"

::= 21122



odsPow3ChKWattHrsCCLEAR TRAP-TYPE

ENTERPRISE opengate

VARIABLES { pow3ChKWattHrsC, pow3ChName, productFriendlyName, alarmTripType }

DESCRIPTION "Kilo Watt Hours C Clear Trap"

::= 21123



odsPow3ChVoltsCCLEAR TRAP-TYPE

ENTERPRISE opengate

VARIABLES { pow3ChVoltsC, pow3ChName, productFriendlyName, alarmTripType }

DESCRIPTION "Volts C Clear Trap"

::= 21124



odsPow3ChVoltMaxCCLEAR TRAP-TYPE

ENTERPRISE opengate

VARIABLES { pow3ChVoltMaxC, pow3ChName, productFriendlyName, alarmTripType }

DESCRIPTION "Volts Max C Clear Trap"

::= 21125



odsPow3ChVoltMinCCLEAR TRAP-TYPE

ENTERPRISE opengate

VARIABLES { pow3ChVoltMinC, pow3ChName, productFriendlyName, alarmTripType }

DESCRIPTION "Volts Min C Clear Trap"

::= 21126



odsPow3ChVoltPkCCLEAR TRAP-TYPE

ENTERPRISE opengate

VARIABLES { pow3ChVoltPkC, pow3ChName, productFriendlyName, alarmTripType }

DESCRIPTION "Volt Peak C Clear Trap"

::= 21127



odsPow3ChAmpsX10CCLEAR TRAP-TYPE

ENTERPRISE opengate

VARIABLES { pow3ChAmpsX10C, pow3ChName, productFriendlyName, alarmTripType }

DESCRIPTION "Amps x 10 C Clear Trap"

::= 21128



odsPow3ChRealPowCCLEAR TRAP-TYPE

ENTERPRISE opengate

VARIABLES { pow3ChRealPowC, pow3ChName, productFriendlyName, alarmTripType }

DESCRIPTION "Real Power C Clear Trap"

::= 21129



odsPow3ChAppPowCCLEAR TRAP-TYPE

ENTERPRISE opengate

VARIABLES { pow3ChAppPowC, pow3ChName, productFriendlyName, alarmTripType }

DESCRIPTION "Apparent Power C Clear Trap"

::= 21130



odsPow3ChPwrFactCCLEAR TRAP-TYPE

ENTERPRISE opengate

VARIABLES { pow3ChPwrFactC, pow3ChName, productFriendlyName, alarmTripType }

DESCRIPTION "Power Factor C Clear Trap"

::= 21131



odsOutlet1StatusCLEAR TRAP-TYPE

ENTERPRISE opengate

VARIABLES { outlet1Status, outletName, productFriendlyName, alarmTripType }

DESCRIPTION "Outlet 1 Status Clear Trap"

::= 21205



odsOutlet2StatusCLEAR TRAP-TYPE

ENTERPRISE opengate

VARIABLES { outlet2Status, outletName, productFriendlyName, alarmTripType }

DESCRIPTION "Outlet 2 Status Clear Trap"

::= 21206



odsVsfcSetPointCCLEAR TRAP-TYPE

ENTERPRISE opengate

VARIABLES { vsfcSetPointC, vsfcName, productFriendlyName, alarmTripType }

DESCRIPTION "Vsfc Temp Set Point Sensor Clear"

::= 21305



odsVsfcSetPointFCLEAR TRAP-TYPE

ENTERPRISE opengate

VARIABLES { vsfcSetPointF, vsfcName, productFriendlyName, alarmTripType }

DESCRIPTION "Vsfc Temp Set Point Sensor Clear"

::= 21306



odsVsfcIntTempCCLEAR TRAP-TYPE

ENTERPRISE opengate

VARIABLES { vsfcIntTempC, vsfcName, productFriendlyName, alarmTripType }

DESCRIPTION "Vsfc Internal Temp Sensor Clear"

::= 21307



odsVsfcIntTempFCLEAR TRAP-TYPE

ENTERPRISE opengate

VARIABLES { vsfcIntTempF, vsfcName, productFriendlyName, alarmTripType }

DESCRIPTION "Vsfc Internal Temp Sensor Clear"

::= 21308



odsVsfcExt1TempCCLEAR TRAP-TYPE

ENTERPRISE opengate

VARIABLES { vsfcExt1TempC, vsfcName, productFriendlyName, alarmTripType }

DESCRIPTION "Vsfc External Temp 1 Sensor Clear"

::= 21309



odsVsfcExt1TempFCLEAR TRAP-TYPE

ENTERPRISE opengate

VARIABLES { vsfcExt1TempF, vsfcName, productFriendlyName, alarmTripType }

DESCRIPTION "Vsfc External Temp 1 Sensor Clear"

::= 21310



odsVsfcExt2TempCCLEAR TRAP-TYPE

ENTERPRISE opengate

VARIABLES { vsfcExt2TempC, vsfcName, productFriendlyName, alarmTripType }

DESCRIPTION "Vsfc External Temp 2 Sensor Clear"

::= 21311



odsVsfcExt2TempFCLEAR TRAP-TYPE

ENTERPRISE opengate

VARIABLES { vsfcExt2TempF, vsfcName, productFriendlyName, alarmTripType }

DESCRIPTION "Vsfc External Temp 2 Sensor Clear"

::= 21312



odsVsfcExt3TempCCLEAR TRAP-TYPE

ENTERPRISE opengate

VARIABLES { vsfcExt3TempC, vsfcName, productFriendlyName, alarmTripType }

DESCRIPTION "Vsfc External Temp 3 Sensor Clear"

::= 21313



odsVsfcExt3TempFCLEAR TRAP-TYPE

ENTERPRISE opengate

VARIABLES { vsfcExt3TempF, vsfcName, productFriendlyName, alarmTripType }

DESCRIPTION "Vsfc External Temp 3 Sensor Clear"

::= 21314



odsVsfcExt4TempCCLEAR TRAP-TYPE

ENTERPRISE opengate

VARIABLES { vsfcExt4TempC, vsfcName, productFriendlyName, alarmTripType }

DESCRIPTION "Vsfc External Temp 4 Sensor Clear"

::= 21315



odsVsfcExt4TempFCLEAR TRAP-TYPE

ENTERPRISE opengate

VARIABLES { vsfcExt4TempF, vsfcName, productFriendlyName, alarmTripType }

DESCRIPTION "Vsfc External Temp 4 Sensor Clear"

::= 21316



odsVsfcFanSpeedCLEAR TRAP-TYPE

ENTERPRISE opengate

VARIABLES { vsfcFanSpeed, vsfcName, productFriendlyName, alarmTripType }

DESCRIPTION "Vsfc Fan Speed Sensor Clear"

::= 21317



odsCtrl3ChVoltsACLEAR TRAP-TYPE

ENTERPRISE opengate

VARIABLES { ctrl3ChVoltsA, ctrl3ChName, productFriendlyName, alarmTripType }

DESCRIPTION "Volts A Clear"

::= 21405



odsCtrl3ChVoltPkACLEAR TRAP-TYPE

ENTERPRISE opengate

VARIABLES { ctrl3ChVoltPkA, ctrl3ChName, productFriendlyName, alarmTripType }

DESCRIPTION "Volt Peak A Clear"

::= 21406



odsCtrl3ChAmpsACLEAR TRAP-TYPE

ENTERPRISE opengate

VARIABLES { ctrl3ChAmpsA, ctrl3ChName, productFriendlyName, alarmTripType }

DESCRIPTION "Amps A Clear"

::= 21407



odsCtrl3ChAmpPkACLEAR TRAP-TYPE

ENTERPRISE opengate

VARIABLES { ctrl3ChAmpPkA, ctrl3ChName, productFriendlyName, alarmTripType }

DESCRIPTION "Amps Peak A Clear"

::= 21408



odsCtrl3ChRealPowACLEAR TRAP-TYPE

ENTERPRISE opengate

VARIABLES { ctrl3ChRealPowA, ctrl3ChName, productFriendlyName, alarmTripType }

DESCRIPTION "Real Power A Clear"

::= 21409



odsCtrl3ChAppPowACLEAR TRAP-TYPE

ENTERPRISE opengate

VARIABLES { ctrl3ChAppPowA, ctrl3ChName, productFriendlyName, alarmTripType }

DESCRIPTION "Apparent Power A Clear"

::= 21410



odsCtrl3ChPwrFactACLEAR TRAP-TYPE

ENTERPRISE opengate

VARIABLES { ctrl3ChPwrFactA, ctrl3ChName, productFriendlyName, alarmTripType }

DESCRIPTION "Power Factor A Clear"

::= 21411



odsCtrl3ChVoltsBCLEAR TRAP-TYPE

ENTERPRISE opengate

VARIABLES { ctrl3ChVoltsB, ctrl3ChName, productFriendlyName, alarmTripType }

DESCRIPTION "Volts B Clear"

::= 21412



odsCtrl3ChVoltPkBCLEAR TRAP-TYPE

ENTERPRISE opengate

VARIABLES { ctrl3ChVoltPkB, ctrl3ChName, productFriendlyName, alarmTripType }

DESCRIPTION "Volt Peak B Clear"

::= 21413



odsCtrl3ChAmpsBCLEAR TRAP-TYPE

ENTERPRISE opengate

VARIABLES { ctrl3ChAmpsB, ctrl3ChName, productFriendlyName, alarmTripType }

DESCRIPTION "Amps B Clear"

::= 21414



odsCtrl3ChAmpPkBCLEAR TRAP-TYPE

ENTERPRISE opengate

VARIABLES { ctrl3ChAmpPkB, ctrl3ChName, productFriendlyName, alarmTripType }

DESCRIPTION "Amps Peak B Clear"

::= 21415



odsCtrl3ChRealPowBCLEAR TRAP-TYPE

ENTERPRISE opengate

VARIABLES { ctrl3ChRealPowB, ctrl3ChName, productFriendlyName, alarmTripType }

DESCRIPTION "Real Power B Clear"

::= 21416



odsCtrl3ChAppPowBCLEAR TRAP-TYPE

ENTERPRISE opengate

VARIABLES { ctrl3ChAppPowB, ctrl3ChName, productFriendlyName, alarmTripType }

DESCRIPTION "Apparent Power B Clear"

::= 21417



odsCtrl3ChPwrFactBCLEAR TRAP-TYPE

ENTERPRISE opengate

VARIABLES { ctrl3ChPwrFactB, ctrl3ChName, productFriendlyName, alarmTripType }

DESCRIPTION "Power Factor B Clear"

::= 21418



odsCtrl3ChVoltsCCLEAR TRAP-TYPE

ENTERPRISE opengate

VARIABLES { ctrl3ChVoltsC, ctrl3ChName, productFriendlyName, alarmTripType }

DESCRIPTION "Volts C Clear"

::= 21419



odsCtrl3ChVoltPkCCLEAR TRAP-TYPE

ENTERPRISE opengate

VARIABLES { ctrl3ChVoltPkC, ctrl3ChName, productFriendlyName, alarmTripType }

DESCRIPTION "Volt Peak C Clear"

::= 21420



odsCtrl3ChAmpsCCLEAR TRAP-TYPE

ENTERPRISE opengate

VARIABLES { ctrl3ChAmpsC, ctrl3ChName, productFriendlyName, alarmTripType }

DESCRIPTION "Amps C Clear"

::= 21421



odsCtrl3ChAmpPkCCLEAR TRAP-TYPE

ENTERPRISE opengate

VARIABLES { ctrl3ChAmpPkC, ctrl3ChName, productFriendlyName, alarmTripType }

DESCRIPTION "Amps Peak C Clear"

::= 21422



odsCtrl3ChRealPowCCLEAR TRAP-TYPE

ENTERPRISE opengate

VARIABLES { ctrl3ChRealPowC, ctrl3ChName, productFriendlyName, alarmTripType }

DESCRIPTION "Real Power C Clear"

::= 21423



odsCtrl3ChAppPowCCLEAR TRAP-TYPE

ENTERPRISE opengate

VARIABLES { ctrl3ChAppPowC, ctrl3ChName, productFriendlyName, alarmTripType }

DESCRIPTION "Apparent Power C Clear"

::= 21424



odsCtrl3ChPwrFactCCLEAR TRAP-TYPE

ENTERPRISE opengate

VARIABLES { ctrl3ChPwrFactC, ctrl3ChName, productFriendlyName, alarmTripType }

DESCRIPTION "Power Factor C Clear"

::= 21425



odsCtrlGrpAmpsACLEAR TRAP-TYPE

ENTERPRISE opengate

VARIABLES { ctrlGrpAmpsA, ctrlGrpAmpsName, productFriendlyName, alarmTripType }

DESCRIPTION "Group A Amps Clear Trap"

::= 21505



odsCtrlGrpAmpsBCLEAR TRAP-TYPE

ENTERPRISE opengate

VARIABLES { ctrlGrpAmpsB, ctrlGrpAmpsName, productFriendlyName, alarmTripType }

DESCRIPTION "Group B Amps Clear Trap"

::= 21506



odsCtrlGrpAmpsCCLEAR TRAP-TYPE

ENTERPRISE opengate

VARIABLES { ctrlGrpAmpsC, ctrlGrpAmpsName, productFriendlyName, alarmTripType }

DESCRIPTION "Group C Amps Clear Trap"

::= 21507



odsCtrlGrpAmpsDCLEAR TRAP-TYPE

ENTERPRISE opengate

VARIABLES { ctrlGrpAmpsD, ctrlGrpAmpsName, productFriendlyName, alarmTripType }

DESCRIPTION "Group D Amps Clear Trap"

::= 21508



odsCtrlGrpAmpsECLEAR TRAP-TYPE

ENTERPRISE opengate

VARIABLES { ctrlGrpAmpsE, ctrlGrpAmpsName, productFriendlyName, alarmTripType }

DESCRIPTION "Group E Amps Clear Trap"

::= 21509



odsCtrlGrpAmpsFCLEAR TRAP-TYPE

ENTERPRISE opengate

VARIABLES { ctrlGrpAmpsF, ctrlGrpAmpsName, productFriendlyName, alarmTripType }

DESCRIPTION "Group F Amps Clear Trap"

::= 21510



odsDewPointSensorDewPointCCLEAR TRAP-TYPE

ENTERPRISE opengate

VARIABLES { dewPointSensorDewPointC, dewPointSensorName, productFriendlyName, alarmTripType }

DESCRIPTION "Remote Dew Point Sensor - Dew Point Clear Trap"

::= 21705



odsDewPointSensorDewPointFCLEAR TRAP-TYPE

ENTERPRISE opengate

VARIABLES { dewPointSensorDewPointF, dewPointSensorName, productFriendlyName, alarmTripType }

DESCRIPTION "Remote Dew Point Sensor - Dew Point Clear Trap"

::= 21706



odsDewPointSensorTempCCLEAR TRAP-TYPE

ENTERPRISE opengate

VARIABLES { dewPointSensorTempC, dewPointSensorName, productFriendlyName, alarmTripType }

DESCRIPTION "Remote Dew Point Sensor - Temperature Clear Trap"

::= 21707



odsDewPointSensorTempFCLEAR TRAP-TYPE

ENTERPRISE opengate

VARIABLES { dewPointSensorTempF, dewPointSensorName, productFriendlyName, alarmTripType }

DESCRIPTION "Remote Dew Point Sensor - Temperature Clear Trap"

::= 21708



odsDewPointSensorHumidityCLEAR TRAP-TYPE

ENTERPRISE opengate

VARIABLES { dewPointSensorHumidity, dewPointSensorName, productFriendlyName, alarmTripType }

DESCRIPTION "Remote Dew Point Sensor - Humidity Clear Trap"

::= 21709



odsDigitalSensorDigitalCLEAR TRAP-TYPE

ENTERPRISE opengate

VARIABLES { digitalSensorDigital, digitalSensorName, productFriendlyName, alarmTripType }

DESCRIPTION "Digital sensor Clear Trap"

::= 21805



odsDstsVoltsACLEAR TRAP-TYPE

ENTERPRISE opengate

VARIABLES { dstsVoltsA, dstsName, productFriendlyName, alarmTripType }

DESCRIPTION "RMS Voltage of Side A Set Point Sensor Clear"

::= 21905



odsDstsAmpsACLEAR TRAP-TYPE

ENTERPRISE opengate

VARIABLES { dstsAmpsA, dstsName, productFriendlyName, alarmTripType }

DESCRIPTION "RMS Current of Side A Set Point Sensor Clear"

::= 21906



odsDstsVoltsBCLEAR TRAP-TYPE

ENTERPRISE opengate

VARIABLES { dstsVoltsB, dstsName, productFriendlyName, alarmTripType }

DESCRIPTION "RMS Voltage of Side B Set Point Sensor Clear"

::= 21907



odsDstsAmpsBCLEAR TRAP-TYPE

ENTERPRISE opengate

VARIABLES { dstsAmpsB, dstsName, productFriendlyName, alarmTripType }

DESCRIPTION "RMS Current of Side B Set Point Sensor Clear"

::= 21908



odsDstsSourceAActiveCLEAR TRAP-TYPE

ENTERPRISE opengate

VARIABLES { dstsSourceAActive, dstsName, productFriendlyName, alarmTripType }

DESCRIPTION "Source A Active Set Point Sensor Clear"

::= 21909



odsDstsSourceBActiveCLEAR TRAP-TYPE

ENTERPRISE opengate

VARIABLES { dstsSourceBActive, dstsName, productFriendlyName, alarmTripType }

DESCRIPTION "Source B Active Set Point Sensor Clear"

::= 21910



odsDstsPowerStatusACLEAR TRAP-TYPE

ENTERPRISE opengate

VARIABLES { dstsPowerStatusA, dstsName, productFriendlyName, alarmTripType }

DESCRIPTION "Source A Power Qualilty Active Set Point Sensor Clear"

::= 21911



odsDstsPowerStatusBCLEAR TRAP-TYPE

ENTERPRISE opengate

VARIABLES { dstsPowerStatusB, dstsName, productFriendlyName, alarmTripType }

DESCRIPTION "Source B Power Qualilty Active Set Point Sensor Clear"

::= 21912



odsDstsSourceATempCCLEAR TRAP-TYPE

ENTERPRISE opengate

VARIABLES { dstsSourceATempC, dstsName, productFriendlyName, alarmTripType }

DESCRIPTION "Source A Temp Sensor Clear"

::= 21913



odsDstsSourceBTempCCLEAR TRAP-TYPE

ENTERPRISE opengate

VARIABLES { dstsSourceBTempC, dstsName, productFriendlyName, alarmTripType }

DESCRIPTION "Source B Temp Sensor Clear"

::= 21914



odsCpmSensorStatusCLEAR TRAP-TYPE

ENTERPRISE opengate

VARIABLES { cpmSensorStatus, cpmSensorName, productFriendlyName, alarmTripType }

DESCRIPTION "City Power sensor Clear Trap"

::= 22005



odsSmokeAlarmStatusCLEAR TRAP-TYPE

ENTERPRISE opengate

VARIABLES { smokeAlarmStatus, smokeAlarmName, productFriendlyName, alarmTripType }

DESCRIPTION "Smoke alarm Clear Trap"

::= 22105



odsNeg48VdcSensorVoltageCLEAR TRAP-TYPE

ENTERPRISE opengate

VARIABLES { neg48VdcSensorVoltage, neg48VdcSensorName, productFriendlyName, alarmTripType }

DESCRIPTION "-48Vdc Sensor Clear Trap"

::= 22205



odsPos30VdcSensorVoltageCLEAR TRAP-TYPE

ENTERPRISE opengate

VARIABLES { pos30VdcSensorVoltage, pos30VdcSensorName, productFriendlyName, alarmTripType }

DESCRIPTION "30Vdc Sensor Clear Trap"

::= 22305



odsFancontrolTempCreturnACLEAR TRAP-TYPE

ENTERPRISE opengate

VARIABLES { fancontrolTempCreturnA, fancontrolName, productFriendlyName, alarmTripType }

DESCRIPTION "TempCreturnA Active Set Point Sensor Clear"

::= 22405



odsFancontrolTempFreturnACLEAR TRAP-TYPE

ENTERPRISE opengate

VARIABLES { fancontrolTempFreturnA, fancontrolName, productFriendlyName, alarmTripType }

DESCRIPTION "TempFreturnA Active Set Point Sensor Clear"

::= 22406



odsFancontrolTempCreturnBCLEAR TRAP-TYPE

ENTERPRISE opengate

VARIABLES { fancontrolTempCreturnB, fancontrolName, productFriendlyName, alarmTripType }

DESCRIPTION "TempCreturnB Active Set Point Sensor Clear"

::= 22407



odsFancontrolTempFreturnBCLEAR TRAP-TYPE

ENTERPRISE opengate

VARIABLES { fancontrolTempFreturnB, fancontrolName, productFriendlyName, alarmTripType }

DESCRIPTION "TempFreturnB Active Set Point Sensor Clear"

::= 22408



odsFancontrolRpmFanACLEAR TRAP-TYPE

ENTERPRISE opengate

VARIABLES { fancontrolRpmFanA, fancontrolName, productFriendlyName, alarmTripType }

DESCRIPTION "RpmFanA Active Set Point Sensor Clear"

::= 22409



odsFancontrolRpmFanBCLEAR TRAP-TYPE

ENTERPRISE opengate

VARIABLES { fancontrolRpmFanB, fancontrolName, productFriendlyName, alarmTripType }

DESCRIPTION "RpmFanB Active Set Point Sensor Clear"

::= 22410



odsFancontrolCapacityACLEAR TRAP-TYPE

ENTERPRISE opengate

VARIABLES { fancontrolCapacityA, fancontrolName, productFriendlyName, alarmTripType }

DESCRIPTION "CapacityA Active Set Point Sensor Clear"

::= 22411



odsFancontrolCapacityBCLEAR TRAP-TYPE

ENTERPRISE opengate

VARIABLES { fancontrolCapacityB, fancontrolName, productFriendlyName, alarmTripType }

DESCRIPTION "CapacityB Active Set Point Sensor Clear"

::= 22412



odsFancontrolPressErrCLEAR TRAP-TYPE

ENTERPRISE opengate

VARIABLES { fancontrolPressErr, fancontrolName, productFriendlyName, alarmTripType }

DESCRIPTION "PressErr Active Set Point Sensor Clear"

::= 22413



odsFancontrolPressDiffCLEAR TRAP-TYPE

ENTERPRISE opengate

VARIABLES { fancontrolPressDiff, fancontrolName, productFriendlyName, alarmTripType }

DESCRIPTION "PressDiff Active Set Point Sensor Clear"

::= 22414



odsFancontrolSetPointCLEAR TRAP-TYPE

ENTERPRISE opengate

VARIABLES { fancontrolSetPoint, fancontrolName, productFriendlyName, alarmTripType }

DESCRIPTION "SetPoint Active Set Point Sensor Clear"

::= 22415



odsFancontrolCFMCLEAR TRAP-TYPE

ENTERPRISE opengate

VARIABLES { fancontrolCFM, fancontrolName, productFriendlyName, alarmTripType }

DESCRIPTION "CFM Active Set Point Sensor Clear"

::= 22416



odsFancontrolTempCreturnCLEAR TRAP-TYPE

ENTERPRISE opengate

VARIABLES { fancontrolTempCreturn, fancontrolName, productFriendlyName, alarmTripType }

DESCRIPTION "TempCreturn Active Set Point Sensor Clear"

::= 22417



odsFancontrolTempFreturnCLEAR TRAP-TYPE

ENTERPRISE opengate

VARIABLES { fancontrolTempFreturn, fancontrolName, productFriendlyName, alarmTripType }

DESCRIPTION "TempCreturn Active Set Point Sensor Clear"

::= 22418



odsFancontrolCapacityCLEAR TRAP-TYPE

ENTERPRISE opengate

VARIABLES { fancontrolCapacity, fancontrolName, productFriendlyName, alarmTripType }

DESCRIPTION "Capacity Active Set Point Sensor Clear"

::= 22419



odsFancontrolFanMissingCLEAR TRAP-TYPE

ENTERPRISE opengate

VARIABLES { fancontrolFanMissing, fancontrolName, productFriendlyName, alarmTripType }

DESCRIPTION "FanMissing Active Set Point Sensor Clear"

::= 22420



odsFancontrolFanRegulateCLEAR TRAP-TYPE

ENTERPRISE opengate

VARIABLES { fancontrolFanRegulate, fancontrolName, productFriendlyName, alarmTripType }

DESCRIPTION "FanRegulate Active Set Point Sensor Clear"

::= 22421



odsFancontrolFanCommCLEAR TRAP-TYPE

ENTERPRISE opengate

VARIABLES { fancontrolFanComm, fancontrolName, productFriendlyName, alarmTripType }

DESCRIPTION "FanComm Active Set Point Sensor Clear"

::= 22422



odsFancontrolTempBus1CLEAR TRAP-TYPE

ENTERPRISE opengate

VARIABLES { fancontrolTempBus1, fancontrolName, productFriendlyName, alarmTripType }

DESCRIPTION "TempBus1 Active Set Point Sensor Clear"

::= 22423



odsFancontrolPowerFeedCLEAR TRAP-TYPE

ENTERPRISE opengate

VARIABLES { fancontrolPowerFeed, fancontrolName, productFriendlyName, alarmTripType }

DESCRIPTION "PowerFeed Active Set Point Sensor Clear"

::= 22424



odsFancontrolFanTypeMismatchCLEAR TRAP-TYPE

ENTERPRISE opengate

VARIABLES { fancontrolFanTypeMismatch, fancontrolName, productFriendlyName, alarmTripType }

DESCRIPTION "FanTypeMismatch Active Set Point Sensor Clear"

::= 22425



odsFancontrolBadPressureSensorCLEAR TRAP-TYPE

ENTERPRISE opengate

VARIABLES { fancontrolBadPressureSensor, fancontrolName, productFriendlyName, alarmTripType }

DESCRIPTION "BadPressureSensor Active Set Point Sensor Clear"

::= 22426



odsFancontrolFanEndofLifeCLEAR TRAP-TYPE

ENTERPRISE opengate

VARIABLES { fancontrolFanEndofLife, fancontrolName, productFriendlyName, alarmTripType }

DESCRIPTION "FanEndofLife Active Set Point Sensor Clear"

::= 22427



odsFancontrolRackDoorOpenCLEAR TRAP-TYPE

ENTERPRISE opengate

VARIABLES { fancontrolRackDoorOpen, fancontrolName, productFriendlyName, alarmTripType }

DESCRIPTION "RackDoorOpen Active Set Point Sensor Clear"

::= 22428



END
