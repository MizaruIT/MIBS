--     
-- System Resources MIB
--

--
-- IMPORTANT:  
--
-- This MIB is intended for internal use only, and is expected to change or be 
-- replaced completely in future releases.  It is published only for 
-- completeness.  Blue Coat Systems makes no guarantees of fitness or accuracy
-- of values supplied by this interface.  
-- 
-- Any use is strongly discouraged.
-- 

SYSTEM-RESOURCES-MIB DEFINITIONS ::= BEGIN

IMPORTS
      MODULE-IDENTITY, OBJECT-TYPE, NOTIFICATION-TYPE,
      ObjectName, Integer32, Counter32, snmpModules
                 FROM SNMPv2-SMI
      DateAndTime, DisplayString, TimeStamp
                 FROM SNMPv2-TC
      MODULE-COMPLIANCE, OBJECT-GROUP
                 FROM SNMPv2-CONF
      bchrSerial FROM BLUECOAT-HOST-RESOURCES-MIB
      blueCoatMgmt FROM BLUECOAT-MIB;

systemResourcesMIB MODULE-IDENTITY
    LAST-UPDATED    "200610230000Z"     -- October 23, 2006
    ORGANIZATION    "Blue Coat"
    CONTACT-INFO    "support@bluecoat.com"
    DESCRIPTION
        "Internal MIB defines Blue Coat SG Health Status for Blue Coat Director."
    REVISION        "200610230000Z"     -- October 23, 2006
    DESCRIPTION     "Marked as deprecated."
    ::= { blueCoatMgmt 8 }

Percent ::= TEXTUAL-CONVENTION
	STATUS		    deprecated
    DESCRIPTION     "Internal type for Blue Coat Director use only."
	SYNTAX          INTEGER (0..100)

ThresholdType ::= TEXTUAL-CONVENTION
    STATUS          deprecated
    DESCRIPTION     "Internal type for Blue Coat Director use only."
    SYNTAX          INTEGER {
       ok(0),
       low-warning(1),
       warning(2),
       high-warning(3),
       low-critical(4),
       critical(5),
       high-critical(6)
    }

NotificationType ::= TEXTUAL-CONVENTION
    STATUS          deprecated
    DESCRIPTION     "Internal type for Blue Coat Director use only."
    SYNTAX          INTEGER {
       none(0),
       log(1),
       email(2),
       snmptrap(3),
       emailandtrap(4),
       logandtrap(5), 
       logandemail(6),
       logandemailandtrap(7)
    }


--
-- GROUPS
--

cpu                OBJECT IDENTIFIER ::= { systemResourcesMIB 1 }
memory             OBJECT IDENTIFIER ::= { systemResourcesMIB 2 }
network            OBJECT IDENTIFIER ::= { systemResourcesMIB 3 } 
licenseUtilization OBJECT IDENTIFIER ::= { systemResourcesMIB 4 } 
licenseExpiration  OBJECT IDENTIFIER ::= { systemResourcesMIB 5 } 


--
-- CPU Utilization Group
--

cpuIndex OBJECT-TYPE
    SYNTAX          Integer32 (1..65535)
    MAX-ACCESS      read-only
    STATUS          deprecated
    DESCRIPTION     "Internal type for Blue Coat Director use only."
    ::= { cpu 1 }

cpuName OBJECT-TYPE
    SYNTAX          DisplayString
    MAX-ACCESS      read-only
    STATUS          deprecated
    DESCRIPTION     "Internal type for Blue Coat Director use only."
    ::= { cpu 2 }

cpuUtilizationValue OBJECT-TYPE
    SYNTAX          Percent
    MAX-ACCESS      read-only
    STATUS          deprecated
    DESCRIPTION     "Internal type for Blue Coat Director use only."
    ::= { cpu 3 }

cpuWarningThreshold OBJECT-TYPE
    SYNTAX          Integer32 (0..100)
    MAX-ACCESS      read-write
    STATUS          deprecated
    DESCRIPTION     "Internal type for Blue Coat Director use only."
    ::= { cpu 4 }

cpuWarningInterval OBJECT-TYPE
    SYNTAX          Integer32 (0..86400)
    UNITS           "Seconds"
    MAX-ACCESS      read-write
    STATUS          deprecated
    DESCRIPTION     "Internal type for Blue Coat Director use only."
    ::= { cpu 5 }

cpuCriticalThreshold OBJECT-TYPE
    SYNTAX          Integer32 (0..100)
    MAX-ACCESS      read-write
    STATUS          deprecated
    DESCRIPTION     "Internal type for Blue Coat Director use only."
    ::= { cpu 6 }

cpuCriticalInterval OBJECT-TYPE
    SYNTAX          Integer32 (0..86400)
    UNITS           "Seconds"
    MAX-ACCESS      read-write
    STATUS          deprecated
    DESCRIPTION     "Internal type for Blue Coat Director use only."
    ::= { cpu 7 }

cpuNotificationType OBJECT-TYPE
    SYNTAX          NotificationType
    MAX-ACCESS      read-write
    STATUS          deprecated
    DESCRIPTION     "Internal type for Blue Coat Director use only."
    DEFVAL { 3 }
    ::= { cpu 8 }

cpuCurrentState OBJECT-TYPE
    SYNTAX          ThresholdType
    MAX-ACCESS      read-only
    STATUS          deprecated
    DESCRIPTION     "Internal type for Blue Coat Director use only."
    ::= { cpu 9 }

cpuPreviousState OBJECT-TYPE
    SYNTAX          ThresholdType
    MAX-ACCESS      read-only
    STATUS          deprecated
    DESCRIPTION     "Internal type for Blue Coat Director use only."
    ::= { cpu 10 }

cpuLastChangeTime OBJECT-TYPE
    SYNTAX          DateAndTime
    MAX-ACCESS      read-only
    STATUS          deprecated
    DESCRIPTION     "Internal type for Blue Coat Director use only."
    ::= { cpu 11 }

cpuEvent OBJECT-IDENTITY
    STATUS          deprecated
    DESCRIPTION     "Internal object for Blue Coat Director use only."
    ::= { cpu 12 }

cpuTrap NOTIFICATION-TYPE
    OBJECTS  {
        cpuName,
        cpuUtilizationValue,
        cpuCurrentState,
        cpuPreviousState,
        cpuLastChangeTime,
        bchrSerial
    }
    STATUS          deprecated
    DESCRIPTION     "Internal trap type for Blue Coat Director use only."
    ::= { cpuEvent 1 }


--
-- Memory Utilization Group
--

memIndex OBJECT-TYPE
    SYNTAX          Integer32 (1..65535)
    MAX-ACCESS      read-only
    STATUS          deprecated
    DESCRIPTION     "Internal type for Blue Coat Director use only."
    ::= { memory 1 }

memName OBJECT-TYPE
    SYNTAX          DisplayString
    MAX-ACCESS      read-only
    STATUS          deprecated
    DESCRIPTION     "Internal type for Blue Coat Director use only."
    ::= { memory 2 }

memPressureValue OBJECT-TYPE
    SYNTAX          Percent
    MAX-ACCESS      read-only
    STATUS          deprecated
    DESCRIPTION     "Internal type for Blue Coat Director use only."
    ::= { memory 3 }

memWarningThreshold OBJECT-TYPE
    SYNTAX          Integer32 (0..100)
    MAX-ACCESS      read-write
    STATUS          deprecated
    DESCRIPTION     "Internal type for Blue Coat Director use only."
    ::= { memory 4 }

memWarningInterval OBJECT-TYPE
    SYNTAX          Integer32 (0..86400)
    UNITS           "Seconds"
    MAX-ACCESS      read-write
    STATUS          deprecated
    DESCRIPTION     "Internal type for Blue Coat Director use only."
    ::= { memory 5 }

memCriticalThreshold OBJECT-TYPE
    SYNTAX          Integer32 (0..100)
    MAX-ACCESS      read-write
    STATUS          deprecated
    DESCRIPTION     "Internal type for Blue Coat Director use only."
    ::= { memory 6 }

memCriticalInterval OBJECT-TYPE
    SYNTAX          Integer32 (0..86400)
    UNITS           "Seconds"
    MAX-ACCESS      read-write
    STATUS          deprecated
    DESCRIPTION     "Internal type for Blue Coat Director use only."
    ::= { memory 7 }

memNotificationType OBJECT-TYPE
    SYNTAX          NotificationType
    MAX-ACCESS      read-write
    STATUS          deprecated
    DESCRIPTION     "Internal type for Blue Coat Director use only."
    DEFVAL { 3 }
    ::= { memory 8 }


memCurrentState OBJECT-TYPE
    SYNTAX          ThresholdType
    MAX-ACCESS      read-only
    STATUS          deprecated
    DESCRIPTION     "Internal type for Blue Coat Director use only."
    ::= { memory 9 }

memPreviousState OBJECT-TYPE
    SYNTAX          ThresholdType
    MAX-ACCESS      read-only
    STATUS          deprecated
    DESCRIPTION     "Internal type for Blue Coat Director use only."
    ::= { memory 10 }

memLastChangeTime OBJECT-TYPE
    SYNTAX          DateAndTime
    MAX-ACCESS      read-only
    STATUS          deprecated
    DESCRIPTION     "Internal type for Blue Coat Director use only."
    ::= { memory 11 }

memEvent OBJECT-IDENTITY
    STATUS          deprecated
    DESCRIPTION     "Internal object for Blue Coat Director use only."
    ::= { memory 12 }
    
memTrap NOTIFICATION-TYPE
    OBJECTS  {
        memName,
        memPressureValue,
        memCurrentState,
        memPreviousState,
        memLastChangeTime,
        bchrSerial
    }
    STATUS          deprecated
    DESCRIPTION     "Internal trap type for Blue Coat Director use only."
    ::= { memEvent 1 }


--
-- Network Utilization Group
--

netTable OBJECT-TYPE
    SYNTAX          SEQUENCE OF NetEntry 
    MAX-ACCESS      not-accessible
    STATUS          deprecated
    DESCRIPTION     "Internal type for Blue Coat Director use only."
    ::= { network  1 }

netEntry OBJECT-TYPE
    SYNTAX          NetEntry 
    MAX-ACCESS      not-accessible
    STATUS          deprecated
    DESCRIPTION     "Internal type for Blue Coat Director use only."
    INDEX   { netIndex }
    ::= { netTable 1 }

NetEntry ::= SEQUENCE {
    netIndex                Integer32,
    netName                 DisplayString,
    netUtilizationValue     Percent,
    netWarningThreshold     Integer32,
    netWarningInterval      Integer32,
    netCriticalThreshold    Integer32,
    netCriticalInterval     Integer32,
    netNotificationType     NotificationType,
    netCurrentState         ThresholdType,
    netPreviousState        ThresholdType,
    netLastChangeTime       DateAndTime
}

netIndex OBJECT-TYPE
    SYNTAX          Integer32 (1..65535)
    MAX-ACCESS      read-only
    STATUS          deprecated
    DESCRIPTION     "Internal type for Blue Coat Director use only."
    ::= { netEntry 1 }

netName OBJECT-TYPE
    SYNTAX          DisplayString
    MAX-ACCESS      read-only
    STATUS          deprecated
    DESCRIPTION     "Internal type for Blue Coat Director use only."
    ::= { netEntry 2 }

netUtilizationValue OBJECT-TYPE
    SYNTAX          Percent
    MAX-ACCESS      read-only
    STATUS          deprecated
    DESCRIPTION     "Internal type for Blue Coat Director use only."
    ::= { netEntry 3 }

netWarningThreshold OBJECT-TYPE
    SYNTAX          Integer32 (0..100)
    MAX-ACCESS      read-write
    STATUS          deprecated
    DESCRIPTION     "Internal type for Blue Coat Director use only."
    ::= { netEntry 4 }

netWarningInterval OBJECT-TYPE
    SYNTAX          Integer32 (0..86400)
    UNITS           "Seconds"
    MAX-ACCESS      read-write
    STATUS          deprecated
    DESCRIPTION     "Internal type for Blue Coat Director use only."
    ::= { netEntry 5 }

netCriticalThreshold OBJECT-TYPE
    SYNTAX          Integer32 (0..100)
    MAX-ACCESS      read-write
    STATUS          deprecated
    DESCRIPTION     "Internal type for Blue Coat Director use only."
    ::= { netEntry 6 }

netCriticalInterval OBJECT-TYPE
    SYNTAX          Integer32 (0..86400)
    UNITS           "Seconds"
    MAX-ACCESS      read-write
    STATUS          deprecated
    DESCRIPTION     "Internal type for Blue Coat Director use only."
    ::= { netEntry 7 }

netNotificationType OBJECT-TYPE
    SYNTAX          NotificationType
    MAX-ACCESS      read-write
    STATUS          deprecated
    DESCRIPTION     "Internal type for Blue Coat Director use only."
    DEFVAL { 3 }
    ::= { netEntry 8 }

netCurrentState OBJECT-TYPE
    SYNTAX          ThresholdType
    MAX-ACCESS      read-only
    STATUS          deprecated
    DESCRIPTION     "Internal type for Blue Coat Director use only."
    ::=  { netEntry 9 }

netPreviousState OBJECT-TYPE
    SYNTAX          ThresholdType
    MAX-ACCESS      read-only
    STATUS          deprecated
    DESCRIPTION     "Internal type for Blue Coat Director use only."
    ::=  { netEntry 10 }

netLastChangeTime OBJECT-TYPE
    SYNTAX          DateAndTime
    MAX-ACCESS      read-only
    STATUS          deprecated
    DESCRIPTION     "Internal type for Blue Coat Director use only."
    ::= { netEntry 11 }

netEvent OBJECT-IDENTITY
    STATUS          deprecated
    DESCRIPTION     "Internal object for Blue Coat Director use only."
    ::= { network 2 }

netTrap  NOTIFICATION-TYPE
    OBJECTS  {
        netName,
        netUtilizationValue,
        netCurrentState,
        netPreviousState,
        netLastChangeTime,
        bchrSerial
    }
    STATUS          deprecated
    DESCRIPTION     "Internal trap type for Blue Coat Director use only."
    ::= { netEvent 1 }

    
--
-- License Utilization Group
--

licUtilTable OBJECT-TYPE
    SYNTAX		    SEQUENCE OF LicUtilEntry 
    MAX-ACCESS	    not-accessible
    STATUS		    deprecated
    DESCRIPTION     "Internal type for Blue Coat Director use only."
    ::= { licenseUtilization 1 }

licUtilEntry OBJECT-TYPE
    SYNTAX		  LicUtilEntry 
    MAX-ACCESS	  not-accessible
    STATUS		  deprecated
    DESCRIPTION   "Internal type for Blue Coat Director use only."
    INDEX	 { licUtilIndex }
    ::= { licUtilTable 1 }

LicUtilEntry ::= SEQUENCE {
    licUtilIndex                Integer32,
    licUtilName 				DisplayString,
    licUtilValue 			    Percent,
    licUtilWarningThreshold 	Integer32,
    licUtilWarningInterval 	    Integer32,
    licUtilCriticalThreshold 	Integer32,
    licUtilCriticalInterval 	Integer32,
    licUtilNotificationType     NotificationType,
    licUtilCurrentState         ThresholdType,
    licUtilPreviousState        ThresholdType,
    licUtilLastChangeTime       DateAndTime
}

licUtilIndex OBJECT-TYPE
    SYNTAX          Integer32 (1..65535)
    MAX-ACCESS      read-only
    STATUS          deprecated
    DESCRIPTION     "Internal type for Blue Coat Director use only."
    ::= { licUtilEntry 1 }

licUtilName OBJECT-TYPE
    SYNTAX          DisplayString
    MAX-ACCESS      read-only
    STATUS          deprecated
    DESCRIPTION     "Internal type for Blue Coat Director use only."
    ::= { licUtilEntry 2 }

licUtilValue OBJECT-TYPE
    SYNTAX          Percent
    MAX-ACCESS      read-only
    STATUS          deprecated
    DESCRIPTION     "Internal type for Blue Coat Director use only."
    ::= { licUtilEntry 3 }

licUtilWarningThreshold OBJECT-TYPE
    SYNTAX          Integer32 (0..100)
    MAX-ACCESS      read-write
    STATUS          deprecated
    DESCRIPTION     "Internal type for Blue Coat Director use only."
    ::= { licUtilEntry 4 }

licUtilWarningInterval OBJECT-TYPE
    SYNTAX          Integer32 (0..86400)
    UNITS           "Seconds"
    MAX-ACCESS      read-write
    STATUS          deprecated
    DESCRIPTION     "Internal type for Blue Coat Director use only."
    ::= { licUtilEntry 5 }

licUtilCriticalThreshold OBJECT-TYPE
    SYNTAX          Integer32 (0..100)
    MAX-ACCESS      read-write
    STATUS          deprecated
    DESCRIPTION     "Internal type for Blue Coat Director use only."
    ::= { licUtilEntry 6 }

licUtilCriticalInterval OBJECT-TYPE
    SYNTAX          Integer32 (0..86400)
    UNITS           "Seconds"
    MAX-ACCESS      read-write
    STATUS          deprecated
    DESCRIPTION     "Internal type for Blue Coat Director use only."
    ::= { licUtilEntry 7 }

licUtilNotificationType OBJECT-TYPE
    SYNTAX          NotificationType
    MAX-ACCESS      read-write
    STATUS          deprecated
    DESCRIPTION     "Internal type for Blue Coat Director use only."
    DEFVAL { 3 }
    ::= { licUtilEntry 8 }

licUtilCurrentState OBJECT-TYPE
    SYNTAX          ThresholdType
    MAX-ACCESS      read-only
    STATUS          deprecated
    DESCRIPTION     "Internal type for Blue Coat Director use only."
    ::= { licUtilEntry 9 }

licUtilPreviousState OBJECT-TYPE
    SYNTAX          ThresholdType
    MAX-ACCESS      read-only
    STATUS          deprecated
    DESCRIPTION     "Internal type for Blue Coat Director use only."
    ::= { licUtilEntry 10 }

licUtilLastChangeTime OBJECT-TYPE
    SYNTAX          DateAndTime
    MAX-ACCESS      read-only
    STATUS          deprecated
    DESCRIPTION     "Internal type for Blue Coat Director use only."
    ::= { licUtilEntry 11 }

licUtilEvent OBJECT-IDENTITY
    STATUS          deprecated
    DESCRIPTION     "Internal object for Blue Coat Director use only."
    ::= { licenseUtilization 2 }

licUtilTrap NOTIFICATION-TYPE
    OBJECTS  {
        licUtilName,
        licUtilValue,
        licUtilCurrentState,
        licUtilPreviousState,
        licUtilLastChangeTime,
        bchrSerial
    }
    STATUS          deprecated
    DESCRIPTION     "Internal trap type for Blue Coat Director use only."
    ::= { licUtilEvent 1 }


--
-- License Expiry Group
--

licExpTable OBJECT-TYPE
	SYNTAX		    SEQUENCE OF LicExpEntry 
	MAX-ACCESS	    not-accessible
	STATUS		    deprecated
    DESCRIPTION     "Internal type for Blue Coat Director use only."
	::= { licenseExpiration 1 }

licExpEntry OBJECT-TYPE
	SYNTAX		    LicExpEntry
	MAX-ACCESS	    not-accessible
	STATUS		    deprecated
    DESCRIPTION     "Internal type for Blue Coat Director use only."
	INDEX { licExpIndex }
	::= { licExpTable 1 }

LicExpEntry ::= SEQUENCE {
        licExpIndex             Integer32,
        licExpName 			    DisplayString,
        licExpValue 		    Percent,
        licExpStatus            INTEGER,
        licExpWarningThreshold  Integer32,
        licExpCriticalThreshold Integer32,
        licExpNotificationType  NotificationType,
        licExpCurrentState      ThresholdType,
        licExpPreviousState     ThresholdType,
        licExpLastChangeTime    DateAndTime
	}

licExpIndex OBJECT-TYPE
    SYNTAX          Integer32 (1..65535)
    MAX-ACCESS      read-only
    STATUS          deprecated
    DESCRIPTION     "Internal type for Blue Coat Director use only."
    ::= { licExpEntry 1 }

licExpName OBJECT-TYPE
    SYNTAX          DisplayString
    MAX-ACCESS      read-only
    STATUS          deprecated
    DESCRIPTION     "Internal type for Blue Coat Director use only."
    ::= { licExpEntry 2 }

licExpValue OBJECT-TYPE
    SYNTAX          INTEGER (0..2147483647)
    MAX-ACCESS      read-only
    STATUS          deprecated
    DESCRIPTION     "Internal type for Blue Coat Director use only."
    ::= { licExpEntry 3 }

licExpStatus OBJECT-TYPE
    SYNTAX          INTEGER {
       not-licensed(0),
       valid(1),
       expired(2)
    }
    MAX-ACCESS      read-only
    STATUS          deprecated
    DESCRIPTION     "Internal type for Blue Coat Director use only."
    ::= { licExpEntry 4 }

licExpWarningThreshold OBJECT-TYPE
    SYNTAX          Integer32 (0..100)
    MAX-ACCESS      read-write
    STATUS          deprecated
    DESCRIPTION     "Internal type for Blue Coat Director use only."
    ::= { licExpEntry 5 }

licExpCriticalThreshold OBJECT-TYPE
    SYNTAX          Integer32 (0..100)
    MAX-ACCESS      read-write
    STATUS          deprecated
    DESCRIPTION     "Internal type for Blue Coat Director use only."
    ::= { licExpEntry 6 }

licExpNotificationType OBJECT-TYPE
    SYNTAX          NotificationType
    MAX-ACCESS      read-write
    STATUS          deprecated
    DESCRIPTION     "Internal type for Blue Coat Director use only."
    DEFVAL { 3 }
    ::= { licExpEntry 7 }

licExpCurrentState OBJECT-TYPE
    SYNTAX          ThresholdType
    MAX-ACCESS      read-only
    STATUS          deprecated
    DESCRIPTION     "Internal type for Blue Coat Director use only."
    ::= { licExpEntry 8 }

licExpPreviousState OBJECT-TYPE
    SYNTAX          ThresholdType
    MAX-ACCESS      read-only
    STATUS          deprecated
    DESCRIPTION     "Internal type for Blue Coat Director use only."
    ::= { licExpEntry 9 }

licExpLastChangeTime OBJECT-TYPE
    SYNTAX          DateAndTime
    MAX-ACCESS      read-only
    STATUS          deprecated
    DESCRIPTION     "Internal type for Blue Coat Director use only."
    ::= { licExpEntry 10 }     

licExpEvent OBJECT-IDENTITY
    STATUS          deprecated
    DESCRIPTION     "Internal object for Blue Coat Director use only."
    ::= { licenseExpiration 2 }

licExpTrap NOTIFICATION-TYPE
    OBJECTS  {
        licExpName,
        licExpValue,
        licExpCurrentState,
        licExpPreviousState,
        licExpLastChangeTime,
        bchrSerial
    }
    STATUS          deprecated
    DESCRIPTION     "Internal trap type for Blue Coat Director use only."
    ::= { licExpEvent 1 }


END
