--
-- OPTIX-HK-RMON-MIB.mib
-- MIB generated by MG-SOFT Visual MIB Builder Version 3.0 Build 253
-- Thursday, June 29, 2006 at 15:03:41
--

--  -------------------------------------------------------------------------
-- Copyright (c) 2000-2010, Huawei Tech. Co., Ltd.
-- File name:   optixSonet.mib
-- Author:      Qinkun You,Shenghong Yu
-- Version:     V1.00
-- Date:        2004/01/05
-- Description: This MIB describes the Alarm,Performance and Event interface of
--              Huawei SONET transmit platform
-- Note:        Please complie OPTIX-GLOBAL-REGISTRY and OPTIX-TC MIB before 
--              compile this MIB.
-- History:  
-- -------------------------------------------------------------------------

	OPTIX-HK-RMON-MIB DEFINITIONS ::= BEGIN
 
		IMPORTS
			optixCommon			
				FROM OPTIX-OID-MIB			
			OBJECT-GROUP, MODULE-COMPLIANCE			
				FROM SNMPv2-CONF			
			mib-2, Integer32, Counter64, OBJECT-TYPE, MODULE-IDENTITY			
				FROM SNMPv2-SMI;
	
	
--  -------------------------------------------------------------------------
-- Module Identity
-- -------------------------------------------------------------------------
		optixHKRmonMib MODULE-IDENTITY 
			LAST-UPDATED "200412010000Z"		-- December 01, 2004 at 00:00 GMT
			ORGANIZATION 
				"Huawei Optix OSP Working Group"
			CONTACT-INFO 
				"OSP Working Group
				Optical NetWork Department
				Huawei Tech. Co., Ltd.
				Longgang District
				Shenzhen City
				China 518029
				Tel:86-755-28780808."
			DESCRIPTION 
				"This module describes the private Rmon 
				statics of Huawei transmit platform."
			::= { optixCommon 30 }
		
	
	
--
-- Node definitions
--
	
--  -------------------------------------------------------------------------
-- This module icludes following nodes
-- -------------------------------------------------------------------------
		-- 1.3.6.1.4.1.2011.2.25.10.30.10
		statistics OBJECT IDENTIFIER ::= { optixHKRmonMib 10 }
		
		-- 1.3.6.1.4.1.2011.2.25.10.30.10.1
		etherStatsTable OBJECT-TYPE
			SYNTAX SEQUENCE OF EtherStatsEntry
			MAX-ACCESS not-accessible
			STATUS deprecated
			DESCRIPTION
				"A list of Ethernet statistics entries."
			::= { statistics 1 }
		
		-- 1.3.6.1.4.1.2011.2.25.10.30.10.1.1
		etherStatsEntry OBJECT-TYPE
			SYNTAX EtherStatsEntry
			MAX-ACCESS not-accessible
			STATUS current
			DESCRIPTION
				"A collection of statistics kept for a particular
				Ethernet interface.  As an example, an instance of the
				etherStatsPkts object might be named etherStatsPkts.1"
			INDEX { etherStatsIndex }
			::= { etherStatsTable 1 }
		
		EtherStatsEntry ::=
			SEQUENCE { 
				etherStatsIndex
					Integer32,
				etherStatsDropEvents
					Counter64,
				etherStatsOctets
					Counter64,
				etherStatsPkts
					Counter64,
				etherStatsBroadcastPkts
					Counter64,
				etherStatsMulticastPkts
					Counter64,
				etherStatsCRCAlignErrors
					Counter64,
				etherStatsUndersizePkts
					Counter64,
				etherStatsOversizePkts
					Counter64,
				etherStatsFragments
					Counter64,
				etherStatsJabbers
					Counter64,
				etherStatsCollisions
					Counter64,
				etherStatsPkts64Octets
					Counter64,
				etherStatsPkts65to127Octets
					Counter64,
				etherStatsPkts128to255Octets
					Counter64,
				etherStatsPkts256to511Octets
					Counter64,
				etherStatsPkts512to1023Octets
					Counter64,
				etherStatsPkts1024to1518Octets
					Counter64,
				etherStatsPkts1519toMtuOctets
					Counter64,
				etherStatsTranPkts64Octets
					Counter64,
				etherStatsTranPkts65to127Octets
					Counter64,
				etherStatsTranPkts128to255Octets
					Counter64,
				etherStatsTranPkts256to511Octets
					Counter64,
				etherStatsTranPkts512to1023Octets
					Counter64,
				etherStatsTranPkts1024to1518Octets
					Counter64,
				etherStatsTranPkts1519toMtuOctets
					Counter64,
				etherStatsRxTxPkts64Octets
					Counter64,
				etherStatsRxTxPkts65to127Octets
					Counter64,
				etherStatsRxTxPkts128to255Octets
					Counter64,
				etherStatsRxTxPkts256to511Octets
					Counter64,
				etherStatsRxTxPkts512to1023Octets
					Counter64,
				etherStatsRxTxPkts1024to1518Octets
					Counter64,
				etherStatsRxTxPkts1519toMtuOctets
					Counter64,
				etherStatsInUcastPkts
					Counter64,
				etherStatsOutUcastPkts
					Counter64,
				etherStatsInPauseFrames
					Counter64,
				etherStatsOutPauseFrames
					Counter64,
				etherStatsOutMulticastPkts
					Counter64,
				etherStatsOutBroadcastPkts
					Counter64,
				etherStatsInGoodOctets
					Counter64,
				etherStatsOutGoodOctets
					Counter64,
				etherStatsInBadOctets
					Counter64,
				etherStatsOutBadOctets
					Counter64,
				etherStatsAlignmentErrors
					Counter64,
				etherStatsFCSErrors
					Counter64,
				etherStatsSingleCollisionFrames
					Counter64,
				etherStatsMultipleCollisionFrames
					Counter64,
				etherStatsLateCollisions
					Counter64,
				etherStatsExcessiveCollisions
					Counter64,
				etherStatsDeferredTransmissions
					Counter64,
				etherStatsCarrierSenseErrors
					Counter64,
				etherStatsInControlFrames
					Counter64,
				etherStatsOutControlFrames
					Counter64,
				etherStatsOutDropEvents
					Counter64,
				etherStatsOutOversizePkts
					Counter64,
				etherStatsOutPkts
					Counter64,
				etherStatsOutOctets
					Counter64,
				etherStatsRxFullGoodOcetcs
					Counter64,
				etherStatsTxFullGoodOctecs
					Counter64
			 }

		-- 1.3.6.1.4.1.2011.2.25.10.30.10.1.1.1
		etherStatsIndex OBJECT-TYPE
			SYNTAX Integer32 (1..65535)
			MAX-ACCESS read-only
			STATUS current
			DESCRIPTION
				"The value of this object uniquely identifies this
				etherStats entry."
			::= { etherStatsEntry 1 }
		
		-- 1.3.6.1.4.1.2011.2.25.10.30.10.1.1.3
		etherStatsDropEvents OBJECT-TYPE
			SYNTAX Counter64
			MAX-ACCESS read-only
			STATUS current
			DESCRIPTION
				"The total number of events in which packets
				were dropped by the probe due to lack of resources.
				Note that this number is not necessarily the number of
				packets dropped; it is just the number of times this
				condition has been detected."
			::= { etherStatsEntry 3 }
		
		-- 1.3.6.1.4.1.2011.2.25.10.30.10.1.1.4
		etherStatsOctets OBJECT-TYPE
			SYNTAX Counter64
			UNITS "Octets"
			MAX-ACCESS read-only
			STATUS current
			DESCRIPTION
				"The total number of octets of data (including
				those in bad packets) received on the
				network (excluding framing bits but including
				FCS octets).
				This object can be used as a reasonable estimate of
				10-Megabit ethernet utilization.  If greater precision is
				desired, the etherStatsPkts and etherStatsOctets objects
				should be sampled before and after a common interval.  The
				differences in the sampled values are Pkts and Octets,
				respectively, and the number of seconds in the interval is
				Interval.  These values are used to calculate the Utilization
				as follows:
				
				                 Pkts * (9.6 + 6.4) + (Octets * .8)
				 Utilization = -------------------------------------
				                         Interval * 10,000
				
				The result of this equation is the value Utilization which
				is the percent utilization of the ethernet segment on a
				scale of 0 to 100 percent."
			::= { etherStatsEntry 4 }
		
		-- 1.3.6.1.4.1.2011.2.25.10.30.10.1.1.5
		etherStatsPkts OBJECT-TYPE
			SYNTAX Counter64
			UNITS "Packets"
			MAX-ACCESS read-only
			STATUS current
			DESCRIPTION
				"The total number of packets (including bad packets,
				broadcast packets, and multicast packets) received."
			::= { etherStatsEntry 5 }
		
		-- 1.3.6.1.4.1.2011.2.25.10.30.10.1.1.6
		etherStatsBroadcastPkts OBJECT-TYPE
			SYNTAX Counter64
			UNITS "Packets"
			MAX-ACCESS read-only
			STATUS current
			DESCRIPTION
				"The total number of good packets received that were
				directed to the broadcast address.  Note that this
				does not include multicast packets."
			::= { etherStatsEntry 6 }
		
		-- 1.3.6.1.4.1.2011.2.25.10.30.10.1.1.7
		etherStatsMulticastPkts OBJECT-TYPE
			SYNTAX Counter64
			UNITS "Packets"
			MAX-ACCESS read-only
			STATUS current
			DESCRIPTION
				"The total number of good packets received that were
				directed to a multicast address.  Note that this number
				does not include packets directed to the broadcast
				address."
			::= { etherStatsEntry 7 }
		
		-- 1.3.6.1.4.1.2011.2.25.10.30.10.1.1.8
		etherStatsCRCAlignErrors OBJECT-TYPE
			SYNTAX Counter64
			UNITS "Packets"
			MAX-ACCESS read-only
			STATUS current
			DESCRIPTION
				"The total number of packets received that
				had a length (excluding framing bits, but
				including FCS octets) of between 64 and 1518
				octets, inclusive, but had either a bad
				Frame Check Sequence (FCS) with an integral
				number of octets (FCS Error) or a bad FCS with
				a non-integral number of octets (Alignment Error)."
			::= { etherStatsEntry 8 }
		
		-- 1.3.6.1.4.1.2011.2.25.10.30.10.1.1.9
		etherStatsUndersizePkts OBJECT-TYPE
			SYNTAX Counter64
			UNITS "Packets"
			MAX-ACCESS read-only
			STATUS current
			DESCRIPTION
				"The total number of packets received that were
				less than 64 octets long (excluding framing bits,
				but including FCS octets) and were otherwise well
				formed."
			::= { etherStatsEntry 9 }
		
		-- 1.3.6.1.4.1.2011.2.25.10.30.10.1.1.10
		etherStatsOversizePkts OBJECT-TYPE
			SYNTAX Counter64
			UNITS "Packets"
			MAX-ACCESS read-only
			STATUS current
			DESCRIPTION
				"The total number of packets received that were
				longer than 1518 octets (excluding framing bits,
				but including FCS octets) and were otherwise
				well formed."
			::= { etherStatsEntry 10 }
		
		-- 1.3.6.1.4.1.2011.2.25.10.30.10.1.1.11
		etherStatsFragments OBJECT-TYPE
			SYNTAX Counter64
			UNITS "Packets"
			MAX-ACCESS read-only
			STATUS current
			DESCRIPTION
				"The total number of packets received that were less than
				64 octets in length (excluding framing bits but including
				FCS octets) and had either a bad Frame Check Sequence
				(FCS) with an integral number of octets (FCS Error) or a
				bad FCS with a non-integral number of octets (Alignment
				Error).
				
				Note that it is entirely normal for etherStatsFragments to
				increment.  This is because it counts both runts (which are
				normal occurrences due to collisions) and noise hits."
			::= { etherStatsEntry 11 }
		
		-- 1.3.6.1.4.1.2011.2.25.10.30.10.1.1.12
		etherStatsJabbers OBJECT-TYPE
			SYNTAX Counter64
			UNITS "Packets"
			MAX-ACCESS read-only
			STATUS current
			DESCRIPTION
				"The total number of packets received that were
				longer than 1518 octets (excluding framing bits,
				but including FCS octets), and had either a bad
				Frame Check Sequence (FCS) with an integral number
				of octets (FCS Error) or a bad FCS with a non-integral
				number of octets (Alignment Error).
				
				Note that this definition of jabber is different
				than the definition in IEEE-802.3 section 8.2.1.5
				(10BASE5) and section 10.3.1.4 (10BASE2).  These
				documents define jabber as the condition where any
				packet exceeds 20 ms.  The allowed range to detect
				jabber is between 20 ms and 150 ms."
			::= { etherStatsEntry 12 }
		
		-- 1.3.6.1.4.1.2011.2.25.10.30.10.1.1.13
		etherStatsCollisions OBJECT-TYPE
			SYNTAX Counter64
			UNITS "Collisions"
			MAX-ACCESS read-only
			STATUS current
			DESCRIPTION
				"The best estimate of the total number of collisions
				on this Ethernet segment.
				
				The value returned will depend on the location of the
				RMON probe. Section 8.2.1.3 (10BASE-5) and section
				10.3.1.3 (10BASE-2) of IEEE standard 802.3 states that a
				station must detect a collision, in the receive mode, if
				three or more stations are transmitting simultaneously.  A
				repeater port must detect a collision when two or more
				stations are transmitting simultaneously.  Thus a probe
				placed on a repeater port could record more collisions
				than a probe connected to a station on the same segment
				would.
				
				Probe location plays a much smaller role when considering
				10BASE-T.  14.2.1.4 (10BASE-T) of IEEE standard 802.3
				defines a collision as the simultaneous presence of signals
				on the DO and RD circuits (transmitting and receiving
				at the same time).  A 10BASE-T station can only detect
				collisions when it is transmitting.  Thus probes placed on
				a station and a repeater, should report the same number of
				collisions.
				
				Note also that an RMON probe inside a repeater should
				ideally report collisions between the repeater and one or
				more other hosts (transmit collisions as defined by IEEE
				802.3k) plus receiver collisions observed on any coax
				segments to which the repeater is connected."
			::= { etherStatsEntry 13 }
		
		-- 1.3.6.1.4.1.2011.2.25.10.30.10.1.1.14
		etherStatsPkts64Octets OBJECT-TYPE
			SYNTAX Counter64
			UNITS "Packets"
			MAX-ACCESS read-only
			STATUS current
			DESCRIPTION
				"The total number of packets (including bad
				packets) received that were 64 octets in length
				(excluding framing bits but including FCS octets)."
			::= { etherStatsEntry 14 }
		
		-- 1.3.6.1.4.1.2011.2.25.10.30.10.1.1.15
		etherStatsPkts65to127Octets OBJECT-TYPE
			SYNTAX Counter64
			UNITS "Packets"
			MAX-ACCESS read-only
			STATUS current
			DESCRIPTION
				"The total number of packets (including bad
				packets) received that were between
				65 and 127 octets in length inclusive
				(excluding framing bits but including FCS octets)."
			::= { etherStatsEntry 15 }
		
		-- 1.3.6.1.4.1.2011.2.25.10.30.10.1.1.16
		etherStatsPkts128to255Octets OBJECT-TYPE
			SYNTAX Counter64
			UNITS "Packets"
			MAX-ACCESS read-only
			STATUS current
			DESCRIPTION
				"The total number of packets (including bad
				packets) received that were between
				128 and 255 octets in length inclusive
				(excluding framing bits but including FCS octets)."
			::= { etherStatsEntry 16 }
		
		-- 1.3.6.1.4.1.2011.2.25.10.30.10.1.1.17
		etherStatsPkts256to511Octets OBJECT-TYPE
			SYNTAX Counter64
			UNITS "Packets"
			MAX-ACCESS read-only
			STATUS current
			DESCRIPTION
				"The total number of packets (including bad
				packets) received that were between
				256 and 511 octets in length inclusive
				(excluding framing bits but including FCS octets)."
			::= { etherStatsEntry 17 }
		
		-- 1.3.6.1.4.1.2011.2.25.10.30.10.1.1.18
		etherStatsPkts512to1023Octets OBJECT-TYPE
			SYNTAX Counter64
			UNITS "Packets"
			MAX-ACCESS read-only
			STATUS current
			DESCRIPTION
				"The total number of packets (including bad
				packets) received that were between
				512 and 1023 octets in length inclusive
				(excluding framing bits but including FCS octets)."
			::= { etherStatsEntry 18 }
		
		-- 1.3.6.1.4.1.2011.2.25.10.30.10.1.1.19
		etherStatsPkts1024to1518Octets OBJECT-TYPE
			SYNTAX Counter64
			UNITS "Packets"
			MAX-ACCESS read-only
			STATUS current
			DESCRIPTION
				"The total number of packets (including bad
				packets) received that were between
				1024 and 1518 octets in length inclusive
				(excluding framing bits but including FCS octets)."
			::= { etherStatsEntry 19 }
		
		-- 1.3.6.1.4.1.2011.2.25.10.30.10.1.1.22
		etherStatsPkts1519toMtuOctets OBJECT-TYPE
			SYNTAX Counter64
			UNITS "Packets"
			MAX-ACCESS read-only
			STATUS current
			DESCRIPTION
				" "
			::= { etherStatsEntry 22 }
		
		-- 1.3.6.1.4.1.2011.2.25.10.30.10.1.1.23
		etherStatsTranPkts64Octets OBJECT-TYPE
			SYNTAX Counter64
			UNITS "Packets"
			MAX-ACCESS read-only
			STATUS current
			DESCRIPTION
				" "
			::= { etherStatsEntry 23 }
		
		-- 1.3.6.1.4.1.2011.2.25.10.30.10.1.1.24
		etherStatsTranPkts65to127Octets OBJECT-TYPE
			SYNTAX Counter64
			UNITS "Packets"
			MAX-ACCESS read-only
			STATUS current
			DESCRIPTION
				" "
			::= { etherStatsEntry 24 }
		
		-- 1.3.6.1.4.1.2011.2.25.10.30.10.1.1.25
		etherStatsTranPkts128to255Octets OBJECT-TYPE
			SYNTAX Counter64
			UNITS "Packets"
			MAX-ACCESS read-only
			STATUS current
			DESCRIPTION
				" "
			::= { etherStatsEntry 25 }
		
		-- 1.3.6.1.4.1.2011.2.25.10.30.10.1.1.26
		etherStatsTranPkts256to511Octets OBJECT-TYPE
			SYNTAX Counter64
			UNITS "Packets"
			MAX-ACCESS read-only
			STATUS current
			DESCRIPTION
				" "
			::= { etherStatsEntry 26 }
		
		-- 1.3.6.1.4.1.2011.2.25.10.30.10.1.1.27
		etherStatsTranPkts512to1023Octets OBJECT-TYPE
			SYNTAX Counter64
			UNITS "Packets"
			MAX-ACCESS read-only
			STATUS current
			DESCRIPTION
				" "
			::= { etherStatsEntry 27 }
		
		-- 1.3.6.1.4.1.2011.2.25.10.30.10.1.1.28
		etherStatsTranPkts1024to1518Octets OBJECT-TYPE
			SYNTAX Counter64
			UNITS "Packets"
			MAX-ACCESS read-only
			STATUS current
			DESCRIPTION
				" "
			::= { etherStatsEntry 28 }
		
		-- 1.3.6.1.4.1.2011.2.25.10.30.10.1.1.29
		etherStatsTranPkts1519toMtuOctets OBJECT-TYPE
			SYNTAX Counter64
			UNITS "Packets"
			MAX-ACCESS read-only
			STATUS current
			DESCRIPTION
				" "
			::= { etherStatsEntry 29 }
		
		-- 1.3.6.1.4.1.2011.2.25.10.30.10.1.1.30
		etherStatsRxTxPkts64Octets OBJECT-TYPE
			SYNTAX Counter64
			UNITS "Packets"
			MAX-ACCESS read-only
			STATUS current
			DESCRIPTION
				" "
			::= { etherStatsEntry 30 }
		
		-- 1.3.6.1.4.1.2011.2.25.10.30.10.1.1.31
		etherStatsRxTxPkts65to127Octets OBJECT-TYPE
			SYNTAX Counter64
			UNITS "Packets"
			MAX-ACCESS read-only
			STATUS current
			DESCRIPTION
				" "
			::= { etherStatsEntry 31 }
		
		-- 1.3.6.1.4.1.2011.2.25.10.30.10.1.1.32
		etherStatsRxTxPkts128to255Octets OBJECT-TYPE
			SYNTAX Counter64
			UNITS "Packets"
			MAX-ACCESS read-only
			STATUS current
			DESCRIPTION
				" "
			::= { etherStatsEntry 32 }
		
		-- 1.3.6.1.4.1.2011.2.25.10.30.10.1.1.33
		etherStatsRxTxPkts256to511Octets OBJECT-TYPE
			SYNTAX Counter64
			UNITS "Packets"
			MAX-ACCESS read-only
			STATUS current
			DESCRIPTION
				" "
			::= { etherStatsEntry 33 }
		
		-- 1.3.6.1.4.1.2011.2.25.10.30.10.1.1.34
		etherStatsRxTxPkts512to1023Octets OBJECT-TYPE
			SYNTAX Counter64
			UNITS "Packets"
			MAX-ACCESS read-only
			STATUS current
			DESCRIPTION
				" "
			::= { etherStatsEntry 34 }
		
		-- 1.3.6.1.4.1.2011.2.25.10.30.10.1.1.35
		etherStatsRxTxPkts1024to1518Octets OBJECT-TYPE
			SYNTAX Counter64
			UNITS "Packets"
			MAX-ACCESS read-only
			STATUS current
			DESCRIPTION
				" "
			::= { etherStatsEntry 35 }
		
		-- 1.3.6.1.4.1.2011.2.25.10.30.10.1.1.36
		etherStatsRxTxPkts1519toMtuOctets OBJECT-TYPE
			SYNTAX Counter64
			UNITS "Packets"
			MAX-ACCESS read-only
			STATUS current
			DESCRIPTION
				" "
			::= { etherStatsEntry 36 }
		
		-- 1.3.6.1.4.1.2011.2.25.10.30.10.1.1.37
		etherStatsInUcastPkts OBJECT-TYPE
			SYNTAX Counter64
			UNITS "Packets"
			MAX-ACCESS read-only
			STATUS current
			DESCRIPTION
				" "
			::= { etherStatsEntry 37 }
		
		-- 1.3.6.1.4.1.2011.2.25.10.30.10.1.1.38
		etherStatsOutUcastPkts OBJECT-TYPE
			SYNTAX Counter64
			UNITS "Packets"
			MAX-ACCESS read-only
			STATUS current
			DESCRIPTION
				" "
			::= { etherStatsEntry 38 }
		
		-- 1.3.6.1.4.1.2011.2.25.10.30.10.1.1.39
		etherStatsInPauseFrames OBJECT-TYPE
			SYNTAX Counter64
			UNITS "Frames"
			MAX-ACCESS read-only
			STATUS current
			DESCRIPTION
				" "
			::= { etherStatsEntry 39 }
		
		-- 1.3.6.1.4.1.2011.2.25.10.30.10.1.1.40
		etherStatsOutPauseFrames OBJECT-TYPE
			SYNTAX Counter64
			UNITS "Frames"
			MAX-ACCESS read-only
			STATUS current
			DESCRIPTION
				" "
			::= { etherStatsEntry 40 }
		
		-- 1.3.6.1.4.1.2011.2.25.10.30.10.1.1.41
		etherStatsOutMulticastPkts OBJECT-TYPE
			SYNTAX Counter64
			UNITS "Packets"
			MAX-ACCESS read-only
			STATUS current
			DESCRIPTION
				" "
			::= { etherStatsEntry 41 }
		
		-- 1.3.6.1.4.1.2011.2.25.10.30.10.1.1.42
		etherStatsOutBroadcastPkts OBJECT-TYPE
			SYNTAX Counter64
			UNITS "Packets"
			MAX-ACCESS read-only
			STATUS current
			DESCRIPTION
				" "
			::= { etherStatsEntry 42 }
		
		-- 1.3.6.1.4.1.2011.2.25.10.30.10.1.1.43
		etherStatsInGoodOctets OBJECT-TYPE
			SYNTAX Counter64
			UNITS "Octets"
			MAX-ACCESS read-only
			STATUS current
			DESCRIPTION
				" "
			::= { etherStatsEntry 43 }
		
		-- 1.3.6.1.4.1.2011.2.25.10.30.10.1.1.44
		etherStatsOutGoodOctets OBJECT-TYPE
			SYNTAX Counter64
			UNITS "Octets"
			MAX-ACCESS read-only
			STATUS current
			DESCRIPTION
				" "
			::= { etherStatsEntry 44 }
		
		-- 1.3.6.1.4.1.2011.2.25.10.30.10.1.1.45
		etherStatsInBadOctets OBJECT-TYPE
			SYNTAX Counter64
			UNITS "Octets"
			MAX-ACCESS read-only
			STATUS current
			DESCRIPTION
				" "
			::= { etherStatsEntry 45 }
		
		-- 1.3.6.1.4.1.2011.2.25.10.30.10.1.1.46
		etherStatsOutBadOctets OBJECT-TYPE
			SYNTAX Counter64
			UNITS "Octets"
			MAX-ACCESS read-only
			STATUS current
			DESCRIPTION
				" "
			::= { etherStatsEntry 46 }
		
		-- 1.3.6.1.4.1.2011.2.25.10.30.10.1.1.47
		etherStatsAlignmentErrors OBJECT-TYPE
			SYNTAX Counter64
			UNITS "Frames"
			MAX-ACCESS read-only
			STATUS current
			DESCRIPTION
				" "
			::= { etherStatsEntry 47 }
		
		-- 1.3.6.1.4.1.2011.2.25.10.30.10.1.1.48
		etherStatsFCSErrors OBJECT-TYPE
			SYNTAX Counter64
			UNITS "Frames"
			MAX-ACCESS read-only
			STATUS current
			DESCRIPTION
				" "
			::= { etherStatsEntry 48 }
		
		-- 1.3.6.1.4.1.2011.2.25.10.30.10.1.1.49
		etherStatsSingleCollisionFrames OBJECT-TYPE
			SYNTAX Counter64
			UNITS "Frames"
			MAX-ACCESS read-only
			STATUS current
			DESCRIPTION
				" "
			::= { etherStatsEntry 49 }
		
		-- 1.3.6.1.4.1.2011.2.25.10.30.10.1.1.50
		etherStatsMultipleCollisionFrames OBJECT-TYPE
			SYNTAX Counter64
			UNITS "Frames"
			MAX-ACCESS read-only
			STATUS current
			DESCRIPTION
				" "
			::= { etherStatsEntry 50 }
		
		-- 1.3.6.1.4.1.2011.2.25.10.30.10.1.1.51
		etherStatsLateCollisions OBJECT-TYPE
			SYNTAX Counter64
			UNITS "Times"
			MAX-ACCESS read-only
			STATUS current
			DESCRIPTION
				" "
			::= { etherStatsEntry 51 }
		
		-- 1.3.6.1.4.1.2011.2.25.10.30.10.1.1.52
		etherStatsExcessiveCollisions OBJECT-TYPE
			SYNTAX Counter64
			UNITS "Frames"
			MAX-ACCESS read-only
			STATUS current
			DESCRIPTION
				" "
			::= { etherStatsEntry 52 }
		
		-- 1.3.6.1.4.1.2011.2.25.10.30.10.1.1.53
		etherStatsDeferredTransmissions OBJECT-TYPE
			SYNTAX Counter64
			UNITS "Frames"
			MAX-ACCESS read-only
			STATUS current
			DESCRIPTION
				" "
			::= { etherStatsEntry 53 }
		
		-- 1.3.6.1.4.1.2011.2.25.10.30.10.1.1.54
		etherStatsCarrierSenseErrors OBJECT-TYPE
			SYNTAX Counter64
			UNITS "Times"
			MAX-ACCESS read-only
			STATUS current
			DESCRIPTION
				" "
			::= { etherStatsEntry 54 }
		
		-- 1.3.6.1.4.1.2011.2.25.10.30.10.1.1.55
		etherStatsInControlFrames OBJECT-TYPE
			SYNTAX Counter64
			UNITS "Frames"
			MAX-ACCESS read-only
			STATUS current
			DESCRIPTION
				" "
			::= { etherStatsEntry 55 }
		
		-- 1.3.6.1.4.1.2011.2.25.10.30.10.1.1.56
		etherStatsOutControlFrames OBJECT-TYPE
			SYNTAX Counter64
			UNITS "Frames"
			MAX-ACCESS read-only
			STATUS current
			DESCRIPTION
				" "
			::= { etherStatsEntry 56 }
		
		-- 1.3.6.1.4.1.2011.2.25.10.30.10.1.1.57
		etherStatsOutDropEvents OBJECT-TYPE
			SYNTAX Counter64
			UNITS "Times"
			MAX-ACCESS read-only
			STATUS current
			DESCRIPTION
				" "
			::= { etherStatsEntry 57 }
		
		-- 1.3.6.1.4.1.2011.2.25.10.30.10.1.1.58
		etherStatsOutOversizePkts OBJECT-TYPE
			SYNTAX Counter64
			UNITS "Packets"
			MAX-ACCESS read-only
			STATUS current
			DESCRIPTION
				" "
			::= { etherStatsEntry 58 }
		
		-- 1.3.6.1.4.1.2011.2.25.10.30.10.1.1.59
		etherStatsOutPkts OBJECT-TYPE
			SYNTAX Counter64
			UNITS "Packets"
			MAX-ACCESS read-only
			STATUS current
			DESCRIPTION
				" "
			::= { etherStatsEntry 59 }
		
		-- 1.3.6.1.4.1.2011.2.25.10.30.10.1.1.60
		etherStatsOutOctets OBJECT-TYPE
			SYNTAX Counter64
			UNITS "Octecs"
			MAX-ACCESS read-only
			STATUS current
			DESCRIPTION
				" "
			::= { etherStatsEntry 60 }
		
		-- 1.3.6.1.4.1.2011.2.25.10.30.10.1.1.61
		etherStatsRxFullGoodOcetcs OBJECT-TYPE
			SYNTAX Counter64
			UNITS "Octecs"
			MAX-ACCESS read-only
			STATUS current
			DESCRIPTION
				"  The total number of received octets of 
				good packets(including framing bits and FCS octets). "
			::= { etherStatsEntry 61 }
		
		-- 1.3.6.1.4.1.2011.2.25.10.30.10.1.1.62
		etherStatsTxFullGoodOctecs OBJECT-TYPE
			SYNTAX Counter64
			UNITS "Octecs"
			MAX-ACCESS read-only
			STATUS current
			DESCRIPTION
				"  The total number of transmited octets of 
				good packets(including framing bits and FCS octets). "
			::= { etherStatsEntry 62 }
		
		-- 1.3.6.1.4.1.2011.2.25.10.30.99
		optixRmonMibConformance OBJECT IDENTIFIER ::= { optixHKRmonMib 99 }
		
		-- 1.3.6.1.4.1.2011.2.25.10.30.99.1
		optixRmonMibGroups OBJECT IDENTIFIER ::= { optixRmonMibConformance 1 }
		
		-- 1.3.6.1.4.1.2011.2.25.10.30.99.1.1
		currentObjectGroup OBJECT-GROUP
			OBJECTS { etherStatsIndex, etherStatsDropEvents, etherStatsOctets, etherStatsPkts, etherStatsBroadcastPkts, 
				etherStatsMulticastPkts, etherStatsCRCAlignErrors, etherStatsUndersizePkts, etherStatsOversizePkts, etherStatsFragments, 
				etherStatsJabbers, etherStatsCollisions, etherStatsPkts64Octets, etherStatsPkts65to127Octets, etherStatsPkts128to255Octets, 
				etherStatsPkts256to511Octets, etherStatsPkts512to1023Octets, etherStatsPkts1024to1518Octets, etherStatsPkts1519toMtuOctets, etherStatsTranPkts64Octets, 
				etherStatsTranPkts65to127Octets, etherStatsTranPkts128to255Octets, etherStatsTranPkts256to511Octets, etherStatsTranPkts512to1023Octets, etherStatsTranPkts1024to1518Octets, 
				etherStatsTranPkts1519toMtuOctets, etherStatsRxTxPkts64Octets, etherStatsRxTxPkts65to127Octets, etherStatsRxTxPkts128to255Octets, etherStatsRxTxPkts256to511Octets, 
				etherStatsRxTxPkts512to1023Octets, etherStatsRxTxPkts1024to1518Octets, etherStatsRxTxPkts1519toMtuOctets, etherStatsInUcastPkts, etherStatsOutUcastPkts, 
				etherStatsInPauseFrames, etherStatsOutPauseFrames, etherStatsOutMulticastPkts, etherStatsOutBroadcastPkts, etherStatsInGoodOctets, 
				etherStatsOutGoodOctets, etherStatsInBadOctets, etherStatsOutBadOctets, etherStatsAlignmentErrors, etherStatsFCSErrors, 
				etherStatsSingleCollisionFrames, etherStatsMultipleCollisionFrames, etherStatsLateCollisions, etherStatsExcessiveCollisions, etherStatsDeferredTransmissions, 
				etherStatsCarrierSenseErrors, etherStatsInControlFrames, etherStatsOutControlFrames, etherStatsOutDropEvents, etherStatsOutOversizePkts, 
				etherStatsOutPkts, etherStatsOutOctets, etherStatsRxFullGoodOcetcs, etherStatsTxFullGoodOctecs }
			STATUS deprecated
			DESCRIPTION 
				"Enter the description of the created OBJECT-GROUP."
			::= { optixRmonMibGroups 1 }
		
		-- 1.3.6.1.4.1.2011.2.25.10.30.99.2
		optixRmonMibCompliances OBJECT IDENTIFIER ::= { optixRmonMibConformance 2 }
		
		-- 1.3.6.1.4.1.2011.2.25.10.30.99.2.1
		basicCompliance MODULE-COMPLIANCE
			STATUS current
			DESCRIPTION 
				"Enter the description of the created MODULE-COMPLIANCE."
			MODULE -- this module
				MANDATORY-GROUPS { currentObjectGroup }
			::= { optixRmonMibCompliances 1 }
		
	
	END

--
-- OPTIX-HK-RMON-MIB.mib
--
