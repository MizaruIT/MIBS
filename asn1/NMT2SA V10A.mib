--  Title:    NMT2SA_V10A.MIB
--  Version:  v1.0
--
--  Copyright @ 1997-2004 DPS Inc. All Rights Reserved
--
--  This MIB defines supplemental objects for the DPS NetMediator T2S series remotes.
--
--

DPS-MIB-NMT2SA-V10A DEFINITIONS ::= BEGIN

IMPORTS
	dpsRTU
		FROM DPS-MIB-V38;

dpsRTUp10001Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 1 is set"
	::= 10001

dpsRTUp11001Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 1 is cleared"
	::= 11001

dpsRTUp10002Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 2 is set"
	::= 10002

dpsRTUp11002Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 2 is cleared"
	::= 11002

dpsRTUp10003Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 3 is set"
	::= 10003

dpsRTUp11003Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 3 is cleared"
	::= 11003

dpsRTUp10004Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 4 is set"
	::= 10004

dpsRTUp11004Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 4 is cleared"
	::= 11004

dpsRTUp10005Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 5 is set"
	::= 10005

dpsRTUp11005Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 5 is cleared"
	::= 11005

dpsRTUp10006Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 6 is set"
	::= 10006

dpsRTUp11006Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 6 is cleared"
	::= 11006

dpsRTUp10007Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 7 is set"
	::= 10007

dpsRTUp11007Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 7 is cleared"
	::= 11007

dpsRTUp10008Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 8 is set"
	::= 10008

dpsRTUp11008Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 8 is cleared"
	::= 11008

dpsRTUp10009Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 9 is set"
	::= 10009

dpsRTUp11009Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 9 is cleared"
	::= 11009

dpsRTUp10010Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 10 is set"
	::= 10010

dpsRTUp11010Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 10 is cleared"
	::= 11010

dpsRTUp10011Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 11 is set"
	::= 10011

dpsRTUp11011Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 11 is cleared"
	::= 11011

dpsRTUp10012Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 12 is set"
	::= 10012

dpsRTUp11012Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 12 is cleared"
	::= 11012

dpsRTUp10013Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 13 is set"
	::= 10013

dpsRTUp11013Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 13 is cleared"
	::= 11013

dpsRTUp10014Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 14 is set"
	::= 10014

dpsRTUp11014Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 14 is cleared"
	::= 11014

dpsRTUp10015Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 15 is set"
	::= 10015

dpsRTUp11015Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 15 is cleared"
	::= 11015

dpsRTUp10016Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 16 is set"
	::= 10016

dpsRTUp11016Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 16 is cleared"
	::= 11016

dpsRTUp10017Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 17 is set"
	::= 10017

dpsRTUp11017Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 17 is cleared"
	::= 11017

dpsRTUp10018Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 18 is set"
	::= 10018

dpsRTUp11018Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 18 is cleared"
	::= 11018

dpsRTUp10019Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 19 is set"
	::= 10019

dpsRTUp11019Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 19 is cleared"
	::= 11019

dpsRTUp10020Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 20 is set"
	::= 10020

dpsRTUp11020Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 20 is cleared"
	::= 11020

dpsRTUp10021Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 21 is set"
	::= 10021

dpsRTUp11021Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 21 is cleared"
	::= 11021

dpsRTUp10022Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 22 is set"
	::= 10022

dpsRTUp11022Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 22 is cleared"
	::= 11022

dpsRTUp10023Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 23 is set"
	::= 10023

dpsRTUp11023Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 23 is cleared"
	::= 11023

dpsRTUp10024Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 24 is set"
	::= 10024

dpsRTUp11024Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 24 is cleared"
	::= 11024

dpsRTUp10025Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 25 is set"
	::= 10025

dpsRTUp11025Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 25 is cleared"
	::= 11025

dpsRTUp10026Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 26 is set"
	::= 10026

dpsRTUp11026Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 26 is cleared"
	::= 11026

dpsRTUp10027Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 27 is set"
	::= 10027

dpsRTUp11027Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 27 is cleared"
	::= 11027

dpsRTUp10028Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 28 is set"
	::= 10028

dpsRTUp11028Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 28 is cleared"
	::= 11028

dpsRTUp10029Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 29 is set"
	::= 10029

dpsRTUp11029Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 29 is cleared"
	::= 11029

dpsRTUp10030Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 30 is set"
	::= 10030

dpsRTUp11030Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 30 is cleared"
	::= 11030

dpsRTUp10031Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 31 is set"
	::= 10031

dpsRTUp11031Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 31 is cleared"
	::= 11031

dpsRTUp10032Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 32 is set"
	::= 10032

dpsRTUp11032Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 32 is cleared"
	::= 11032

dpsRTUp10033Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 33 is set"
	::= 10033

dpsRTUp11033Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 33 is cleared"
	::= 11033

dpsRTUp10034Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 34 is set"
	::= 10034

dpsRTUp11034Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 34 is cleared"
	::= 11034

dpsRTUp10035Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 35 is set"
	::= 10035

dpsRTUp11035Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 35 is cleared"
	::= 11035

dpsRTUp10036Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 36 is set"
	::= 10036

dpsRTUp11036Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 36 is cleared"
	::= 11036

dpsRTUp10037Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 37 is set"
	::= 10037

dpsRTUp11037Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 37 is cleared"
	::= 11037

dpsRTUp10038Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 38 is set"
	::= 10038

dpsRTUp11038Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 38 is cleared"
	::= 11038

dpsRTUp10039Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 39 is set"
	::= 10039

dpsRTUp11039Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 39 is cleared"
	::= 11039

dpsRTUp10040Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 40 is set"
	::= 10040

dpsRTUp11040Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 40 is cleared"
	::= 11040

dpsRTUp10041Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 41 is set"
	::= 10041

dpsRTUp11041Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 41 is cleared"
	::= 11041

dpsRTUp10042Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 42 is set"
	::= 10042

dpsRTUp11042Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 42 is cleared"
	::= 11042

dpsRTUp10043Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 43 is set"
	::= 10043

dpsRTUp11043Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 43 is cleared"
	::= 11043

dpsRTUp10044Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 44 is set"
	::= 10044

dpsRTUp11044Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 44 is cleared"
	::= 11044

dpsRTUp10045Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 45 is set"
	::= 10045

dpsRTUp11045Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 45 is cleared"
	::= 11045

dpsRTUp10046Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 46 is set"
	::= 10046

dpsRTUp11046Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 46 is cleared"
	::= 11046

dpsRTUp10047Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 47 is set"
	::= 10047

dpsRTUp11047Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 47 is cleared"
	::= 11047

dpsRTUp10048Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 48 is set"
	::= 10048

dpsRTUp11048Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 48 is cleared"
	::= 11048

dpsRTUp10049Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 49 is set"
	::= 10049

dpsRTUp11049Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 49 is cleared"
	::= 11049

dpsRTUp10050Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 50 is set"
	::= 10050

dpsRTUp11050Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 50 is cleared"
	::= 11050

dpsRTUp10051Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 51 is set"
	::= 10051

dpsRTUp11051Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 51 is cleared"
	::= 11051

dpsRTUp10052Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 52 is set"
	::= 10052

dpsRTUp11052Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 52 is cleared"
	::= 11052

dpsRTUp10053Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 53 is set"
	::= 10053

dpsRTUp11053Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 53 is cleared"
	::= 11053

dpsRTUp10054Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 54 is set"
	::= 10054

dpsRTUp11054Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 54 is cleared"
	::= 11054

dpsRTUp10055Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 55 is set"
	::= 10055

dpsRTUp11055Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 55 is cleared"
	::= 11055

dpsRTUp10056Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 56 is set"
	::= 10056

dpsRTUp11056Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 56 is cleared"
	::= 11056

dpsRTUp10057Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 57 is set"
	::= 10057

dpsRTUp11057Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 57 is cleared"
	::= 11057

dpsRTUp10058Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 58 is set"
	::= 10058

dpsRTUp11058Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 58 is cleared"
	::= 11058

dpsRTUp10059Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 59 is set"
	::= 10059

dpsRTUp11059Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 59 is cleared"
	::= 11059

dpsRTUp10060Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 60 is set"
	::= 10060

dpsRTUp11060Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 60 is cleared"
	::= 11060

dpsRTUp10061Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 61 is set"
	::= 10061

dpsRTUp11061Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 61 is cleared"
	::= 11061

dpsRTUp10062Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 62 is set"
	::= 10062

dpsRTUp11062Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 62 is cleared"
	::= 11062

dpsRTUp10063Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 63 is set"
	::= 10063

dpsRTUp11063Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 63 is cleared"
	::= 11063

dpsRTUp10064Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 64 is set"
	::= 10064

dpsRTUp11064Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 1 point 64 is cleared"
	::= 11064

dpsRTUp10065Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 1 is set"
	::= 10065

dpsRTUp11065Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 1 is cleared"
	::= 11065

dpsRTUp10066Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 2 is set"
	::= 10066

dpsRTUp11066Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 2 is cleared"
	::= 11066

dpsRTUp10067Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 3 is set"
	::= 10067

dpsRTUp11067Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 3 is cleared"
	::= 11067

dpsRTUp10068Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 4 is set"
	::= 10068

dpsRTUp11068Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 4 is cleared"
	::= 11068

dpsRTUp10069Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 5 is set"
	::= 10069

dpsRTUp11069Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 5 is cleared"
	::= 11069

dpsRTUp10070Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 6 is set"
	::= 10070

dpsRTUp11070Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 6 is cleared"
	::= 11070

dpsRTUp10071Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 7 is set"
	::= 10071

dpsRTUp11071Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 7 is cleared"
	::= 11071

dpsRTUp10072Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 8 is set"
	::= 10072

dpsRTUp11072Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 8 is cleared"
	::= 11072

dpsRTUp10073Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 9 is set"
	::= 10073

dpsRTUp11073Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 9 is cleared"
	::= 11073

dpsRTUp10074Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 10 is set"
	::= 10074

dpsRTUp11074Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 10 is cleared"
	::= 11074

dpsRTUp10075Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 11 is set"
	::= 10075

dpsRTUp11075Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 11 is cleared"
	::= 11075

dpsRTUp10076Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 12 is set"
	::= 10076

dpsRTUp11076Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 12 is cleared"
	::= 11076

dpsRTUp10077Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 13 is set"
	::= 10077

dpsRTUp11077Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 13 is cleared"
	::= 11077

dpsRTUp10078Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 14 is set"
	::= 10078

dpsRTUp11078Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 14 is cleared"
	::= 11078

dpsRTUp10079Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 15 is set"
	::= 10079

dpsRTUp11079Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 15 is cleared"
	::= 11079

dpsRTUp10080Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 16 is set"
	::= 10080

dpsRTUp11080Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 16 is cleared"
	::= 11080

dpsRTUp10081Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 17 is set"
	::= 10081

dpsRTUp11081Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 17 is cleared"
	::= 11081

dpsRTUp10082Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 18 is set"
	::= 10082

dpsRTUp11082Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 18 is cleared"
	::= 11082

dpsRTUp10083Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 19 is set"
	::= 10083

dpsRTUp11083Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 19 is cleared"
	::= 11083

dpsRTUp10084Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 20 is set"
	::= 10084

dpsRTUp11084Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 20 is cleared"
	::= 11084

dpsRTUp10085Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 21 is set"
	::= 10085

dpsRTUp11085Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 21 is cleared"
	::= 11085

dpsRTUp10086Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 22 is set"
	::= 10086

dpsRTUp11086Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 22 is cleared"
	::= 11086

dpsRTUp10087Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 23 is set"
	::= 10087

dpsRTUp11087Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 23 is cleared"
	::= 11087

dpsRTUp10088Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 24 is set"
	::= 10088

dpsRTUp11088Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 24 is cleared"
	::= 11088

dpsRTUp10089Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 25 is set"
	::= 10089

dpsRTUp11089Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 25 is cleared"
	::= 11089

dpsRTUp10090Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 26 is set"
	::= 10090

dpsRTUp11090Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 26 is cleared"
	::= 11090

dpsRTUp10091Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 27 is set"
	::= 10091

dpsRTUp11091Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 27 is cleared"
	::= 11091

dpsRTUp10092Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 28 is set"
	::= 10092

dpsRTUp11092Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 28 is cleared"
	::= 11092

dpsRTUp10093Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 29 is set"
	::= 10093

dpsRTUp11093Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 29 is cleared"
	::= 11093

dpsRTUp10094Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 30 is set"
	::= 10094

dpsRTUp11094Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 30 is cleared"
	::= 11094

dpsRTUp10095Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 31 is set"
	::= 10095

dpsRTUp11095Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 31 is cleared"
	::= 11095

dpsRTUp10096Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 32 is set"
	::= 10096

dpsRTUp11096Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 32 is cleared"
	::= 11096

dpsRTUp10097Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 33 is set"
	::= 10097

dpsRTUp11097Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 33 is cleared"
	::= 11097

dpsRTUp10098Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 34 is set"
	::= 10098

dpsRTUp11098Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 34 is cleared"
	::= 11098

dpsRTUp10099Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 35 is set"
	::= 10099

dpsRTUp11099Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 35 is cleared"
	::= 11099

dpsRTUp10100Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 36 is set"
	::= 10100

dpsRTUp11100Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 36 is cleared"
	::= 11100

dpsRTUp10101Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 37 is set"
	::= 10101

dpsRTUp11101Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 37 is cleared"
	::= 11101

dpsRTUp10102Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 38 is set"
	::= 10102

dpsRTUp11102Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 38 is cleared"
	::= 11102

dpsRTUp10103Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 39 is set"
	::= 10103

dpsRTUp11103Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 39 is cleared"
	::= 11103

dpsRTUp10104Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 40 is set"
	::= 10104

dpsRTUp11104Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 40 is cleared"
	::= 11104

dpsRTUp10105Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 41 is set"
	::= 10105

dpsRTUp11105Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 41 is cleared"
	::= 11105

dpsRTUp10106Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 42 is set"
	::= 10106

dpsRTUp11106Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 42 is cleared"
	::= 11106

dpsRTUp10107Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 43 is set"
	::= 10107

dpsRTUp11107Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 43 is cleared"
	::= 11107

dpsRTUp10108Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 44 is set"
	::= 10108

dpsRTUp11108Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 44 is cleared"
	::= 11108

dpsRTUp10109Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 45 is set"
	::= 10109

dpsRTUp11109Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 45 is cleared"
	::= 11109

dpsRTUp10110Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 46 is set"
	::= 10110

dpsRTUp11110Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 46 is cleared"
	::= 11110

dpsRTUp10111Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 47 is set"
	::= 10111

dpsRTUp11111Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 47 is cleared"
	::= 11111

dpsRTUp10112Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 48 is set"
	::= 10112

dpsRTUp11112Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 48 is cleared"
	::= 11112

dpsRTUp10113Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 49 is set"
	::= 10113

dpsRTUp11113Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 49 is cleared"
	::= 11113

dpsRTUp10114Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 50 is set"
	::= 10114

dpsRTUp11114Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 50 is cleared"
	::= 11114

dpsRTUp10115Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 51 is set"
	::= 10115

dpsRTUp11115Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 51 is cleared"
	::= 11115

dpsRTUp10116Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 52 is set"
	::= 10116

dpsRTUp11116Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 52 is cleared"
	::= 11116

dpsRTUp10117Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 53 is set"
	::= 10117

dpsRTUp11117Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 53 is cleared"
	::= 11117

dpsRTUp10118Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 54 is set"
	::= 10118

dpsRTUp11118Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 54 is cleared"
	::= 11118

dpsRTUp10119Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 55 is set"
	::= 10119

dpsRTUp11119Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 55 is cleared"
	::= 11119

dpsRTUp10120Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 56 is set"
	::= 10120

dpsRTUp11120Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 56 is cleared"
	::= 11120

dpsRTUp10121Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 57 is set"
	::= 10121

dpsRTUp11121Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 57 is cleared"
	::= 11121

dpsRTUp10122Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 58 is set"
	::= 10122

dpsRTUp11122Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 58 is cleared"
	::= 11122

dpsRTUp10123Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 59 is set"
	::= 10123

dpsRTUp11123Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 59 is cleared"
	::= 11123

dpsRTUp10124Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 60 is set"
	::= 10124

dpsRTUp11124Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 60 is cleared"
	::= 11124

dpsRTUp10125Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 61 is set"
	::= 10125

dpsRTUp11125Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 61 is cleared"
	::= 11125

dpsRTUp10126Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 62 is set"
	::= 10126

dpsRTUp11126Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 62 is cleared"
	::= 11126

dpsRTUp10127Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 63 is set"
	::= 10127

dpsRTUp11127Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 63 is cleared"
	::= 11127

dpsRTUp10128Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 64 is set"
	::= 10128

dpsRTUp11128Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 2 point 64 is cleared"
	::= 11128

dpsRTUp10129Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 1 is set"
	::= 10129

dpsRTUp11129Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 1 is cleared"
	::= 11129

dpsRTUp10130Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 2 is set"
	::= 10130

dpsRTUp11130Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 2 is cleared"
	::= 11130

dpsRTUp10131Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 3 is set"
	::= 10131

dpsRTUp11131Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 3 is cleared"
	::= 11131

dpsRTUp10132Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 4 is set"
	::= 10132

dpsRTUp11132Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 4 is cleared"
	::= 11132

dpsRTUp10133Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 5 is set"
	::= 10133

dpsRTUp11133Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 5 is cleared"
	::= 11133

dpsRTUp10134Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 6 is set"
	::= 10134

dpsRTUp11134Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 6 is cleared"
	::= 11134

dpsRTUp10135Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 7 is set"
	::= 10135

dpsRTUp11135Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 7 is cleared"
	::= 11135

dpsRTUp10136Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 8 is set"
	::= 10136

dpsRTUp11136Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 8 is cleared"
	::= 11136

dpsRTUp10137Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 9 is set"
	::= 10137

dpsRTUp11137Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 9 is cleared"
	::= 11137

dpsRTUp10138Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 10 is set"
	::= 10138

dpsRTUp11138Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 10 is cleared"
	::= 11138

dpsRTUp10139Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 11 is set"
	::= 10139

dpsRTUp11139Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 11 is cleared"
	::= 11139

dpsRTUp10140Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 12 is set"
	::= 10140

dpsRTUp11140Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 12 is cleared"
	::= 11140

dpsRTUp10141Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 13 is set"
	::= 10141

dpsRTUp11141Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 13 is cleared"
	::= 11141

dpsRTUp10142Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 14 is set"
	::= 10142

dpsRTUp11142Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 14 is cleared"
	::= 11142

dpsRTUp10143Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 15 is set"
	::= 10143

dpsRTUp11143Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 15 is cleared"
	::= 11143

dpsRTUp10144Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 16 is set"
	::= 10144

dpsRTUp11144Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 16 is cleared"
	::= 11144

dpsRTUp10145Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 17 is set"
	::= 10145

dpsRTUp11145Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 17 is cleared"
	::= 11145

dpsRTUp10146Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 18 is set"
	::= 10146

dpsRTUp11146Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 18 is cleared"
	::= 11146

dpsRTUp10147Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 19 is set"
	::= 10147

dpsRTUp11147Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 19 is cleared"
	::= 11147

dpsRTUp10148Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 20 is set"
	::= 10148

dpsRTUp11148Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 20 is cleared"
	::= 11148

dpsRTUp10149Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 21 is set"
	::= 10149

dpsRTUp11149Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 21 is cleared"
	::= 11149

dpsRTUp10150Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 22 is set"
	::= 10150

dpsRTUp11150Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 22 is cleared"
	::= 11150

dpsRTUp10151Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 23 is set"
	::= 10151

dpsRTUp11151Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 23 is cleared"
	::= 11151

dpsRTUp10152Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 24 is set"
	::= 10152

dpsRTUp11152Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 24 is cleared"
	::= 11152

dpsRTUp10153Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 25 is set"
	::= 10153

dpsRTUp11153Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 25 is cleared"
	::= 11153

dpsRTUp10154Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 26 is set"
	::= 10154

dpsRTUp11154Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 26 is cleared"
	::= 11154

dpsRTUp10155Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 27 is set"
	::= 10155

dpsRTUp11155Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 27 is cleared"
	::= 11155

dpsRTUp10156Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 28 is set"
	::= 10156

dpsRTUp11156Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 28 is cleared"
	::= 11156

dpsRTUp10157Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 29 is set"
	::= 10157

dpsRTUp11157Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 29 is cleared"
	::= 11157

dpsRTUp10158Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 30 is set"
	::= 10158

dpsRTUp11158Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 30 is cleared"
	::= 11158

dpsRTUp10159Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 31 is set"
	::= 10159

dpsRTUp11159Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 31 is cleared"
	::= 11159

dpsRTUp10160Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 32 is set"
	::= 10160

dpsRTUp11160Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 32 is cleared"
	::= 11160

dpsRTUp10161Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 33 is set"
	::= 10161

dpsRTUp11161Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 33 is cleared"
	::= 11161

dpsRTUp10162Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 34 is set"
	::= 10162

dpsRTUp11162Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 34 is cleared"
	::= 11162

dpsRTUp10163Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 35 is set"
	::= 10163

dpsRTUp11163Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 35 is cleared"
	::= 11163

dpsRTUp10164Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 36 is set"
	::= 10164

dpsRTUp11164Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 36 is cleared"
	::= 11164

dpsRTUp10165Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 37 is set"
	::= 10165

dpsRTUp11165Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 37 is cleared"
	::= 11165

dpsRTUp10166Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 38 is set"
	::= 10166

dpsRTUp11166Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 38 is cleared"
	::= 11166

dpsRTUp10167Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 39 is set"
	::= 10167

dpsRTUp11167Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 39 is cleared"
	::= 11167

dpsRTUp10168Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 40 is set"
	::= 10168

dpsRTUp11168Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 40 is cleared"
	::= 11168

dpsRTUp10169Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 41 is set"
	::= 10169

dpsRTUp11169Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 41 is cleared"
	::= 11169

dpsRTUp10170Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 42 is set"
	::= 10170

dpsRTUp11170Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 42 is cleared"
	::= 11170

dpsRTUp10171Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 43 is set"
	::= 10171

dpsRTUp11171Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 43 is cleared"
	::= 11171

dpsRTUp10172Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 44 is set"
	::= 10172

dpsRTUp11172Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 44 is cleared"
	::= 11172

dpsRTUp10173Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 45 is set"
	::= 10173

dpsRTUp11173Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 45 is cleared"
	::= 11173

dpsRTUp10174Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 46 is set"
	::= 10174

dpsRTUp11174Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 46 is cleared"
	::= 11174

dpsRTUp10175Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 47 is set"
	::= 10175

dpsRTUp11175Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 47 is cleared"
	::= 11175

dpsRTUp10176Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 48 is set"
	::= 10176

dpsRTUp11176Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 48 is cleared"
	::= 11176

dpsRTUp10177Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 49 is set"
	::= 10177

dpsRTUp11177Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 49 is cleared"
	::= 11177

dpsRTUp10178Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 50 is set"
	::= 10178

dpsRTUp11178Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 50 is cleared"
	::= 11178

dpsRTUp10179Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 51 is set"
	::= 10179

dpsRTUp11179Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 51 is cleared"
	::= 11179

dpsRTUp10180Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 52 is set"
	::= 10180

dpsRTUp11180Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 52 is cleared"
	::= 11180

dpsRTUp10181Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 53 is set"
	::= 10181

dpsRTUp11181Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 53 is cleared"
	::= 11181

dpsRTUp10182Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 54 is set"
	::= 10182

dpsRTUp11182Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 54 is cleared"
	::= 11182

dpsRTUp10183Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 55 is set"
	::= 10183

dpsRTUp11183Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 55 is cleared"
	::= 11183

dpsRTUp10184Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 56 is set"
	::= 10184

dpsRTUp11184Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 56 is cleared"
	::= 11184

dpsRTUp10185Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 57 is set"
	::= 10185

dpsRTUp11185Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 57 is cleared"
	::= 11185

dpsRTUp10186Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 58 is set"
	::= 10186

dpsRTUp11186Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 58 is cleared"
	::= 11186

dpsRTUp10187Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 59 is set"
	::= 10187

dpsRTUp11187Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 59 is cleared"
	::= 11187

dpsRTUp10188Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 60 is set"
	::= 10188

dpsRTUp11188Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 60 is cleared"
	::= 11188

dpsRTUp10189Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 61 is set"
	::= 10189

dpsRTUp11189Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 61 is cleared"
	::= 11189

dpsRTUp10190Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 62 is set"
	::= 10190

dpsRTUp11190Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 62 is cleared"
	::= 11190

dpsRTUp10191Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 63 is set"
	::= 10191

dpsRTUp11191Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 63 is cleared"
	::= 11191

dpsRTUp10192Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 64 is set"
	::= 10192

dpsRTUp11192Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 3 point 64 is cleared"
	::= 11192

dpsRTUp10193Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 1 is set"
	::= 10193

dpsRTUp11193Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 1 is cleared"
	::= 11193

dpsRTUp10194Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 2 is set"
	::= 10194

dpsRTUp11194Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 2 is cleared"
	::= 11194

dpsRTUp10195Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 3 is set"
	::= 10195

dpsRTUp11195Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 3 is cleared"
	::= 11195

dpsRTUp10196Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 4 is set"
	::= 10196

dpsRTUp11196Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 4 is cleared"
	::= 11196

dpsRTUp10197Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 5 is set"
	::= 10197

dpsRTUp11197Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 5 is cleared"
	::= 11197

dpsRTUp10198Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 6 is set"
	::= 10198

dpsRTUp11198Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 6 is cleared"
	::= 11198

dpsRTUp10199Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 7 is set"
	::= 10199

dpsRTUp11199Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 7 is cleared"
	::= 11199

dpsRTUp10200Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 8 is set"
	::= 10200

dpsRTUp11200Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 8 is cleared"
	::= 11200

dpsRTUp10201Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 9 is set"
	::= 10201

dpsRTUp11201Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 9 is cleared"
	::= 11201

dpsRTUp10202Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 10 is set"
	::= 10202

dpsRTUp11202Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 10 is cleared"
	::= 11202

dpsRTUp10203Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 11 is set"
	::= 10203

dpsRTUp11203Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 11 is cleared"
	::= 11203

dpsRTUp10204Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 12 is set"
	::= 10204

dpsRTUp11204Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 12 is cleared"
	::= 11204

dpsRTUp10205Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 13 is set"
	::= 10205

dpsRTUp11205Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 13 is cleared"
	::= 11205

dpsRTUp10206Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 14 is set"
	::= 10206

dpsRTUp11206Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 14 is cleared"
	::= 11206

dpsRTUp10207Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 15 is set"
	::= 10207

dpsRTUp11207Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 15 is cleared"
	::= 11207

dpsRTUp10208Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 16 is set"
	::= 10208

dpsRTUp11208Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 16 is cleared"
	::= 11208

dpsRTUp10209Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 17 is set"
	::= 10209

dpsRTUp11209Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 17 is cleared"
	::= 11209

dpsRTUp10210Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 18 is set"
	::= 10210

dpsRTUp11210Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 18 is cleared"
	::= 11210

dpsRTUp10211Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 19 is set"
	::= 10211

dpsRTUp11211Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 19 is cleared"
	::= 11211

dpsRTUp10212Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 20 is set"
	::= 10212

dpsRTUp11212Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 20 is cleared"
	::= 11212

dpsRTUp10213Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 21 is set"
	::= 10213

dpsRTUp11213Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 21 is cleared"
	::= 11213

dpsRTUp10214Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 22 is set"
	::= 10214

dpsRTUp11214Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 22 is cleared"
	::= 11214

dpsRTUp10215Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 23 is set"
	::= 10215

dpsRTUp11215Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 23 is cleared"
	::= 11215

dpsRTUp10216Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 24 is set"
	::= 10216

dpsRTUp11216Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 24 is cleared"
	::= 11216

dpsRTUp10217Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 25 is set"
	::= 10217

dpsRTUp11217Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 25 is cleared"
	::= 11217

dpsRTUp10218Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 26 is set"
	::= 10218

dpsRTUp11218Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 26 is cleared"
	::= 11218

dpsRTUp10219Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 27 is set"
	::= 10219

dpsRTUp11219Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 27 is cleared"
	::= 11219

dpsRTUp10220Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 28 is set"
	::= 10220

dpsRTUp11220Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 28 is cleared"
	::= 11220

dpsRTUp10221Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 29 is set"
	::= 10221

dpsRTUp11221Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 29 is cleared"
	::= 11221

dpsRTUp10222Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 30 is set"
	::= 10222

dpsRTUp11222Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 30 is cleared"
	::= 11222

dpsRTUp10223Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 31 is set"
	::= 10223

dpsRTUp11223Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 31 is cleared"
	::= 11223

dpsRTUp10224Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 32 is set"
	::= 10224

dpsRTUp11224Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 32 is cleared"
	::= 11224

dpsRTUp10225Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 33 is set"
	::= 10225

dpsRTUp11225Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 33 is cleared"
	::= 11225

dpsRTUp10226Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 34 is set"
	::= 10226

dpsRTUp11226Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 34 is cleared"
	::= 11226

dpsRTUp10227Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 35 is set"
	::= 10227

dpsRTUp11227Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 35 is cleared"
	::= 11227

dpsRTUp10228Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 36 is set"
	::= 10228

dpsRTUp11228Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 36 is cleared"
	::= 11228

dpsRTUp10229Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 37 is set"
	::= 10229

dpsRTUp11229Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 37 is cleared"
	::= 11229

dpsRTUp10230Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 38 is set"
	::= 10230

dpsRTUp11230Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 38 is cleared"
	::= 11230

dpsRTUp10231Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 39 is set"
	::= 10231

dpsRTUp11231Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 39 is cleared"
	::= 11231

dpsRTUp10232Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 40 is set"
	::= 10232

dpsRTUp11232Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 40 is cleared"
	::= 11232

dpsRTUp10233Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 41 is set"
	::= 10233

dpsRTUp11233Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 41 is cleared"
	::= 11233

dpsRTUp10234Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 42 is set"
	::= 10234

dpsRTUp11234Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 42 is cleared"
	::= 11234

dpsRTUp10235Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 43 is set"
	::= 10235

dpsRTUp11235Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 43 is cleared"
	::= 11235

dpsRTUp10236Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 44 is set"
	::= 10236

dpsRTUp11236Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 44 is cleared"
	::= 11236

dpsRTUp10237Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 45 is set"
	::= 10237

dpsRTUp11237Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 45 is cleared"
	::= 11237

dpsRTUp10238Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 46 is set"
	::= 10238

dpsRTUp11238Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 46 is cleared"
	::= 11238

dpsRTUp10239Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 47 is set"
	::= 10239

dpsRTUp11239Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 47 is cleared"
	::= 11239

dpsRTUp10240Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 48 is set"
	::= 10240

dpsRTUp11240Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 48 is cleared"
	::= 11240

dpsRTUp10241Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 49 is set"
	::= 10241

dpsRTUp11241Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 49 is cleared"
	::= 11241

dpsRTUp10242Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 50 is set"
	::= 10242

dpsRTUp11242Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 50 is cleared"
	::= 11242

dpsRTUp10243Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 51 is set"
	::= 10243

dpsRTUp11243Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 51 is cleared"
	::= 11243

dpsRTUp10244Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 52 is set"
	::= 10244

dpsRTUp11244Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 52 is cleared"
	::= 11244

dpsRTUp10245Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 53 is set"
	::= 10245

dpsRTUp11245Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 53 is cleared"
	::= 11245

dpsRTUp10246Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 54 is set"
	::= 10246

dpsRTUp11246Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 54 is cleared"
	::= 11246

dpsRTUp10247Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 55 is set"
	::= 10247

dpsRTUp11247Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 55 is cleared"
	::= 11247

dpsRTUp10248Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 56 is set"
	::= 10248

dpsRTUp11248Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 56 is cleared"
	::= 11248

dpsRTUp10249Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 57 is set"
	::= 10249

dpsRTUp11249Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 57 is cleared"
	::= 11249

dpsRTUp10250Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 58 is set"
	::= 10250

dpsRTUp11250Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 58 is cleared"
	::= 11250

dpsRTUp10251Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 59 is set"
	::= 10251

dpsRTUp11251Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 59 is cleared"
	::= 11251

dpsRTUp10252Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 60 is set"
	::= 10252

dpsRTUp11252Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 60 is cleared"
	::= 11252

dpsRTUp10253Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 61 is set"
	::= 10253

dpsRTUp11253Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 61 is cleared"
	::= 11253

dpsRTUp10254Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 62 is set"
	::= 10254

dpsRTUp11254Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 62 is cleared"
	::= 11254

dpsRTUp10255Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 63 is set"
	::= 10255

dpsRTUp11255Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 63 is cleared"
	::= 11255

dpsRTUp10256Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 64 is set"
	::= 10256

dpsRTUp11256Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 4 point 64 is cleared"
	::= 11256

dpsRTUp10257Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 1 is set"
	::= 10257

dpsRTUp11257Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 1 is cleared"
	::= 11257

dpsRTUp10258Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 2 is set"
	::= 10258

dpsRTUp11258Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 2 is cleared"
	::= 11258

dpsRTUp10259Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 3 is set"
	::= 10259

dpsRTUp11259Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 3 is cleared"
	::= 11259

dpsRTUp10260Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 4 is set"
	::= 10260

dpsRTUp11260Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 4 is cleared"
	::= 11260

dpsRTUp10261Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 5 is set"
	::= 10261

dpsRTUp11261Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 5 is cleared"
	::= 11261

dpsRTUp10262Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 6 is set"
	::= 10262

dpsRTUp11262Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 6 is cleared"
	::= 11262

dpsRTUp10263Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 7 is set"
	::= 10263

dpsRTUp11263Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 7 is cleared"
	::= 11263

dpsRTUp10264Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 8 is set"
	::= 10264

dpsRTUp11264Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 8 is cleared"
	::= 11264

dpsRTUp10265Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 9 is set"
	::= 10265

dpsRTUp11265Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 9 is cleared"
	::= 11265

dpsRTUp10266Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 10 is set"
	::= 10266

dpsRTUp11266Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 10 is cleared"
	::= 11266

dpsRTUp10267Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 11 is set"
	::= 10267

dpsRTUp11267Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 11 is cleared"
	::= 11267

dpsRTUp10268Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 12 is set"
	::= 10268

dpsRTUp11268Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 12 is cleared"
	::= 11268

dpsRTUp10269Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 13 is set"
	::= 10269

dpsRTUp11269Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 13 is cleared"
	::= 11269

dpsRTUp10270Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 14 is set"
	::= 10270

dpsRTUp11270Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 14 is cleared"
	::= 11270

dpsRTUp10271Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 15 is set"
	::= 10271

dpsRTUp11271Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 15 is cleared"
	::= 11271

dpsRTUp10272Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 16 is set"
	::= 10272

dpsRTUp11272Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 16 is cleared"
	::= 11272

dpsRTUp10273Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 17 is set"
	::= 10273

dpsRTUp11273Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 17 is cleared"
	::= 11273

dpsRTUp10274Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 18 is set"
	::= 10274

dpsRTUp11274Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 18 is cleared"
	::= 11274

dpsRTUp10275Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 19 is set"
	::= 10275

dpsRTUp11275Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 19 is cleared"
	::= 11275

dpsRTUp10276Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 20 is set"
	::= 10276

dpsRTUp11276Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 20 is cleared"
	::= 11276

dpsRTUp10277Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 21 is set"
	::= 10277

dpsRTUp11277Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 21 is cleared"
	::= 11277

dpsRTUp10278Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 22 is set"
	::= 10278

dpsRTUp11278Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 22 is cleared"
	::= 11278

dpsRTUp10279Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 23 is set"
	::= 10279

dpsRTUp11279Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 23 is cleared"
	::= 11279

dpsRTUp10280Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 24 is set"
	::= 10280

dpsRTUp11280Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 24 is cleared"
	::= 11280

dpsRTUp10281Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 25 is set"
	::= 10281

dpsRTUp11281Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 25 is cleared"
	::= 11281

dpsRTUp10282Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 26 is set"
	::= 10282

dpsRTUp11282Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 26 is cleared"
	::= 11282

dpsRTUp10283Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 27 is set"
	::= 10283

dpsRTUp11283Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 27 is cleared"
	::= 11283

dpsRTUp10284Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 28 is set"
	::= 10284

dpsRTUp11284Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 28 is cleared"
	::= 11284

dpsRTUp10285Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 29 is set"
	::= 10285

dpsRTUp11285Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 29 is cleared"
	::= 11285

dpsRTUp10286Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 30 is set"
	::= 10286

dpsRTUp11286Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 30 is cleared"
	::= 11286

dpsRTUp10287Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 31 is set"
	::= 10287

dpsRTUp11287Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 31 is cleared"
	::= 11287

dpsRTUp10288Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 32 is set"
	::= 10288

dpsRTUp11288Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 32 is cleared"
	::= 11288

dpsRTUp10289Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 33 is set"
	::= 10289

dpsRTUp11289Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 33 is cleared"
	::= 11289

dpsRTUp10290Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 34 is set"
	::= 10290

dpsRTUp11290Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 34 is cleared"
	::= 11290

dpsRTUp10291Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 35 is set"
	::= 10291

dpsRTUp11291Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 35 is cleared"
	::= 11291

dpsRTUp10292Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 36 is set"
	::= 10292

dpsRTUp11292Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 36 is cleared"
	::= 11292

dpsRTUp10293Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 37 is set"
	::= 10293

dpsRTUp11293Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 37 is cleared"
	::= 11293

dpsRTUp10294Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 38 is set"
	::= 10294

dpsRTUp11294Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 38 is cleared"
	::= 11294

dpsRTUp10295Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 39 is set"
	::= 10295

dpsRTUp11295Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 39 is cleared"
	::= 11295

dpsRTUp10296Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 40 is set"
	::= 10296

dpsRTUp11296Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 40 is cleared"
	::= 11296

dpsRTUp10297Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 41 is set"
	::= 10297

dpsRTUp11297Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 41 is cleared"
	::= 11297

dpsRTUp10298Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 42 is set"
	::= 10298

dpsRTUp11298Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 42 is cleared"
	::= 11298

dpsRTUp10299Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 43 is set"
	::= 10299

dpsRTUp11299Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 43 is cleared"
	::= 11299

dpsRTUp10300Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 44 is set"
	::= 10300

dpsRTUp11300Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 44 is cleared"
	::= 11300

dpsRTUp10301Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 45 is set"
	::= 10301

dpsRTUp11301Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 45 is cleared"
	::= 11301

dpsRTUp10302Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 46 is set"
	::= 10302

dpsRTUp11302Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 46 is cleared"
	::= 11302

dpsRTUp10303Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 47 is set"
	::= 10303

dpsRTUp11303Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 47 is cleared"
	::= 11303

dpsRTUp10304Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 48 is set"
	::= 10304

dpsRTUp11304Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 48 is cleared"
	::= 11304

dpsRTUp10305Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 49 is set"
	::= 10305

dpsRTUp11305Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 49 is cleared"
	::= 11305

dpsRTUp10306Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 50 is set"
	::= 10306

dpsRTUp11306Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 50 is cleared"
	::= 11306

dpsRTUp10307Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 51 is set"
	::= 10307

dpsRTUp11307Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 51 is cleared"
	::= 11307

dpsRTUp10308Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 52 is set"
	::= 10308

dpsRTUp11308Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 52 is cleared"
	::= 11308

dpsRTUp10309Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 53 is set"
	::= 10309

dpsRTUp11309Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 53 is cleared"
	::= 11309

dpsRTUp10310Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 54 is set"
	::= 10310

dpsRTUp11310Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 54 is cleared"
	::= 11310

dpsRTUp10311Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 55 is set"
	::= 10311

dpsRTUp11311Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 55 is cleared"
	::= 11311

dpsRTUp10312Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 56 is set"
	::= 10312

dpsRTUp11312Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 56 is cleared"
	::= 11312

dpsRTUp10313Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 57 is set"
	::= 10313

dpsRTUp11313Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 57 is cleared"
	::= 11313

dpsRTUp10314Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 58 is set"
	::= 10314

dpsRTUp11314Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 58 is cleared"
	::= 11314

dpsRTUp10315Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 59 is set"
	::= 10315

dpsRTUp11315Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 59 is cleared"
	::= 11315

dpsRTUp10316Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 60 is set"
	::= 10316

dpsRTUp11316Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 60 is cleared"
	::= 11316

dpsRTUp10317Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 61 is set"
	::= 10317

dpsRTUp11317Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 61 is cleared"
	::= 11317

dpsRTUp10318Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 62 is set"
	::= 10318

dpsRTUp11318Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 62 is cleared"
	::= 11318

dpsRTUp10319Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 63 is set"
	::= 10319

dpsRTUp11319Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 63 is cleared"
	::= 11319

dpsRTUp10320Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 64 is set"
	::= 10320

dpsRTUp11320Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 5 point 64 is cleared"
	::= 11320

dpsRTUp10321Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 1 is set"
	::= 10321

dpsRTUp11321Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 1 is cleared"
	::= 11321

dpsRTUp10322Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 2 is set"
	::= 10322

dpsRTUp11322Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 2 is cleared"
	::= 11322

dpsRTUp10323Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 3 is set"
	::= 10323

dpsRTUp11323Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 3 is cleared"
	::= 11323

dpsRTUp10324Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 4 is set"
	::= 10324

dpsRTUp11324Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 4 is cleared"
	::= 11324

dpsRTUp10325Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 5 is set"
	::= 10325

dpsRTUp11325Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 5 is cleared"
	::= 11325

dpsRTUp10326Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 6 is set"
	::= 10326

dpsRTUp11326Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 6 is cleared"
	::= 11326

dpsRTUp10327Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 7 is set"
	::= 10327

dpsRTUp11327Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 7 is cleared"
	::= 11327

dpsRTUp10328Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 8 is set"
	::= 10328

dpsRTUp11328Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 8 is cleared"
	::= 11328

dpsRTUp10329Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 9 is set"
	::= 10329

dpsRTUp11329Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 9 is cleared"
	::= 11329

dpsRTUp10330Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 10 is set"
	::= 10330

dpsRTUp11330Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 10 is cleared"
	::= 11330

dpsRTUp10331Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 11 is set"
	::= 10331

dpsRTUp11331Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 11 is cleared"
	::= 11331

dpsRTUp10332Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 12 is set"
	::= 10332

dpsRTUp11332Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 12 is cleared"
	::= 11332

dpsRTUp10333Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 13 is set"
	::= 10333

dpsRTUp11333Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 13 is cleared"
	::= 11333

dpsRTUp10334Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 14 is set"
	::= 10334

dpsRTUp11334Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 14 is cleared"
	::= 11334

dpsRTUp10335Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 15 is set"
	::= 10335

dpsRTUp11335Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 15 is cleared"
	::= 11335

dpsRTUp10336Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 16 is set"
	::= 10336

dpsRTUp11336Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 16 is cleared"
	::= 11336

dpsRTUp10337Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 17 is set"
	::= 10337

dpsRTUp11337Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 17 is cleared"
	::= 11337

dpsRTUp10338Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 18 is set"
	::= 10338

dpsRTUp11338Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 18 is cleared"
	::= 11338

dpsRTUp10339Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 19 is set"
	::= 10339

dpsRTUp11339Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 19 is cleared"
	::= 11339

dpsRTUp10340Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 20 is set"
	::= 10340

dpsRTUp11340Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 20 is cleared"
	::= 11340

dpsRTUp10341Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 21 is set"
	::= 10341

dpsRTUp11341Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 21 is cleared"
	::= 11341

dpsRTUp10342Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 22 is set"
	::= 10342

dpsRTUp11342Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 22 is cleared"
	::= 11342

dpsRTUp10343Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 23 is set"
	::= 10343

dpsRTUp11343Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 23 is cleared"
	::= 11343

dpsRTUp10344Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 24 is set"
	::= 10344

dpsRTUp11344Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 24 is cleared"
	::= 11344

dpsRTUp10345Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 25 is set"
	::= 10345

dpsRTUp11345Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 25 is cleared"
	::= 11345

dpsRTUp10346Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 26 is set"
	::= 10346

dpsRTUp11346Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 26 is cleared"
	::= 11346

dpsRTUp10347Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 27 is set"
	::= 10347

dpsRTUp11347Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 27 is cleared"
	::= 11347

dpsRTUp10348Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 28 is set"
	::= 10348

dpsRTUp11348Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 28 is cleared"
	::= 11348

dpsRTUp10349Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 29 is set"
	::= 10349

dpsRTUp11349Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 29 is cleared"
	::= 11349

dpsRTUp10350Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 30 is set"
	::= 10350

dpsRTUp11350Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 30 is cleared"
	::= 11350

dpsRTUp10351Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 31 is set"
	::= 10351

dpsRTUp11351Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 31 is cleared"
	::= 11351

dpsRTUp10352Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 32 is set"
	::= 10352

dpsRTUp11352Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 32 is cleared"
	::= 11352

dpsRTUp10353Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 33 is set"
	::= 10353

dpsRTUp11353Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 33 is cleared"
	::= 11353

dpsRTUp10354Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 34 is set"
	::= 10354

dpsRTUp11354Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 34 is cleared"
	::= 11354

dpsRTUp10355Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 35 is set"
	::= 10355

dpsRTUp11355Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 35 is cleared"
	::= 11355

dpsRTUp10356Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 36 is set"
	::= 10356

dpsRTUp11356Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 36 is cleared"
	::= 11356

dpsRTUp10357Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 37 is set"
	::= 10357

dpsRTUp11357Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 37 is cleared"
	::= 11357

dpsRTUp10358Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 38 is set"
	::= 10358

dpsRTUp11358Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 38 is cleared"
	::= 11358

dpsRTUp10359Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 39 is set"
	::= 10359

dpsRTUp11359Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 39 is cleared"
	::= 11359

dpsRTUp10360Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 40 is set"
	::= 10360

dpsRTUp11360Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 40 is cleared"
	::= 11360

dpsRTUp10361Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 41 is set"
	::= 10361

dpsRTUp11361Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 41 is cleared"
	::= 11361

dpsRTUp10362Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 42 is set"
	::= 10362

dpsRTUp11362Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 42 is cleared"
	::= 11362

dpsRTUp10363Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 43 is set"
	::= 10363

dpsRTUp11363Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 43 is cleared"
	::= 11363

dpsRTUp10364Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 44 is set"
	::= 10364

dpsRTUp11364Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 44 is cleared"
	::= 11364

dpsRTUp10365Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 45 is set"
	::= 10365

dpsRTUp11365Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 45 is cleared"
	::= 11365

dpsRTUp10366Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 46 is set"
	::= 10366

dpsRTUp11366Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 46 is cleared"
	::= 11366

dpsRTUp10367Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 47 is set"
	::= 10367

dpsRTUp11367Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 47 is cleared"
	::= 11367

dpsRTUp10368Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 48 is set"
	::= 10368

dpsRTUp11368Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 48 is cleared"
	::= 11368

dpsRTUp10369Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 49 is set"
	::= 10369

dpsRTUp11369Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 49 is cleared"
	::= 11369

dpsRTUp10370Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 50 is set"
	::= 10370

dpsRTUp11370Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 50 is cleared"
	::= 11370

dpsRTUp10371Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 51 is set"
	::= 10371

dpsRTUp11371Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 51 is cleared"
	::= 11371

dpsRTUp10372Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 52 is set"
	::= 10372

dpsRTUp11372Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 52 is cleared"
	::= 11372

dpsRTUp10373Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 53 is set"
	::= 10373

dpsRTUp11373Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 53 is cleared"
	::= 11373

dpsRTUp10374Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 54 is set"
	::= 10374

dpsRTUp11374Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 54 is cleared"
	::= 11374

dpsRTUp10375Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 55 is set"
	::= 10375

dpsRTUp11375Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 55 is cleared"
	::= 11375

dpsRTUp10376Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 56 is set"
	::= 10376

dpsRTUp11376Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 56 is cleared"
	::= 11376

dpsRTUp10377Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 57 is set"
	::= 10377

dpsRTUp11377Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 57 is cleared"
	::= 11377

dpsRTUp10378Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 58 is set"
	::= 10378

dpsRTUp11378Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 58 is cleared"
	::= 11378

dpsRTUp10379Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 59 is set"
	::= 10379

dpsRTUp11379Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 59 is cleared"
	::= 11379

dpsRTUp10380Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 60 is set"
	::= 10380

dpsRTUp11380Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 60 is cleared"
	::= 11380

dpsRTUp10381Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 61 is set"
	::= 10381

dpsRTUp11381Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 61 is cleared"
	::= 11381

dpsRTUp10382Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 62 is set"
	::= 10382

dpsRTUp11382Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 62 is cleared"
	::= 11382

dpsRTUp10383Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 63 is set"
	::= 10383

dpsRTUp11383Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 63 is cleared"
	::= 11383

dpsRTUp10384Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 64 is set"
	::= 10384

dpsRTUp11384Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 6 point 64 is cleared"
	::= 11384

dpsRTUp10385Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 1 is set"
	::= 10385

dpsRTUp11385Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 1 is cleared"
	::= 11385

dpsRTUp10386Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 2 is set"
	::= 10386

dpsRTUp11386Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 2 is cleared"
	::= 11386

dpsRTUp10387Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 3 is set"
	::= 10387

dpsRTUp11387Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 3 is cleared"
	::= 11387

dpsRTUp10388Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 4 is set"
	::= 10388

dpsRTUp11388Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 4 is cleared"
	::= 11388

dpsRTUp10389Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 5 is set"
	::= 10389

dpsRTUp11389Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 5 is cleared"
	::= 11389

dpsRTUp10390Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 6 is set"
	::= 10390

dpsRTUp11390Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 6 is cleared"
	::= 11390

dpsRTUp10391Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 7 is set"
	::= 10391

dpsRTUp11391Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 7 is cleared"
	::= 11391

dpsRTUp10392Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 8 is set"
	::= 10392

dpsRTUp11392Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 8 is cleared"
	::= 11392

dpsRTUp10393Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 9 is set"
	::= 10393

dpsRTUp11393Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 9 is cleared"
	::= 11393

dpsRTUp10394Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 10 is set"
	::= 10394

dpsRTUp11394Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 10 is cleared"
	::= 11394

dpsRTUp10395Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 11 is set"
	::= 10395

dpsRTUp11395Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 11 is cleared"
	::= 11395

dpsRTUp10396Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 12 is set"
	::= 10396

dpsRTUp11396Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 12 is cleared"
	::= 11396

dpsRTUp10397Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 13 is set"
	::= 10397

dpsRTUp11397Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 13 is cleared"
	::= 11397

dpsRTUp10398Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 14 is set"
	::= 10398

dpsRTUp11398Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 14 is cleared"
	::= 11398

dpsRTUp10399Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 15 is set"
	::= 10399

dpsRTUp11399Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 15 is cleared"
	::= 11399

dpsRTUp10400Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 16 is set"
	::= 10400

dpsRTUp11400Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 16 is cleared"
	::= 11400

dpsRTUp10401Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 17 is set"
	::= 10401

dpsRTUp11401Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 17 is cleared"
	::= 11401

dpsRTUp10402Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 18 is set"
	::= 10402

dpsRTUp11402Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 18 is cleared"
	::= 11402

dpsRTUp10403Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 19 is set"
	::= 10403

dpsRTUp11403Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 19 is cleared"
	::= 11403

dpsRTUp10404Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 20 is set"
	::= 10404

dpsRTUp11404Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 20 is cleared"
	::= 11404

dpsRTUp10405Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 21 is set"
	::= 10405

dpsRTUp11405Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 21 is cleared"
	::= 11405

dpsRTUp10406Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 22 is set"
	::= 10406

dpsRTUp11406Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 22 is cleared"
	::= 11406

dpsRTUp10407Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 23 is set"
	::= 10407

dpsRTUp11407Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 23 is cleared"
	::= 11407

dpsRTUp10408Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 24 is set"
	::= 10408

dpsRTUp11408Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 24 is cleared"
	::= 11408

dpsRTUp10409Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 25 is set"
	::= 10409

dpsRTUp11409Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 25 is cleared"
	::= 11409

dpsRTUp10410Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 26 is set"
	::= 10410

dpsRTUp11410Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 26 is cleared"
	::= 11410

dpsRTUp10411Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 27 is set"
	::= 10411

dpsRTUp11411Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 27 is cleared"
	::= 11411

dpsRTUp10412Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 28 is set"
	::= 10412

dpsRTUp11412Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 28 is cleared"
	::= 11412

dpsRTUp10413Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 29 is set"
	::= 10413

dpsRTUp11413Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 29 is cleared"
	::= 11413

dpsRTUp10414Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 30 is set"
	::= 10414

dpsRTUp11414Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 30 is cleared"
	::= 11414

dpsRTUp10415Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 31 is set"
	::= 10415

dpsRTUp11415Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 31 is cleared"
	::= 11415

dpsRTUp10416Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 32 is set"
	::= 10416

dpsRTUp11416Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 32 is cleared"
	::= 11416

dpsRTUp10417Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 33 is set"
	::= 10417

dpsRTUp11417Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 33 is cleared"
	::= 11417

dpsRTUp10418Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 34 is set"
	::= 10418

dpsRTUp11418Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 34 is cleared"
	::= 11418

dpsRTUp10419Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 35 is set"
	::= 10419

dpsRTUp11419Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 35 is cleared"
	::= 11419

dpsRTUp10420Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 36 is set"
	::= 10420

dpsRTUp11420Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 36 is cleared"
	::= 11420

dpsRTUp10421Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 37 is set"
	::= 10421

dpsRTUp11421Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 37 is cleared"
	::= 11421

dpsRTUp10422Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 38 is set"
	::= 10422

dpsRTUp11422Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 38 is cleared"
	::= 11422

dpsRTUp10423Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 39 is set"
	::= 10423

dpsRTUp11423Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 39 is cleared"
	::= 11423

dpsRTUp10424Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 40 is set"
	::= 10424

dpsRTUp11424Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 40 is cleared"
	::= 11424

dpsRTUp10425Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 41 is set"
	::= 10425

dpsRTUp11425Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 41 is cleared"
	::= 11425

dpsRTUp10426Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 42 is set"
	::= 10426

dpsRTUp11426Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 42 is cleared"
	::= 11426

dpsRTUp10427Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 43 is set"
	::= 10427

dpsRTUp11427Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 43 is cleared"
	::= 11427

dpsRTUp10428Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 44 is set"
	::= 10428

dpsRTUp11428Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 44 is cleared"
	::= 11428

dpsRTUp10429Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 45 is set"
	::= 10429

dpsRTUp11429Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 45 is cleared"
	::= 11429

dpsRTUp10430Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 46 is set"
	::= 10430

dpsRTUp11430Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 46 is cleared"
	::= 11430

dpsRTUp10431Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 47 is set"
	::= 10431

dpsRTUp11431Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 47 is cleared"
	::= 11431

dpsRTUp10432Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 48 is set"
	::= 10432

dpsRTUp11432Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 48 is cleared"
	::= 11432

dpsRTUp10433Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 49 is set"
	::= 10433

dpsRTUp11433Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 49 is cleared"
	::= 11433

dpsRTUp10434Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 50 is set"
	::= 10434

dpsRTUp11434Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 50 is cleared"
	::= 11434

dpsRTUp10435Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 51 is set"
	::= 10435

dpsRTUp11435Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 51 is cleared"
	::= 11435

dpsRTUp10436Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 52 is set"
	::= 10436

dpsRTUp11436Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 52 is cleared"
	::= 11436

dpsRTUp10437Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 53 is set"
	::= 10437

dpsRTUp11437Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 53 is cleared"
	::= 11437

dpsRTUp10438Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 54 is set"
	::= 10438

dpsRTUp11438Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 54 is cleared"
	::= 11438

dpsRTUp10439Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 55 is set"
	::= 10439

dpsRTUp11439Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 55 is cleared"
	::= 11439

dpsRTUp10440Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 56 is set"
	::= 10440

dpsRTUp11440Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 56 is cleared"
	::= 11440

dpsRTUp10441Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 57 is set"
	::= 10441

dpsRTUp11441Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 57 is cleared"
	::= 11441

dpsRTUp10442Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 58 is set"
	::= 10442

dpsRTUp11442Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 58 is cleared"
	::= 11442

dpsRTUp10443Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 59 is set"
	::= 10443

dpsRTUp11443Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 59 is cleared"
	::= 11443

dpsRTUp10444Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 60 is set"
	::= 10444

dpsRTUp11444Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 60 is cleared"
	::= 11444

dpsRTUp10445Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 61 is set"
	::= 10445

dpsRTUp11445Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 61 is cleared"
	::= 11445

dpsRTUp10446Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 62 is set"
	::= 10446

dpsRTUp11446Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 62 is cleared"
	::= 11446

dpsRTUp10447Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 63 is set"
	::= 10447

dpsRTUp11447Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 63 is cleared"
	::= 11447

dpsRTUp10448Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 64 is set"
	::= 10448

dpsRTUp11448Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 7 point 64 is cleared"
	::= 11448

dpsRTUp10449Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 1 is set"
	::= 10449

dpsRTUp11449Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 1 is cleared"
	::= 11449

dpsRTUp10450Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 2 is set"
	::= 10450

dpsRTUp11450Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 2 is cleared"
	::= 11450

dpsRTUp10451Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 3 is set"
	::= 10451

dpsRTUp11451Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 3 is cleared"
	::= 11451

dpsRTUp10452Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 4 is set"
	::= 10452

dpsRTUp11452Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 4 is cleared"
	::= 11452

dpsRTUp10453Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 5 is set"
	::= 10453

dpsRTUp11453Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 5 is cleared"
	::= 11453

dpsRTUp10454Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 6 is set"
	::= 10454

dpsRTUp11454Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 6 is cleared"
	::= 11454

dpsRTUp10455Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 7 is set"
	::= 10455

dpsRTUp11455Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 7 is cleared"
	::= 11455

dpsRTUp10456Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 8 is set"
	::= 10456

dpsRTUp11456Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 8 is cleared"
	::= 11456

dpsRTUp10457Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 9 is set"
	::= 10457

dpsRTUp11457Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 9 is cleared"
	::= 11457

dpsRTUp10458Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 10 is set"
	::= 10458

dpsRTUp11458Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 10 is cleared"
	::= 11458

dpsRTUp10459Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 11 is set"
	::= 10459

dpsRTUp11459Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 11 is cleared"
	::= 11459

dpsRTUp10460Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 12 is set"
	::= 10460

dpsRTUp11460Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 12 is cleared"
	::= 11460

dpsRTUp10461Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 13 is set"
	::= 10461

dpsRTUp11461Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 13 is cleared"
	::= 11461

dpsRTUp10462Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 14 is set"
	::= 10462

dpsRTUp11462Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 14 is cleared"
	::= 11462

dpsRTUp10463Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 15 is set"
	::= 10463

dpsRTUp11463Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 15 is cleared"
	::= 11463

dpsRTUp10464Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 16 is set"
	::= 10464

dpsRTUp11464Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 16 is cleared"
	::= 11464

dpsRTUp10465Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 17 is set"
	::= 10465

dpsRTUp11465Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 17 is cleared"
	::= 11465

dpsRTUp10466Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 18 is set"
	::= 10466

dpsRTUp11466Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 18 is cleared"
	::= 11466

dpsRTUp10467Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 19 is set"
	::= 10467

dpsRTUp11467Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 19 is cleared"
	::= 11467

dpsRTUp10468Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 20 is set"
	::= 10468

dpsRTUp11468Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 20 is cleared"
	::= 11468

dpsRTUp10469Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 21 is set"
	::= 10469

dpsRTUp11469Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 21 is cleared"
	::= 11469

dpsRTUp10470Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 22 is set"
	::= 10470

dpsRTUp11470Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 22 is cleared"
	::= 11470

dpsRTUp10471Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 23 is set"
	::= 10471

dpsRTUp11471Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 23 is cleared"
	::= 11471

dpsRTUp10472Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 24 is set"
	::= 10472

dpsRTUp11472Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 24 is cleared"
	::= 11472

dpsRTUp10473Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 25 is set"
	::= 10473

dpsRTUp11473Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 25 is cleared"
	::= 11473

dpsRTUp10474Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 26 is set"
	::= 10474

dpsRTUp11474Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 26 is cleared"
	::= 11474

dpsRTUp10475Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 27 is set"
	::= 10475

dpsRTUp11475Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 27 is cleared"
	::= 11475

dpsRTUp10476Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 28 is set"
	::= 10476

dpsRTUp11476Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 28 is cleared"
	::= 11476

dpsRTUp10477Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 29 is set"
	::= 10477

dpsRTUp11477Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 29 is cleared"
	::= 11477

dpsRTUp10478Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 30 is set"
	::= 10478

dpsRTUp11478Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 30 is cleared"
	::= 11478

dpsRTUp10479Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 31 is set"
	::= 10479

dpsRTUp11479Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 31 is cleared"
	::= 11479

dpsRTUp10480Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 32 is set"
	::= 10480

dpsRTUp11480Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 32 is cleared"
	::= 11480

dpsRTUp10481Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 33 is set"
	::= 10481

dpsRTUp11481Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 33 is cleared"
	::= 11481

dpsRTUp10482Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 34 is set"
	::= 10482

dpsRTUp11482Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 34 is cleared"
	::= 11482

dpsRTUp10483Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 35 is set"
	::= 10483

dpsRTUp11483Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 35 is cleared"
	::= 11483

dpsRTUp10484Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 36 is set"
	::= 10484

dpsRTUp11484Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 36 is cleared"
	::= 11484

dpsRTUp10485Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 37 is set"
	::= 10485

dpsRTUp11485Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 37 is cleared"
	::= 11485

dpsRTUp10486Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 38 is set"
	::= 10486

dpsRTUp11486Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 38 is cleared"
	::= 11486

dpsRTUp10487Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 39 is set"
	::= 10487

dpsRTUp11487Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 39 is cleared"
	::= 11487

dpsRTUp10488Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 40 is set"
	::= 10488

dpsRTUp11488Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 40 is cleared"
	::= 11488

dpsRTUp10489Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 41 is set"
	::= 10489

dpsRTUp11489Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 41 is cleared"
	::= 11489

dpsRTUp10490Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 42 is set"
	::= 10490

dpsRTUp11490Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 42 is cleared"
	::= 11490

dpsRTUp10491Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 43 is set"
	::= 10491

dpsRTUp11491Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 43 is cleared"
	::= 11491

dpsRTUp10492Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 44 is set"
	::= 10492

dpsRTUp11492Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 44 is cleared"
	::= 11492

dpsRTUp10493Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 45 is set"
	::= 10493

dpsRTUp11493Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 45 is cleared"
	::= 11493

dpsRTUp10494Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 46 is set"
	::= 10494

dpsRTUp11494Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 46 is cleared"
	::= 11494

dpsRTUp10495Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 47 is set"
	::= 10495

dpsRTUp11495Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 47 is cleared"
	::= 11495

dpsRTUp10496Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 48 is set"
	::= 10496

dpsRTUp11496Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 48 is cleared"
	::= 11496

dpsRTUp10497Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 49 is set"
	::= 10497

dpsRTUp11497Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 49 is cleared"
	::= 11497

dpsRTUp10498Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 50 is set"
	::= 10498

dpsRTUp11498Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 50 is cleared"
	::= 11498

dpsRTUp10499Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 51 is set"
	::= 10499

dpsRTUp11499Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 51 is cleared"
	::= 11499

dpsRTUp10500Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 52 is set"
	::= 10500

dpsRTUp11500Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 52 is cleared"
	::= 11500

dpsRTUp10501Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 53 is set"
	::= 10501

dpsRTUp11501Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 53 is cleared"
	::= 11501

dpsRTUp10502Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 54 is set"
	::= 10502

dpsRTUp11502Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 54 is cleared"
	::= 11502

dpsRTUp10503Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 55 is set"
	::= 10503

dpsRTUp11503Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 55 is cleared"
	::= 11503

dpsRTUp10504Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 56 is set"
	::= 10504

dpsRTUp11504Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 56 is cleared"
	::= 11504

dpsRTUp10505Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 57 is set"
	::= 10505

dpsRTUp11505Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 57 is cleared"
	::= 11505

dpsRTUp10506Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 58 is set"
	::= 10506

dpsRTUp11506Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 58 is cleared"
	::= 11506

dpsRTUp10507Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 59 is set"
	::= 10507

dpsRTUp11507Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 59 is cleared"
	::= 11507

dpsRTUp10508Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 60 is set"
	::= 10508

dpsRTUp11508Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 60 is cleared"
	::= 11508

dpsRTUp10509Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 61 is set"
	::= 10509

dpsRTUp11509Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 61 is cleared"
	::= 11509

dpsRTUp10510Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 62 is set"
	::= 10510

dpsRTUp11510Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 62 is cleared"
	::= 11510

dpsRTUp10511Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 63 is set"
	::= 10511

dpsRTUp11511Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 63 is cleared"
	::= 11511

dpsRTUp10512Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 64 is set"
	::= 10512

dpsRTUp11512Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 1 display 8 point 64 is cleared"
	::= 11512
dpsRTUp12001Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 1 is set"
	::= 12001

dpsRTUp13001Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 1 is cleared"
	::= 13001

dpsRTUp12002Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 2 is set"
	::= 12002

dpsRTUp13002Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 2 is cleared"
	::= 13002

dpsRTUp12003Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 3 is set"
	::= 12003

dpsRTUp13003Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 3 is cleared"
	::= 13003

dpsRTUp12004Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 4 is set"
	::= 12004

dpsRTUp13004Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 4 is cleared"
	::= 13004

dpsRTUp12005Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 5 is set"
	::= 12005

dpsRTUp13005Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 5 is cleared"
	::= 13005

dpsRTUp12006Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 6 is set"
	::= 12006

dpsRTUp13006Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 6 is cleared"
	::= 13006

dpsRTUp12007Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 7 is set"
	::= 12007

dpsRTUp13007Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 7 is cleared"
	::= 13007

dpsRTUp12008Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 8 is set"
	::= 12008

dpsRTUp13008Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 8 is cleared"
	::= 13008

dpsRTUp12009Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 9 is set"
	::= 12009

dpsRTUp13009Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 9 is cleared"
	::= 13009

dpsRTUp12010Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 10 is set"
	::= 12010

dpsRTUp13010Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 10 is cleared"
	::= 13010

dpsRTUp12011Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 11 is set"
	::= 12011

dpsRTUp13011Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 11 is cleared"
	::= 13011

dpsRTUp12012Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 12 is set"
	::= 12012

dpsRTUp13012Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 12 is cleared"
	::= 13012

dpsRTUp12013Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 13 is set"
	::= 12013

dpsRTUp13013Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 13 is cleared"
	::= 13013

dpsRTUp12014Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 14 is set"
	::= 12014

dpsRTUp13014Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 14 is cleared"
	::= 13014

dpsRTUp12015Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 15 is set"
	::= 12015

dpsRTUp13015Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 15 is cleared"
	::= 13015

dpsRTUp12016Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 16 is set"
	::= 12016

dpsRTUp13016Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 16 is cleared"
	::= 13016

dpsRTUp12017Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 17 is set"
	::= 12017

dpsRTUp13017Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 17 is cleared"
	::= 13017

dpsRTUp12018Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 18 is set"
	::= 12018

dpsRTUp13018Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 18 is cleared"
	::= 13018

dpsRTUp12019Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 19 is set"
	::= 12019

dpsRTUp13019Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 19 is cleared"
	::= 13019

dpsRTUp12020Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 20 is set"
	::= 12020

dpsRTUp13020Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 20 is cleared"
	::= 13020

dpsRTUp12021Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 21 is set"
	::= 12021

dpsRTUp13021Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 21 is cleared"
	::= 13021

dpsRTUp12022Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 22 is set"
	::= 12022

dpsRTUp13022Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 22 is cleared"
	::= 13022

dpsRTUp12023Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 23 is set"
	::= 12023

dpsRTUp13023Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 23 is cleared"
	::= 13023

dpsRTUp12024Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 24 is set"
	::= 12024

dpsRTUp13024Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 24 is cleared"
	::= 13024

dpsRTUp12025Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 25 is set"
	::= 12025

dpsRTUp13025Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 25 is cleared"
	::= 13025

dpsRTUp12026Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 26 is set"
	::= 12026

dpsRTUp13026Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 26 is cleared"
	::= 13026

dpsRTUp12027Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 27 is set"
	::= 12027

dpsRTUp13027Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 27 is cleared"
	::= 13027

dpsRTUp12028Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 28 is set"
	::= 12028

dpsRTUp13028Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 28 is cleared"
	::= 13028

dpsRTUp12029Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 29 is set"
	::= 12029

dpsRTUp13029Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 29 is cleared"
	::= 13029

dpsRTUp12030Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 30 is set"
	::= 12030

dpsRTUp13030Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 30 is cleared"
	::= 13030

dpsRTUp12031Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 31 is set"
	::= 12031

dpsRTUp13031Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 31 is cleared"
	::= 13031

dpsRTUp12032Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 32 is set"
	::= 12032

dpsRTUp13032Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 32 is cleared"
	::= 13032

dpsRTUp12033Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 33 is set"
	::= 12033

dpsRTUp13033Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 33 is cleared"
	::= 13033

dpsRTUp12034Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 34 is set"
	::= 12034

dpsRTUp13034Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 34 is cleared"
	::= 13034

dpsRTUp12035Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 35 is set"
	::= 12035

dpsRTUp13035Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 35 is cleared"
	::= 13035

dpsRTUp12036Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 36 is set"
	::= 12036

dpsRTUp13036Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 36 is cleared"
	::= 13036

dpsRTUp12037Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 37 is set"
	::= 12037

dpsRTUp13037Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 37 is cleared"
	::= 13037

dpsRTUp12038Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 38 is set"
	::= 12038

dpsRTUp13038Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 38 is cleared"
	::= 13038

dpsRTUp12039Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 39 is set"
	::= 12039

dpsRTUp13039Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 39 is cleared"
	::= 13039

dpsRTUp12040Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 40 is set"
	::= 12040

dpsRTUp13040Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 40 is cleared"
	::= 13040

dpsRTUp12041Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 41 is set"
	::= 12041

dpsRTUp13041Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 41 is cleared"
	::= 13041

dpsRTUp12042Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 42 is set"
	::= 12042

dpsRTUp13042Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 42 is cleared"
	::= 13042

dpsRTUp12043Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 43 is set"
	::= 12043

dpsRTUp13043Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 43 is cleared"
	::= 13043

dpsRTUp12044Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 44 is set"
	::= 12044

dpsRTUp13044Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 44 is cleared"
	::= 13044

dpsRTUp12045Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 45 is set"
	::= 12045

dpsRTUp13045Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 45 is cleared"
	::= 13045

dpsRTUp12046Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 46 is set"
	::= 12046

dpsRTUp13046Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 46 is cleared"
	::= 13046

dpsRTUp12047Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 47 is set"
	::= 12047

dpsRTUp13047Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 47 is cleared"
	::= 13047

dpsRTUp12048Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 48 is set"
	::= 12048

dpsRTUp13048Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 48 is cleared"
	::= 13048

dpsRTUp12049Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 49 is set"
	::= 12049

dpsRTUp13049Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 49 is cleared"
	::= 13049

dpsRTUp12050Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 50 is set"
	::= 12050

dpsRTUp13050Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 50 is cleared"
	::= 13050

dpsRTUp12051Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 51 is set"
	::= 12051

dpsRTUp13051Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 51 is cleared"
	::= 13051

dpsRTUp12052Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 52 is set"
	::= 12052

dpsRTUp13052Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 52 is cleared"
	::= 13052

dpsRTUp12053Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 53 is set"
	::= 12053

dpsRTUp13053Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 53 is cleared"
	::= 13053

dpsRTUp12054Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 54 is set"
	::= 12054

dpsRTUp13054Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 54 is cleared"
	::= 13054

dpsRTUp12055Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 55 is set"
	::= 12055

dpsRTUp13055Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 55 is cleared"
	::= 13055

dpsRTUp12056Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 56 is set"
	::= 12056

dpsRTUp13056Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 56 is cleared"
	::= 13056

dpsRTUp12057Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 57 is set"
	::= 12057

dpsRTUp13057Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 57 is cleared"
	::= 13057

dpsRTUp12058Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 58 is set"
	::= 12058

dpsRTUp13058Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 58 is cleared"
	::= 13058

dpsRTUp12059Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 59 is set"
	::= 12059

dpsRTUp13059Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 59 is cleared"
	::= 13059

dpsRTUp12060Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 60 is set"
	::= 12060

dpsRTUp13060Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 60 is cleared"
	::= 13060

dpsRTUp12061Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 61 is set"
	::= 12061

dpsRTUp13061Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 61 is cleared"
	::= 13061

dpsRTUp12062Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 62 is set"
	::= 12062

dpsRTUp13062Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 62 is cleared"
	::= 13062

dpsRTUp12063Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 63 is set"
	::= 12063

dpsRTUp13063Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 63 is cleared"
	::= 13063

dpsRTUp12064Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 64 is set"
	::= 12064

dpsRTUp13064Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 1 point 64 is cleared"
	::= 13064

dpsRTUp12065Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 1 is set"
	::= 12065

dpsRTUp13065Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 1 is cleared"
	::= 13065

dpsRTUp12066Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 2 is set"
	::= 12066

dpsRTUp13066Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 2 is cleared"
	::= 13066

dpsRTUp12067Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 3 is set"
	::= 12067

dpsRTUp13067Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 3 is cleared"
	::= 13067

dpsRTUp12068Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 4 is set"
	::= 12068

dpsRTUp13068Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 4 is cleared"
	::= 13068

dpsRTUp12069Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 5 is set"
	::= 12069

dpsRTUp13069Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 5 is cleared"
	::= 13069

dpsRTUp12070Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 6 is set"
	::= 12070

dpsRTUp13070Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 6 is cleared"
	::= 13070

dpsRTUp12071Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 7 is set"
	::= 12071

dpsRTUp13071Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 7 is cleared"
	::= 13071

dpsRTUp12072Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 8 is set"
	::= 12072

dpsRTUp13072Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 8 is cleared"
	::= 13072

dpsRTUp12073Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 9 is set"
	::= 12073

dpsRTUp13073Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 9 is cleared"
	::= 13073

dpsRTUp12074Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 10 is set"
	::= 12074

dpsRTUp13074Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 10 is cleared"
	::= 13074

dpsRTUp12075Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 11 is set"
	::= 12075

dpsRTUp13075Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 11 is cleared"
	::= 13075

dpsRTUp12076Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 12 is set"
	::= 12076

dpsRTUp13076Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 12 is cleared"
	::= 13076

dpsRTUp12077Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 13 is set"
	::= 12077

dpsRTUp13077Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 13 is cleared"
	::= 13077

dpsRTUp12078Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 14 is set"
	::= 12078

dpsRTUp13078Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 14 is cleared"
	::= 13078

dpsRTUp12079Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 15 is set"
	::= 12079

dpsRTUp13079Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 15 is cleared"
	::= 13079

dpsRTUp12080Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 16 is set"
	::= 12080

dpsRTUp13080Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 16 is cleared"
	::= 13080

dpsRTUp12081Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 17 is set"
	::= 12081

dpsRTUp13081Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 17 is cleared"
	::= 13081

dpsRTUp12082Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 18 is set"
	::= 12082

dpsRTUp13082Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 18 is cleared"
	::= 13082

dpsRTUp12083Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 19 is set"
	::= 12083

dpsRTUp13083Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 19 is cleared"
	::= 13083

dpsRTUp12084Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 20 is set"
	::= 12084

dpsRTUp13084Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 20 is cleared"
	::= 13084

dpsRTUp12085Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 21 is set"
	::= 12085

dpsRTUp13085Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 21 is cleared"
	::= 13085

dpsRTUp12086Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 22 is set"
	::= 12086

dpsRTUp13086Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 22 is cleared"
	::= 13086

dpsRTUp12087Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 23 is set"
	::= 12087

dpsRTUp13087Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 23 is cleared"
	::= 13087

dpsRTUp12088Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 24 is set"
	::= 12088

dpsRTUp13088Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 24 is cleared"
	::= 13088

dpsRTUp12089Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 25 is set"
	::= 12089

dpsRTUp13089Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 25 is cleared"
	::= 13089

dpsRTUp12090Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 26 is set"
	::= 12090

dpsRTUp13090Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 26 is cleared"
	::= 13090

dpsRTUp12091Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 27 is set"
	::= 12091

dpsRTUp13091Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 27 is cleared"
	::= 13091

dpsRTUp12092Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 28 is set"
	::= 12092

dpsRTUp13092Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 28 is cleared"
	::= 13092

dpsRTUp12093Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 29 is set"
	::= 12093

dpsRTUp13093Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 29 is cleared"
	::= 13093

dpsRTUp12094Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 30 is set"
	::= 12094

dpsRTUp13094Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 30 is cleared"
	::= 13094

dpsRTUp12095Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 31 is set"
	::= 12095

dpsRTUp13095Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 31 is cleared"
	::= 13095

dpsRTUp12096Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 32 is set"
	::= 12096

dpsRTUp13096Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 32 is cleared"
	::= 13096

dpsRTUp12097Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 33 is set"
	::= 12097

dpsRTUp13097Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 33 is cleared"
	::= 13097

dpsRTUp12098Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 34 is set"
	::= 12098

dpsRTUp13098Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 34 is cleared"
	::= 13098

dpsRTUp12099Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 35 is set"
	::= 12099

dpsRTUp13099Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 35 is cleared"
	::= 13099

dpsRTUp12100Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 36 is set"
	::= 12100

dpsRTUp13100Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 36 is cleared"
	::= 13100

dpsRTUp12101Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 37 is set"
	::= 12101

dpsRTUp13101Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 37 is cleared"
	::= 13101

dpsRTUp12102Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 38 is set"
	::= 12102

dpsRTUp13102Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 38 is cleared"
	::= 13102

dpsRTUp12103Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 39 is set"
	::= 12103

dpsRTUp13103Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 39 is cleared"
	::= 13103

dpsRTUp12104Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 40 is set"
	::= 12104

dpsRTUp13104Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 40 is cleared"
	::= 13104

dpsRTUp12105Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 41 is set"
	::= 12105

dpsRTUp13105Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 41 is cleared"
	::= 13105

dpsRTUp12106Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 42 is set"
	::= 12106

dpsRTUp13106Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 42 is cleared"
	::= 13106

dpsRTUp12107Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 43 is set"
	::= 12107

dpsRTUp13107Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 43 is cleared"
	::= 13107

dpsRTUp12108Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 44 is set"
	::= 12108

dpsRTUp13108Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 44 is cleared"
	::= 13108

dpsRTUp12109Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 45 is set"
	::= 12109

dpsRTUp13109Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 45 is cleared"
	::= 13109

dpsRTUp12110Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 46 is set"
	::= 12110

dpsRTUp13110Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 46 is cleared"
	::= 13110

dpsRTUp12111Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 47 is set"
	::= 12111

dpsRTUp13111Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 47 is cleared"
	::= 13111

dpsRTUp12112Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 48 is set"
	::= 12112

dpsRTUp13112Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 48 is cleared"
	::= 13112

dpsRTUp12113Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 49 is set"
	::= 12113

dpsRTUp13113Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 49 is cleared"
	::= 13113

dpsRTUp12114Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 50 is set"
	::= 12114

dpsRTUp13114Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 50 is cleared"
	::= 13114

dpsRTUp12115Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 51 is set"
	::= 12115

dpsRTUp13115Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 51 is cleared"
	::= 13115

dpsRTUp12116Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 52 is set"
	::= 12116

dpsRTUp13116Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 52 is cleared"
	::= 13116

dpsRTUp12117Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 53 is set"
	::= 12117

dpsRTUp13117Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 53 is cleared"
	::= 13117

dpsRTUp12118Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 54 is set"
	::= 12118

dpsRTUp13118Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 54 is cleared"
	::= 13118

dpsRTUp12119Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 55 is set"
	::= 12119

dpsRTUp13119Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 55 is cleared"
	::= 13119

dpsRTUp12120Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 56 is set"
	::= 12120

dpsRTUp13120Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 56 is cleared"
	::= 13120

dpsRTUp12121Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 57 is set"
	::= 12121

dpsRTUp13121Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 57 is cleared"
	::= 13121

dpsRTUp12122Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 58 is set"
	::= 12122

dpsRTUp13122Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 58 is cleared"
	::= 13122

dpsRTUp12123Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 59 is set"
	::= 12123

dpsRTUp13123Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 59 is cleared"
	::= 13123

dpsRTUp12124Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 60 is set"
	::= 12124

dpsRTUp13124Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 60 is cleared"
	::= 13124

dpsRTUp12125Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 61 is set"
	::= 12125

dpsRTUp13125Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 61 is cleared"
	::= 13125

dpsRTUp12126Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 62 is set"
	::= 12126

dpsRTUp13126Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 62 is cleared"
	::= 13126

dpsRTUp12127Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 63 is set"
	::= 12127

dpsRTUp13127Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 63 is cleared"
	::= 13127

dpsRTUp12128Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 64 is set"
	::= 12128

dpsRTUp13128Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 2 point 64 is cleared"
	::= 13128

dpsRTUp12129Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 1 is set"
	::= 12129

dpsRTUp13129Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 1 is cleared"
	::= 13129

dpsRTUp12130Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 2 is set"
	::= 12130

dpsRTUp13130Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 2 is cleared"
	::= 13130

dpsRTUp12131Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 3 is set"
	::= 12131

dpsRTUp13131Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 3 is cleared"
	::= 13131

dpsRTUp12132Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 4 is set"
	::= 12132

dpsRTUp13132Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 4 is cleared"
	::= 13132

dpsRTUp12133Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 5 is set"
	::= 12133

dpsRTUp13133Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 5 is cleared"
	::= 13133

dpsRTUp12134Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 6 is set"
	::= 12134

dpsRTUp13134Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 6 is cleared"
	::= 13134

dpsRTUp12135Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 7 is set"
	::= 12135

dpsRTUp13135Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 7 is cleared"
	::= 13135

dpsRTUp12136Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 8 is set"
	::= 12136

dpsRTUp13136Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 8 is cleared"
	::= 13136

dpsRTUp12137Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 9 is set"
	::= 12137

dpsRTUp13137Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 9 is cleared"
	::= 13137

dpsRTUp12138Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 10 is set"
	::= 12138

dpsRTUp13138Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 10 is cleared"
	::= 13138

dpsRTUp12139Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 11 is set"
	::= 12139

dpsRTUp13139Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 11 is cleared"
	::= 13139

dpsRTUp12140Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 12 is set"
	::= 12140

dpsRTUp13140Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 12 is cleared"
	::= 13140

dpsRTUp12141Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 13 is set"
	::= 12141

dpsRTUp13141Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 13 is cleared"
	::= 13141

dpsRTUp12142Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 14 is set"
	::= 12142

dpsRTUp13142Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 14 is cleared"
	::= 13142

dpsRTUp12143Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 15 is set"
	::= 12143

dpsRTUp13143Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 15 is cleared"
	::= 13143

dpsRTUp12144Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 16 is set"
	::= 12144

dpsRTUp13144Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 16 is cleared"
	::= 13144

dpsRTUp12145Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 17 is set"
	::= 12145

dpsRTUp13145Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 17 is cleared"
	::= 13145

dpsRTUp12146Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 18 is set"
	::= 12146

dpsRTUp13146Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 18 is cleared"
	::= 13146

dpsRTUp12147Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 19 is set"
	::= 12147

dpsRTUp13147Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 19 is cleared"
	::= 13147

dpsRTUp12148Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 20 is set"
	::= 12148

dpsRTUp13148Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 20 is cleared"
	::= 13148

dpsRTUp12149Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 21 is set"
	::= 12149

dpsRTUp13149Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 21 is cleared"
	::= 13149

dpsRTUp12150Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 22 is set"
	::= 12150

dpsRTUp13150Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 22 is cleared"
	::= 13150

dpsRTUp12151Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 23 is set"
	::= 12151

dpsRTUp13151Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 23 is cleared"
	::= 13151

dpsRTUp12152Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 24 is set"
	::= 12152

dpsRTUp13152Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 24 is cleared"
	::= 13152

dpsRTUp12153Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 25 is set"
	::= 12153

dpsRTUp13153Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 25 is cleared"
	::= 13153

dpsRTUp12154Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 26 is set"
	::= 12154

dpsRTUp13154Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 26 is cleared"
	::= 13154

dpsRTUp12155Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 27 is set"
	::= 12155

dpsRTUp13155Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 27 is cleared"
	::= 13155

dpsRTUp12156Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 28 is set"
	::= 12156

dpsRTUp13156Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 28 is cleared"
	::= 13156

dpsRTUp12157Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 29 is set"
	::= 12157

dpsRTUp13157Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 29 is cleared"
	::= 13157

dpsRTUp12158Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 30 is set"
	::= 12158

dpsRTUp13158Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 30 is cleared"
	::= 13158

dpsRTUp12159Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 31 is set"
	::= 12159

dpsRTUp13159Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 31 is cleared"
	::= 13159

dpsRTUp12160Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 32 is set"
	::= 12160

dpsRTUp13160Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 32 is cleared"
	::= 13160

dpsRTUp12161Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 33 is set"
	::= 12161

dpsRTUp13161Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 33 is cleared"
	::= 13161

dpsRTUp12162Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 34 is set"
	::= 12162

dpsRTUp13162Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 34 is cleared"
	::= 13162

dpsRTUp12163Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 35 is set"
	::= 12163

dpsRTUp13163Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 35 is cleared"
	::= 13163

dpsRTUp12164Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 36 is set"
	::= 12164

dpsRTUp13164Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 36 is cleared"
	::= 13164

dpsRTUp12165Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 37 is set"
	::= 12165

dpsRTUp13165Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 37 is cleared"
	::= 13165

dpsRTUp12166Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 38 is set"
	::= 12166

dpsRTUp13166Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 38 is cleared"
	::= 13166

dpsRTUp12167Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 39 is set"
	::= 12167

dpsRTUp13167Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 39 is cleared"
	::= 13167

dpsRTUp12168Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 40 is set"
	::= 12168

dpsRTUp13168Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 40 is cleared"
	::= 13168

dpsRTUp12169Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 41 is set"
	::= 12169

dpsRTUp13169Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 41 is cleared"
	::= 13169

dpsRTUp12170Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 42 is set"
	::= 12170

dpsRTUp13170Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 42 is cleared"
	::= 13170

dpsRTUp12171Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 43 is set"
	::= 12171

dpsRTUp13171Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 43 is cleared"
	::= 13171

dpsRTUp12172Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 44 is set"
	::= 12172

dpsRTUp13172Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 44 is cleared"
	::= 13172

dpsRTUp12173Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 45 is set"
	::= 12173

dpsRTUp13173Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 45 is cleared"
	::= 13173

dpsRTUp12174Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 46 is set"
	::= 12174

dpsRTUp13174Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 46 is cleared"
	::= 13174

dpsRTUp12175Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 47 is set"
	::= 12175

dpsRTUp13175Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 47 is cleared"
	::= 13175

dpsRTUp12176Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 48 is set"
	::= 12176

dpsRTUp13176Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 48 is cleared"
	::= 13176

dpsRTUp12177Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 49 is set"
	::= 12177

dpsRTUp13177Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 49 is cleared"
	::= 13177

dpsRTUp12178Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 50 is set"
	::= 12178

dpsRTUp13178Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 50 is cleared"
	::= 13178

dpsRTUp12179Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 51 is set"
	::= 12179

dpsRTUp13179Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 51 is cleared"
	::= 13179

dpsRTUp12180Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 52 is set"
	::= 12180

dpsRTUp13180Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 52 is cleared"
	::= 13180

dpsRTUp12181Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 53 is set"
	::= 12181

dpsRTUp13181Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 53 is cleared"
	::= 13181

dpsRTUp12182Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 54 is set"
	::= 12182

dpsRTUp13182Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 54 is cleared"
	::= 13182

dpsRTUp12183Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 55 is set"
	::= 12183

dpsRTUp13183Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 55 is cleared"
	::= 13183

dpsRTUp12184Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 56 is set"
	::= 12184

dpsRTUp13184Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 56 is cleared"
	::= 13184

dpsRTUp12185Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 57 is set"
	::= 12185

dpsRTUp13185Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 57 is cleared"
	::= 13185

dpsRTUp12186Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 58 is set"
	::= 12186

dpsRTUp13186Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 58 is cleared"
	::= 13186

dpsRTUp12187Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 59 is set"
	::= 12187

dpsRTUp13187Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 59 is cleared"
	::= 13187

dpsRTUp12188Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 60 is set"
	::= 12188

dpsRTUp13188Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 60 is cleared"
	::= 13188

dpsRTUp12189Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 61 is set"
	::= 12189

dpsRTUp13189Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 61 is cleared"
	::= 13189

dpsRTUp12190Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 62 is set"
	::= 12190

dpsRTUp13190Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 62 is cleared"
	::= 13190

dpsRTUp12191Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 63 is set"
	::= 12191

dpsRTUp13191Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 63 is cleared"
	::= 13191

dpsRTUp12192Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 64 is set"
	::= 12192

dpsRTUp13192Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 3 point 64 is cleared"
	::= 13192

dpsRTUp12193Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 1 is set"
	::= 12193

dpsRTUp13193Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 1 is cleared"
	::= 13193

dpsRTUp12194Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 2 is set"
	::= 12194

dpsRTUp13194Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 2 is cleared"
	::= 13194

dpsRTUp12195Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 3 is set"
	::= 12195

dpsRTUp13195Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 3 is cleared"
	::= 13195

dpsRTUp12196Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 4 is set"
	::= 12196

dpsRTUp13196Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 4 is cleared"
	::= 13196

dpsRTUp12197Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 5 is set"
	::= 12197

dpsRTUp13197Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 5 is cleared"
	::= 13197

dpsRTUp12198Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 6 is set"
	::= 12198

dpsRTUp13198Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 6 is cleared"
	::= 13198

dpsRTUp12199Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 7 is set"
	::= 12199

dpsRTUp13199Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 7 is cleared"
	::= 13199

dpsRTUp12200Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 8 is set"
	::= 12200

dpsRTUp13200Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 8 is cleared"
	::= 13200

dpsRTUp12201Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 9 is set"
	::= 12201

dpsRTUp13201Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 9 is cleared"
	::= 13201

dpsRTUp12202Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 10 is set"
	::= 12202

dpsRTUp13202Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 10 is cleared"
	::= 13202

dpsRTUp12203Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 11 is set"
	::= 12203

dpsRTUp13203Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 11 is cleared"
	::= 13203

dpsRTUp12204Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 12 is set"
	::= 12204

dpsRTUp13204Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 12 is cleared"
	::= 13204

dpsRTUp12205Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 13 is set"
	::= 12205

dpsRTUp13205Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 13 is cleared"
	::= 13205

dpsRTUp12206Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 14 is set"
	::= 12206

dpsRTUp13206Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 14 is cleared"
	::= 13206

dpsRTUp12207Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 15 is set"
	::= 12207

dpsRTUp13207Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 15 is cleared"
	::= 13207

dpsRTUp12208Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 16 is set"
	::= 12208

dpsRTUp13208Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 16 is cleared"
	::= 13208

dpsRTUp12209Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 17 is set"
	::= 12209

dpsRTUp13209Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 17 is cleared"
	::= 13209

dpsRTUp12210Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 18 is set"
	::= 12210

dpsRTUp13210Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 18 is cleared"
	::= 13210

dpsRTUp12211Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 19 is set"
	::= 12211

dpsRTUp13211Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 19 is cleared"
	::= 13211

dpsRTUp12212Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 20 is set"
	::= 12212

dpsRTUp13212Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 20 is cleared"
	::= 13212

dpsRTUp12213Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 21 is set"
	::= 12213

dpsRTUp13213Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 21 is cleared"
	::= 13213

dpsRTUp12214Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 22 is set"
	::= 12214

dpsRTUp13214Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 22 is cleared"
	::= 13214

dpsRTUp12215Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 23 is set"
	::= 12215

dpsRTUp13215Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 23 is cleared"
	::= 13215

dpsRTUp12216Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 24 is set"
	::= 12216

dpsRTUp13216Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 24 is cleared"
	::= 13216

dpsRTUp12217Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 25 is set"
	::= 12217

dpsRTUp13217Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 25 is cleared"
	::= 13217

dpsRTUp12218Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 26 is set"
	::= 12218

dpsRTUp13218Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 26 is cleared"
	::= 13218

dpsRTUp12219Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 27 is set"
	::= 12219

dpsRTUp13219Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 27 is cleared"
	::= 13219

dpsRTUp12220Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 28 is set"
	::= 12220

dpsRTUp13220Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 28 is cleared"
	::= 13220

dpsRTUp12221Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 29 is set"
	::= 12221

dpsRTUp13221Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 29 is cleared"
	::= 13221

dpsRTUp12222Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 30 is set"
	::= 12222

dpsRTUp13222Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 30 is cleared"
	::= 13222

dpsRTUp12223Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 31 is set"
	::= 12223

dpsRTUp13223Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 31 is cleared"
	::= 13223

dpsRTUp12224Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 32 is set"
	::= 12224

dpsRTUp13224Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 32 is cleared"
	::= 13224

dpsRTUp12225Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 33 is set"
	::= 12225

dpsRTUp13225Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 33 is cleared"
	::= 13225

dpsRTUp12226Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 34 is set"
	::= 12226

dpsRTUp13226Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 34 is cleared"
	::= 13226

dpsRTUp12227Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 35 is set"
	::= 12227

dpsRTUp13227Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 35 is cleared"
	::= 13227

dpsRTUp12228Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 36 is set"
	::= 12228

dpsRTUp13228Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 36 is cleared"
	::= 13228

dpsRTUp12229Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 37 is set"
	::= 12229

dpsRTUp13229Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 37 is cleared"
	::= 13229

dpsRTUp12230Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 38 is set"
	::= 12230

dpsRTUp13230Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 38 is cleared"
	::= 13230

dpsRTUp12231Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 39 is set"
	::= 12231

dpsRTUp13231Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 39 is cleared"
	::= 13231

dpsRTUp12232Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 40 is set"
	::= 12232

dpsRTUp13232Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 40 is cleared"
	::= 13232

dpsRTUp12233Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 41 is set"
	::= 12233

dpsRTUp13233Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 41 is cleared"
	::= 13233

dpsRTUp12234Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 42 is set"
	::= 12234

dpsRTUp13234Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 42 is cleared"
	::= 13234

dpsRTUp12235Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 43 is set"
	::= 12235

dpsRTUp13235Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 43 is cleared"
	::= 13235

dpsRTUp12236Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 44 is set"
	::= 12236

dpsRTUp13236Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 44 is cleared"
	::= 13236

dpsRTUp12237Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 45 is set"
	::= 12237

dpsRTUp13237Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 45 is cleared"
	::= 13237

dpsRTUp12238Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 46 is set"
	::= 12238

dpsRTUp13238Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 46 is cleared"
	::= 13238

dpsRTUp12239Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 47 is set"
	::= 12239

dpsRTUp13239Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 47 is cleared"
	::= 13239

dpsRTUp12240Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 48 is set"
	::= 12240

dpsRTUp13240Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 48 is cleared"
	::= 13240

dpsRTUp12241Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 49 is set"
	::= 12241

dpsRTUp13241Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 49 is cleared"
	::= 13241

dpsRTUp12242Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 50 is set"
	::= 12242

dpsRTUp13242Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 50 is cleared"
	::= 13242

dpsRTUp12243Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 51 is set"
	::= 12243

dpsRTUp13243Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 51 is cleared"
	::= 13243

dpsRTUp12244Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 52 is set"
	::= 12244

dpsRTUp13244Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 52 is cleared"
	::= 13244

dpsRTUp12245Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 53 is set"
	::= 12245

dpsRTUp13245Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 53 is cleared"
	::= 13245

dpsRTUp12246Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 54 is set"
	::= 12246

dpsRTUp13246Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 54 is cleared"
	::= 13246

dpsRTUp12247Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 55 is set"
	::= 12247

dpsRTUp13247Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 55 is cleared"
	::= 13247

dpsRTUp12248Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 56 is set"
	::= 12248

dpsRTUp13248Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 56 is cleared"
	::= 13248

dpsRTUp12249Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 57 is set"
	::= 12249

dpsRTUp13249Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 57 is cleared"
	::= 13249

dpsRTUp12250Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 58 is set"
	::= 12250

dpsRTUp13250Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 58 is cleared"
	::= 13250

dpsRTUp12251Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 59 is set"
	::= 12251

dpsRTUp13251Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 59 is cleared"
	::= 13251

dpsRTUp12252Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 60 is set"
	::= 12252

dpsRTUp13252Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 60 is cleared"
	::= 13252

dpsRTUp12253Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 61 is set"
	::= 12253

dpsRTUp13253Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 61 is cleared"
	::= 13253

dpsRTUp12254Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 62 is set"
	::= 12254

dpsRTUp13254Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 62 is cleared"
	::= 13254

dpsRTUp12255Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 63 is set"
	::= 12255

dpsRTUp13255Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 63 is cleared"
	::= 13255

dpsRTUp12256Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 64 is set"
	::= 12256

dpsRTUp13256Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 4 point 64 is cleared"
	::= 13256

dpsRTUp12257Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 1 is set"
	::= 12257

dpsRTUp13257Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 1 is cleared"
	::= 13257

dpsRTUp12258Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 2 is set"
	::= 12258

dpsRTUp13258Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 2 is cleared"
	::= 13258

dpsRTUp12259Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 3 is set"
	::= 12259

dpsRTUp13259Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 3 is cleared"
	::= 13259

dpsRTUp12260Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 4 is set"
	::= 12260

dpsRTUp13260Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 4 is cleared"
	::= 13260

dpsRTUp12261Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 5 is set"
	::= 12261

dpsRTUp13261Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 5 is cleared"
	::= 13261

dpsRTUp12262Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 6 is set"
	::= 12262

dpsRTUp13262Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 6 is cleared"
	::= 13262

dpsRTUp12263Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 7 is set"
	::= 12263

dpsRTUp13263Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 7 is cleared"
	::= 13263

dpsRTUp12264Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 8 is set"
	::= 12264

dpsRTUp13264Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 8 is cleared"
	::= 13264

dpsRTUp12265Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 9 is set"
	::= 12265

dpsRTUp13265Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 9 is cleared"
	::= 13265

dpsRTUp12266Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 10 is set"
	::= 12266

dpsRTUp13266Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 10 is cleared"
	::= 13266

dpsRTUp12267Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 11 is set"
	::= 12267

dpsRTUp13267Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 11 is cleared"
	::= 13267

dpsRTUp12268Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 12 is set"
	::= 12268

dpsRTUp13268Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 12 is cleared"
	::= 13268

dpsRTUp12269Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 13 is set"
	::= 12269

dpsRTUp13269Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 13 is cleared"
	::= 13269

dpsRTUp12270Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 14 is set"
	::= 12270

dpsRTUp13270Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 14 is cleared"
	::= 13270

dpsRTUp12271Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 15 is set"
	::= 12271

dpsRTUp13271Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 15 is cleared"
	::= 13271

dpsRTUp12272Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 16 is set"
	::= 12272

dpsRTUp13272Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 16 is cleared"
	::= 13272

dpsRTUp12273Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 17 is set"
	::= 12273

dpsRTUp13273Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 17 is cleared"
	::= 13273

dpsRTUp12274Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 18 is set"
	::= 12274

dpsRTUp13274Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 18 is cleared"
	::= 13274

dpsRTUp12275Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 19 is set"
	::= 12275

dpsRTUp13275Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 19 is cleared"
	::= 13275

dpsRTUp12276Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 20 is set"
	::= 12276

dpsRTUp13276Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 20 is cleared"
	::= 13276

dpsRTUp12277Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 21 is set"
	::= 12277

dpsRTUp13277Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 21 is cleared"
	::= 13277

dpsRTUp12278Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 22 is set"
	::= 12278

dpsRTUp13278Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 22 is cleared"
	::= 13278

dpsRTUp12279Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 23 is set"
	::= 12279

dpsRTUp13279Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 23 is cleared"
	::= 13279

dpsRTUp12280Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 24 is set"
	::= 12280

dpsRTUp13280Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 24 is cleared"
	::= 13280

dpsRTUp12281Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 25 is set"
	::= 12281

dpsRTUp13281Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 25 is cleared"
	::= 13281

dpsRTUp12282Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 26 is set"
	::= 12282

dpsRTUp13282Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 26 is cleared"
	::= 13282

dpsRTUp12283Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 27 is set"
	::= 12283

dpsRTUp13283Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 27 is cleared"
	::= 13283

dpsRTUp12284Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 28 is set"
	::= 12284

dpsRTUp13284Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 28 is cleared"
	::= 13284

dpsRTUp12285Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 29 is set"
	::= 12285

dpsRTUp13285Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 29 is cleared"
	::= 13285

dpsRTUp12286Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 30 is set"
	::= 12286

dpsRTUp13286Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 30 is cleared"
	::= 13286

dpsRTUp12287Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 31 is set"
	::= 12287

dpsRTUp13287Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 31 is cleared"
	::= 13287

dpsRTUp12288Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 32 is set"
	::= 12288

dpsRTUp13288Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 32 is cleared"
	::= 13288

dpsRTUp12289Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 33 is set"
	::= 12289

dpsRTUp13289Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 33 is cleared"
	::= 13289

dpsRTUp12290Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 34 is set"
	::= 12290

dpsRTUp13290Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 34 is cleared"
	::= 13290

dpsRTUp12291Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 35 is set"
	::= 12291

dpsRTUp13291Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 35 is cleared"
	::= 13291

dpsRTUp12292Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 36 is set"
	::= 12292

dpsRTUp13292Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 36 is cleared"
	::= 13292

dpsRTUp12293Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 37 is set"
	::= 12293

dpsRTUp13293Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 37 is cleared"
	::= 13293

dpsRTUp12294Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 38 is set"
	::= 12294

dpsRTUp13294Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 38 is cleared"
	::= 13294

dpsRTUp12295Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 39 is set"
	::= 12295

dpsRTUp13295Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 39 is cleared"
	::= 13295

dpsRTUp12296Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 40 is set"
	::= 12296

dpsRTUp13296Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 40 is cleared"
	::= 13296

dpsRTUp12297Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 41 is set"
	::= 12297

dpsRTUp13297Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 41 is cleared"
	::= 13297

dpsRTUp12298Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 42 is set"
	::= 12298

dpsRTUp13298Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 42 is cleared"
	::= 13298

dpsRTUp12299Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 43 is set"
	::= 12299

dpsRTUp13299Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 43 is cleared"
	::= 13299

dpsRTUp12300Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 44 is set"
	::= 12300

dpsRTUp13300Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 44 is cleared"
	::= 13300

dpsRTUp12301Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 45 is set"
	::= 12301

dpsRTUp13301Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 45 is cleared"
	::= 13301

dpsRTUp12302Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 46 is set"
	::= 12302

dpsRTUp13302Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 46 is cleared"
	::= 13302

dpsRTUp12303Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 47 is set"
	::= 12303

dpsRTUp13303Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 47 is cleared"
	::= 13303

dpsRTUp12304Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 48 is set"
	::= 12304

dpsRTUp13304Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 48 is cleared"
	::= 13304

dpsRTUp12305Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 49 is set"
	::= 12305

dpsRTUp13305Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 49 is cleared"
	::= 13305

dpsRTUp12306Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 50 is set"
	::= 12306

dpsRTUp13306Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 50 is cleared"
	::= 13306

dpsRTUp12307Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 51 is set"
	::= 12307

dpsRTUp13307Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 51 is cleared"
	::= 13307

dpsRTUp12308Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 52 is set"
	::= 12308

dpsRTUp13308Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 52 is cleared"
	::= 13308

dpsRTUp12309Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 53 is set"
	::= 12309

dpsRTUp13309Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 53 is cleared"
	::= 13309

dpsRTUp12310Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 54 is set"
	::= 12310

dpsRTUp13310Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 54 is cleared"
	::= 13310

dpsRTUp12311Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 55 is set"
	::= 12311

dpsRTUp13311Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 55 is cleared"
	::= 13311

dpsRTUp12312Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 56 is set"
	::= 12312

dpsRTUp13312Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 56 is cleared"
	::= 13312

dpsRTUp12313Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 57 is set"
	::= 12313

dpsRTUp13313Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 57 is cleared"
	::= 13313

dpsRTUp12314Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 58 is set"
	::= 12314

dpsRTUp13314Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 58 is cleared"
	::= 13314

dpsRTUp12315Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 59 is set"
	::= 12315

dpsRTUp13315Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 59 is cleared"
	::= 13315

dpsRTUp12316Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 60 is set"
	::= 12316

dpsRTUp13316Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 60 is cleared"
	::= 13316

dpsRTUp12317Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 61 is set"
	::= 12317

dpsRTUp13317Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 61 is cleared"
	::= 13317

dpsRTUp12318Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 62 is set"
	::= 12318

dpsRTUp13318Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 62 is cleared"
	::= 13318

dpsRTUp12319Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 63 is set"
	::= 12319

dpsRTUp13319Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 63 is cleared"
	::= 13319

dpsRTUp12320Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 64 is set"
	::= 12320

dpsRTUp13320Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 5 point 64 is cleared"
	::= 13320

dpsRTUp12321Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 1 is set"
	::= 12321

dpsRTUp13321Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 1 is cleared"
	::= 13321

dpsRTUp12322Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 2 is set"
	::= 12322

dpsRTUp13322Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 2 is cleared"
	::= 13322

dpsRTUp12323Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 3 is set"
	::= 12323

dpsRTUp13323Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 3 is cleared"
	::= 13323

dpsRTUp12324Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 4 is set"
	::= 12324

dpsRTUp13324Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 4 is cleared"
	::= 13324

dpsRTUp12325Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 5 is set"
	::= 12325

dpsRTUp13325Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 5 is cleared"
	::= 13325

dpsRTUp12326Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 6 is set"
	::= 12326

dpsRTUp13326Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 6 is cleared"
	::= 13326

dpsRTUp12327Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 7 is set"
	::= 12327

dpsRTUp13327Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 7 is cleared"
	::= 13327

dpsRTUp12328Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 8 is set"
	::= 12328

dpsRTUp13328Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 8 is cleared"
	::= 13328

dpsRTUp12329Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 9 is set"
	::= 12329

dpsRTUp13329Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 9 is cleared"
	::= 13329

dpsRTUp12330Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 10 is set"
	::= 12330

dpsRTUp13330Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 10 is cleared"
	::= 13330

dpsRTUp12331Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 11 is set"
	::= 12331

dpsRTUp13331Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 11 is cleared"
	::= 13331

dpsRTUp12332Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 12 is set"
	::= 12332

dpsRTUp13332Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 12 is cleared"
	::= 13332

dpsRTUp12333Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 13 is set"
	::= 12333

dpsRTUp13333Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 13 is cleared"
	::= 13333

dpsRTUp12334Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 14 is set"
	::= 12334

dpsRTUp13334Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 14 is cleared"
	::= 13334

dpsRTUp12335Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 15 is set"
	::= 12335

dpsRTUp13335Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 15 is cleared"
	::= 13335

dpsRTUp12336Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 16 is set"
	::= 12336

dpsRTUp13336Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 16 is cleared"
	::= 13336

dpsRTUp12337Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 17 is set"
	::= 12337

dpsRTUp13337Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 17 is cleared"
	::= 13337

dpsRTUp12338Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 18 is set"
	::= 12338

dpsRTUp13338Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 18 is cleared"
	::= 13338

dpsRTUp12339Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 19 is set"
	::= 12339

dpsRTUp13339Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 19 is cleared"
	::= 13339

dpsRTUp12340Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 20 is set"
	::= 12340

dpsRTUp13340Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 20 is cleared"
	::= 13340

dpsRTUp12341Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 21 is set"
	::= 12341

dpsRTUp13341Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 21 is cleared"
	::= 13341

dpsRTUp12342Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 22 is set"
	::= 12342

dpsRTUp13342Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 22 is cleared"
	::= 13342

dpsRTUp12343Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 23 is set"
	::= 12343

dpsRTUp13343Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 23 is cleared"
	::= 13343

dpsRTUp12344Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 24 is set"
	::= 12344

dpsRTUp13344Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 24 is cleared"
	::= 13344

dpsRTUp12345Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 25 is set"
	::= 12345

dpsRTUp13345Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 25 is cleared"
	::= 13345

dpsRTUp12346Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 26 is set"
	::= 12346

dpsRTUp13346Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 26 is cleared"
	::= 13346

dpsRTUp12347Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 27 is set"
	::= 12347

dpsRTUp13347Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 27 is cleared"
	::= 13347

dpsRTUp12348Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 28 is set"
	::= 12348

dpsRTUp13348Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 28 is cleared"
	::= 13348

dpsRTUp12349Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 29 is set"
	::= 12349

dpsRTUp13349Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 29 is cleared"
	::= 13349

dpsRTUp12350Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 30 is set"
	::= 12350

dpsRTUp13350Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 30 is cleared"
	::= 13350

dpsRTUp12351Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 31 is set"
	::= 12351

dpsRTUp13351Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 31 is cleared"
	::= 13351

dpsRTUp12352Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 32 is set"
	::= 12352

dpsRTUp13352Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 32 is cleared"
	::= 13352

dpsRTUp12353Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 33 is set"
	::= 12353

dpsRTUp13353Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 33 is cleared"
	::= 13353

dpsRTUp12354Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 34 is set"
	::= 12354

dpsRTUp13354Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 34 is cleared"
	::= 13354

dpsRTUp12355Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 35 is set"
	::= 12355

dpsRTUp13355Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 35 is cleared"
	::= 13355

dpsRTUp12356Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 36 is set"
	::= 12356

dpsRTUp13356Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 36 is cleared"
	::= 13356

dpsRTUp12357Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 37 is set"
	::= 12357

dpsRTUp13357Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 37 is cleared"
	::= 13357

dpsRTUp12358Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 38 is set"
	::= 12358

dpsRTUp13358Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 38 is cleared"
	::= 13358

dpsRTUp12359Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 39 is set"
	::= 12359

dpsRTUp13359Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 39 is cleared"
	::= 13359

dpsRTUp12360Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 40 is set"
	::= 12360

dpsRTUp13360Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 40 is cleared"
	::= 13360

dpsRTUp12361Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 41 is set"
	::= 12361

dpsRTUp13361Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 41 is cleared"
	::= 13361

dpsRTUp12362Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 42 is set"
	::= 12362

dpsRTUp13362Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 42 is cleared"
	::= 13362

dpsRTUp12363Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 43 is set"
	::= 12363

dpsRTUp13363Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 43 is cleared"
	::= 13363

dpsRTUp12364Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 44 is set"
	::= 12364

dpsRTUp13364Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 44 is cleared"
	::= 13364

dpsRTUp12365Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 45 is set"
	::= 12365

dpsRTUp13365Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 45 is cleared"
	::= 13365

dpsRTUp12366Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 46 is set"
	::= 12366

dpsRTUp13366Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 46 is cleared"
	::= 13366

dpsRTUp12367Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 47 is set"
	::= 12367

dpsRTUp13367Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 47 is cleared"
	::= 13367

dpsRTUp12368Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 48 is set"
	::= 12368

dpsRTUp13368Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 48 is cleared"
	::= 13368

dpsRTUp12369Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 49 is set"
	::= 12369

dpsRTUp13369Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 49 is cleared"
	::= 13369

dpsRTUp12370Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 50 is set"
	::= 12370

dpsRTUp13370Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 50 is cleared"
	::= 13370

dpsRTUp12371Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 51 is set"
	::= 12371

dpsRTUp13371Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 51 is cleared"
	::= 13371

dpsRTUp12372Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 52 is set"
	::= 12372

dpsRTUp13372Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 52 is cleared"
	::= 13372

dpsRTUp12373Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 53 is set"
	::= 12373

dpsRTUp13373Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 53 is cleared"
	::= 13373

dpsRTUp12374Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 54 is set"
	::= 12374

dpsRTUp13374Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 54 is cleared"
	::= 13374

dpsRTUp12375Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 55 is set"
	::= 12375

dpsRTUp13375Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 55 is cleared"
	::= 13375

dpsRTUp12376Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 56 is set"
	::= 12376

dpsRTUp13376Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 56 is cleared"
	::= 13376

dpsRTUp12377Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 57 is set"
	::= 12377

dpsRTUp13377Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 57 is cleared"
	::= 13377

dpsRTUp12378Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 58 is set"
	::= 12378

dpsRTUp13378Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 58 is cleared"
	::= 13378

dpsRTUp12379Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 59 is set"
	::= 12379

dpsRTUp13379Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 59 is cleared"
	::= 13379

dpsRTUp12380Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 60 is set"
	::= 12380

dpsRTUp13380Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 60 is cleared"
	::= 13380

dpsRTUp12381Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 61 is set"
	::= 12381

dpsRTUp13381Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 61 is cleared"
	::= 13381

dpsRTUp12382Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 62 is set"
	::= 12382

dpsRTUp13382Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 62 is cleared"
	::= 13382

dpsRTUp12383Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 63 is set"
	::= 12383

dpsRTUp13383Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 63 is cleared"
	::= 13383

dpsRTUp12384Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 64 is set"
	::= 12384

dpsRTUp13384Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 6 point 64 is cleared"
	::= 13384

dpsRTUp12385Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 1 is set"
	::= 12385

dpsRTUp13385Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 1 is cleared"
	::= 13385

dpsRTUp12386Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 2 is set"
	::= 12386

dpsRTUp13386Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 2 is cleared"
	::= 13386

dpsRTUp12387Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 3 is set"
	::= 12387

dpsRTUp13387Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 3 is cleared"
	::= 13387

dpsRTUp12388Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 4 is set"
	::= 12388

dpsRTUp13388Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 4 is cleared"
	::= 13388

dpsRTUp12389Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 5 is set"
	::= 12389

dpsRTUp13389Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 5 is cleared"
	::= 13389

dpsRTUp12390Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 6 is set"
	::= 12390

dpsRTUp13390Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 6 is cleared"
	::= 13390

dpsRTUp12391Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 7 is set"
	::= 12391

dpsRTUp13391Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 7 is cleared"
	::= 13391

dpsRTUp12392Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 8 is set"
	::= 12392

dpsRTUp13392Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 8 is cleared"
	::= 13392

dpsRTUp12393Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 9 is set"
	::= 12393

dpsRTUp13393Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 9 is cleared"
	::= 13393

dpsRTUp12394Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 10 is set"
	::= 12394

dpsRTUp13394Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 10 is cleared"
	::= 13394

dpsRTUp12395Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 11 is set"
	::= 12395

dpsRTUp13395Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 11 is cleared"
	::= 13395

dpsRTUp12396Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 12 is set"
	::= 12396

dpsRTUp13396Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 12 is cleared"
	::= 13396

dpsRTUp12397Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 13 is set"
	::= 12397

dpsRTUp13397Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 13 is cleared"
	::= 13397

dpsRTUp12398Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 14 is set"
	::= 12398

dpsRTUp13398Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 14 is cleared"
	::= 13398

dpsRTUp12399Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 15 is set"
	::= 12399

dpsRTUp13399Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 15 is cleared"
	::= 13399

dpsRTUp12400Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 16 is set"
	::= 12400

dpsRTUp13400Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 16 is cleared"
	::= 13400

dpsRTUp12401Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 17 is set"
	::= 12401

dpsRTUp13401Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 17 is cleared"
	::= 13401

dpsRTUp12402Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 18 is set"
	::= 12402

dpsRTUp13402Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 18 is cleared"
	::= 13402

dpsRTUp12403Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 19 is set"
	::= 12403

dpsRTUp13403Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 19 is cleared"
	::= 13403

dpsRTUp12404Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 20 is set"
	::= 12404

dpsRTUp13404Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 20 is cleared"
	::= 13404

dpsRTUp12405Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 21 is set"
	::= 12405

dpsRTUp13405Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 21 is cleared"
	::= 13405

dpsRTUp12406Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 22 is set"
	::= 12406

dpsRTUp13406Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 22 is cleared"
	::= 13406

dpsRTUp12407Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 23 is set"
	::= 12407

dpsRTUp13407Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 23 is cleared"
	::= 13407

dpsRTUp12408Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 24 is set"
	::= 12408

dpsRTUp13408Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 24 is cleared"
	::= 13408

dpsRTUp12409Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 25 is set"
	::= 12409

dpsRTUp13409Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 25 is cleared"
	::= 13409

dpsRTUp12410Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 26 is set"
	::= 12410

dpsRTUp13410Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 26 is cleared"
	::= 13410

dpsRTUp12411Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 27 is set"
	::= 12411

dpsRTUp13411Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 27 is cleared"
	::= 13411

dpsRTUp12412Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 28 is set"
	::= 12412

dpsRTUp13412Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 28 is cleared"
	::= 13412

dpsRTUp12413Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 29 is set"
	::= 12413

dpsRTUp13413Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 29 is cleared"
	::= 13413

dpsRTUp12414Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 30 is set"
	::= 12414

dpsRTUp13414Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 30 is cleared"
	::= 13414

dpsRTUp12415Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 31 is set"
	::= 12415

dpsRTUp13415Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 31 is cleared"
	::= 13415

dpsRTUp12416Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 32 is set"
	::= 12416

dpsRTUp13416Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 32 is cleared"
	::= 13416

dpsRTUp12417Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 33 is set"
	::= 12417

dpsRTUp13417Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 33 is cleared"
	::= 13417

dpsRTUp12418Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 34 is set"
	::= 12418

dpsRTUp13418Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 34 is cleared"
	::= 13418

dpsRTUp12419Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 35 is set"
	::= 12419

dpsRTUp13419Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 35 is cleared"
	::= 13419

dpsRTUp12420Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 36 is set"
	::= 12420

dpsRTUp13420Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 36 is cleared"
	::= 13420

dpsRTUp12421Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 37 is set"
	::= 12421

dpsRTUp13421Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 37 is cleared"
	::= 13421

dpsRTUp12422Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 38 is set"
	::= 12422

dpsRTUp13422Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 38 is cleared"
	::= 13422

dpsRTUp12423Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 39 is set"
	::= 12423

dpsRTUp13423Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 39 is cleared"
	::= 13423

dpsRTUp12424Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 40 is set"
	::= 12424

dpsRTUp13424Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 40 is cleared"
	::= 13424

dpsRTUp12425Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 41 is set"
	::= 12425

dpsRTUp13425Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 41 is cleared"
	::= 13425

dpsRTUp12426Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 42 is set"
	::= 12426

dpsRTUp13426Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 42 is cleared"
	::= 13426

dpsRTUp12427Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 43 is set"
	::= 12427

dpsRTUp13427Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 43 is cleared"
	::= 13427

dpsRTUp12428Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 44 is set"
	::= 12428

dpsRTUp13428Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 44 is cleared"
	::= 13428

dpsRTUp12429Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 45 is set"
	::= 12429

dpsRTUp13429Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 45 is cleared"
	::= 13429

dpsRTUp12430Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 46 is set"
	::= 12430

dpsRTUp13430Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 46 is cleared"
	::= 13430

dpsRTUp12431Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 47 is set"
	::= 12431

dpsRTUp13431Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 47 is cleared"
	::= 13431

dpsRTUp12432Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 48 is set"
	::= 12432

dpsRTUp13432Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 48 is cleared"
	::= 13432

dpsRTUp12433Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 49 is set"
	::= 12433

dpsRTUp13433Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 49 is cleared"
	::= 13433

dpsRTUp12434Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 50 is set"
	::= 12434

dpsRTUp13434Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 50 is cleared"
	::= 13434

dpsRTUp12435Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 51 is set"
	::= 12435

dpsRTUp13435Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 51 is cleared"
	::= 13435

dpsRTUp12436Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 52 is set"
	::= 12436

dpsRTUp13436Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 52 is cleared"
	::= 13436

dpsRTUp12437Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 53 is set"
	::= 12437

dpsRTUp13437Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 53 is cleared"
	::= 13437

dpsRTUp12438Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 54 is set"
	::= 12438

dpsRTUp13438Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 54 is cleared"
	::= 13438

dpsRTUp12439Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 55 is set"
	::= 12439

dpsRTUp13439Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 55 is cleared"
	::= 13439

dpsRTUp12440Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 56 is set"
	::= 12440

dpsRTUp13440Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 56 is cleared"
	::= 13440

dpsRTUp12441Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 57 is set"
	::= 12441

dpsRTUp13441Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 57 is cleared"
	::= 13441

dpsRTUp12442Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 58 is set"
	::= 12442

dpsRTUp13442Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 58 is cleared"
	::= 13442

dpsRTUp12443Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 59 is set"
	::= 12443

dpsRTUp13443Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 59 is cleared"
	::= 13443

dpsRTUp12444Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 60 is set"
	::= 12444

dpsRTUp13444Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 60 is cleared"
	::= 13444

dpsRTUp12445Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 61 is set"
	::= 12445

dpsRTUp13445Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 61 is cleared"
	::= 13445

dpsRTUp12446Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 62 is set"
	::= 12446

dpsRTUp13446Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 62 is cleared"
	::= 13446

dpsRTUp12447Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 63 is set"
	::= 12447

dpsRTUp13447Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 63 is cleared"
	::= 13447

dpsRTUp12448Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 64 is set"
	::= 12448

dpsRTUp13448Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 7 point 64 is cleared"
	::= 13448

dpsRTUp12449Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 1 is set"
	::= 12449

dpsRTUp13449Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 1 is cleared"
	::= 13449

dpsRTUp12450Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 2 is set"
	::= 12450

dpsRTUp13450Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 2 is cleared"
	::= 13450

dpsRTUp12451Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 3 is set"
	::= 12451

dpsRTUp13451Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 3 is cleared"
	::= 13451

dpsRTUp12452Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 4 is set"
	::= 12452

dpsRTUp13452Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 4 is cleared"
	::= 13452

dpsRTUp12453Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 5 is set"
	::= 12453

dpsRTUp13453Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 5 is cleared"
	::= 13453

dpsRTUp12454Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 6 is set"
	::= 12454

dpsRTUp13454Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 6 is cleared"
	::= 13454

dpsRTUp12455Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 7 is set"
	::= 12455

dpsRTUp13455Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 7 is cleared"
	::= 13455

dpsRTUp12456Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 8 is set"
	::= 12456

dpsRTUp13456Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 8 is cleared"
	::= 13456

dpsRTUp12457Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 9 is set"
	::= 12457

dpsRTUp13457Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 9 is cleared"
	::= 13457

dpsRTUp12458Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 10 is set"
	::= 12458

dpsRTUp13458Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 10 is cleared"
	::= 13458

dpsRTUp12459Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 11 is set"
	::= 12459

dpsRTUp13459Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 11 is cleared"
	::= 13459

dpsRTUp12460Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 12 is set"
	::= 12460

dpsRTUp13460Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 12 is cleared"
	::= 13460

dpsRTUp12461Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 13 is set"
	::= 12461

dpsRTUp13461Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 13 is cleared"
	::= 13461

dpsRTUp12462Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 14 is set"
	::= 12462

dpsRTUp13462Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 14 is cleared"
	::= 13462

dpsRTUp12463Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 15 is set"
	::= 12463

dpsRTUp13463Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 15 is cleared"
	::= 13463

dpsRTUp12464Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 16 is set"
	::= 12464

dpsRTUp13464Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 16 is cleared"
	::= 13464

dpsRTUp12465Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 17 is set"
	::= 12465

dpsRTUp13465Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 17 is cleared"
	::= 13465

dpsRTUp12466Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 18 is set"
	::= 12466

dpsRTUp13466Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 18 is cleared"
	::= 13466

dpsRTUp12467Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 19 is set"
	::= 12467

dpsRTUp13467Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 19 is cleared"
	::= 13467

dpsRTUp12468Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 20 is set"
	::= 12468

dpsRTUp13468Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 20 is cleared"
	::= 13468

dpsRTUp12469Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 21 is set"
	::= 12469

dpsRTUp13469Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 21 is cleared"
	::= 13469

dpsRTUp12470Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 22 is set"
	::= 12470

dpsRTUp13470Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 22 is cleared"
	::= 13470

dpsRTUp12471Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 23 is set"
	::= 12471

dpsRTUp13471Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 23 is cleared"
	::= 13471

dpsRTUp12472Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 24 is set"
	::= 12472

dpsRTUp13472Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 24 is cleared"
	::= 13472

dpsRTUp12473Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 25 is set"
	::= 12473

dpsRTUp13473Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 25 is cleared"
	::= 13473

dpsRTUp12474Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 26 is set"
	::= 12474

dpsRTUp13474Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 26 is cleared"
	::= 13474

dpsRTUp12475Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 27 is set"
	::= 12475

dpsRTUp13475Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 27 is cleared"
	::= 13475

dpsRTUp12476Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 28 is set"
	::= 12476

dpsRTUp13476Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 28 is cleared"
	::= 13476

dpsRTUp12477Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 29 is set"
	::= 12477

dpsRTUp13477Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 29 is cleared"
	::= 13477

dpsRTUp12478Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 30 is set"
	::= 12478

dpsRTUp13478Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 30 is cleared"
	::= 13478

dpsRTUp12479Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 31 is set"
	::= 12479

dpsRTUp13479Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 31 is cleared"
	::= 13479

dpsRTUp12480Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 32 is set"
	::= 12480

dpsRTUp13480Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 32 is cleared"
	::= 13480

dpsRTUp12481Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 33 is set"
	::= 12481

dpsRTUp13481Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 33 is cleared"
	::= 13481

dpsRTUp12482Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 34 is set"
	::= 12482

dpsRTUp13482Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 34 is cleared"
	::= 13482

dpsRTUp12483Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 35 is set"
	::= 12483

dpsRTUp13483Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 35 is cleared"
	::= 13483

dpsRTUp12484Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 36 is set"
	::= 12484

dpsRTUp13484Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 36 is cleared"
	::= 13484

dpsRTUp12485Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 37 is set"
	::= 12485

dpsRTUp13485Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 37 is cleared"
	::= 13485

dpsRTUp12486Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 38 is set"
	::= 12486

dpsRTUp13486Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 38 is cleared"
	::= 13486

dpsRTUp12487Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 39 is set"
	::= 12487

dpsRTUp13487Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 39 is cleared"
	::= 13487

dpsRTUp12488Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 40 is set"
	::= 12488

dpsRTUp13488Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 40 is cleared"
	::= 13488

dpsRTUp12489Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 41 is set"
	::= 12489

dpsRTUp13489Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 41 is cleared"
	::= 13489

dpsRTUp12490Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 42 is set"
	::= 12490

dpsRTUp13490Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 42 is cleared"
	::= 13490

dpsRTUp12491Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 43 is set"
	::= 12491

dpsRTUp13491Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 43 is cleared"
	::= 13491

dpsRTUp12492Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 44 is set"
	::= 12492

dpsRTUp13492Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 44 is cleared"
	::= 13492

dpsRTUp12493Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 45 is set"
	::= 12493

dpsRTUp13493Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 45 is cleared"
	::= 13493

dpsRTUp12494Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 46 is set"
	::= 12494

dpsRTUp13494Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 46 is cleared"
	::= 13494

dpsRTUp12495Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 47 is set"
	::= 12495

dpsRTUp13495Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 47 is cleared"
	::= 13495

dpsRTUp12496Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 48 is set"
	::= 12496

dpsRTUp13496Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 48 is cleared"
	::= 13496

dpsRTUp12497Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 49 is set"
	::= 12497

dpsRTUp13497Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 49 is cleared"
	::= 13497

dpsRTUp12498Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 50 is set"
	::= 12498

dpsRTUp13498Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 50 is cleared"
	::= 13498

dpsRTUp12499Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 51 is set"
	::= 12499

dpsRTUp13499Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 51 is cleared"
	::= 13499

dpsRTUp12500Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 52 is set"
	::= 12500

dpsRTUp13500Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 52 is cleared"
	::= 13500

dpsRTUp12501Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 53 is set"
	::= 12501

dpsRTUp13501Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 53 is cleared"
	::= 13501

dpsRTUp12502Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 54 is set"
	::= 12502

dpsRTUp13502Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 54 is cleared"
	::= 13502

dpsRTUp12503Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 55 is set"
	::= 12503

dpsRTUp13503Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 55 is cleared"
	::= 13503

dpsRTUp12504Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 56 is set"
	::= 12504

dpsRTUp13504Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 56 is cleared"
	::= 13504

dpsRTUp12505Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 57 is set"
	::= 12505

dpsRTUp13505Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 57 is cleared"
	::= 13505

dpsRTUp12506Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 58 is set"
	::= 12506

dpsRTUp13506Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 58 is cleared"
	::= 13506

dpsRTUp12507Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 59 is set"
	::= 12507

dpsRTUp13507Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 59 is cleared"
	::= 13507

dpsRTUp12508Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 60 is set"
	::= 12508

dpsRTUp13508Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 60 is cleared"
	::= 13508

dpsRTUp12509Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 61 is set"
	::= 12509

dpsRTUp13509Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 61 is cleared"
	::= 13509

dpsRTUp12510Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 62 is set"
	::= 12510

dpsRTUp13510Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 62 is cleared"
	::= 13510

dpsRTUp12511Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 63 is set"
	::= 12511

dpsRTUp13511Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 63 is cleared"
	::= 13511

dpsRTUp12512Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 64 is set"
	::= 12512

dpsRTUp13512Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 2 display 8 point 64 is cleared"
	::= 13512
dpsRTUp14001Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 1 is set"
	::= 14001

dpsRTUp15001Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 1 is cleared"
	::= 15001

dpsRTUp14002Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 2 is set"
	::= 14002

dpsRTUp15002Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 2 is cleared"
	::= 15002

dpsRTUp14003Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 3 is set"
	::= 14003

dpsRTUp15003Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 3 is cleared"
	::= 15003

dpsRTUp14004Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 4 is set"
	::= 14004

dpsRTUp15004Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 4 is cleared"
	::= 15004

dpsRTUp14005Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 5 is set"
	::= 14005

dpsRTUp15005Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 5 is cleared"
	::= 15005

dpsRTUp14006Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 6 is set"
	::= 14006

dpsRTUp15006Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 6 is cleared"
	::= 15006

dpsRTUp14007Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 7 is set"
	::= 14007

dpsRTUp15007Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 7 is cleared"
	::= 15007

dpsRTUp14008Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 8 is set"
	::= 14008

dpsRTUp15008Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 8 is cleared"
	::= 15008

dpsRTUp14009Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 9 is set"
	::= 14009

dpsRTUp15009Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 9 is cleared"
	::= 15009

dpsRTUp14010Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 10 is set"
	::= 14010

dpsRTUp15010Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 10 is cleared"
	::= 15010

dpsRTUp14011Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 11 is set"
	::= 14011

dpsRTUp15011Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 11 is cleared"
	::= 15011

dpsRTUp14012Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 12 is set"
	::= 14012

dpsRTUp15012Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 12 is cleared"
	::= 15012

dpsRTUp14013Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 13 is set"
	::= 14013

dpsRTUp15013Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 13 is cleared"
	::= 15013

dpsRTUp14014Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 14 is set"
	::= 14014

dpsRTUp15014Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 14 is cleared"
	::= 15014

dpsRTUp14015Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 15 is set"
	::= 14015

dpsRTUp15015Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 15 is cleared"
	::= 15015

dpsRTUp14016Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 16 is set"
	::= 14016

dpsRTUp15016Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 16 is cleared"
	::= 15016

dpsRTUp14017Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 17 is set"
	::= 14017

dpsRTUp15017Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 17 is cleared"
	::= 15017

dpsRTUp14018Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 18 is set"
	::= 14018

dpsRTUp15018Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 18 is cleared"
	::= 15018

dpsRTUp14019Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 19 is set"
	::= 14019

dpsRTUp15019Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 19 is cleared"
	::= 15019

dpsRTUp14020Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 20 is set"
	::= 14020

dpsRTUp15020Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 20 is cleared"
	::= 15020

dpsRTUp14021Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 21 is set"
	::= 14021

dpsRTUp15021Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 21 is cleared"
	::= 15021

dpsRTUp14022Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 22 is set"
	::= 14022

dpsRTUp15022Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 22 is cleared"
	::= 15022

dpsRTUp14023Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 23 is set"
	::= 14023

dpsRTUp15023Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 23 is cleared"
	::= 15023

dpsRTUp14024Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 24 is set"
	::= 14024

dpsRTUp15024Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 24 is cleared"
	::= 15024

dpsRTUp14025Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 25 is set"
	::= 14025

dpsRTUp15025Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 25 is cleared"
	::= 15025

dpsRTUp14026Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 26 is set"
	::= 14026

dpsRTUp15026Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 26 is cleared"
	::= 15026

dpsRTUp14027Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 27 is set"
	::= 14027

dpsRTUp15027Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 27 is cleared"
	::= 15027

dpsRTUp14028Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 28 is set"
	::= 14028

dpsRTUp15028Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 28 is cleared"
	::= 15028

dpsRTUp14029Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 29 is set"
	::= 14029

dpsRTUp15029Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 29 is cleared"
	::= 15029

dpsRTUp14030Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 30 is set"
	::= 14030

dpsRTUp15030Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 30 is cleared"
	::= 15030

dpsRTUp14031Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 31 is set"
	::= 14031

dpsRTUp15031Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 31 is cleared"
	::= 15031

dpsRTUp14032Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 32 is set"
	::= 14032

dpsRTUp15032Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 32 is cleared"
	::= 15032

dpsRTUp14033Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 33 is set"
	::= 14033

dpsRTUp15033Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 33 is cleared"
	::= 15033

dpsRTUp14034Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 34 is set"
	::= 14034

dpsRTUp15034Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 34 is cleared"
	::= 15034

dpsRTUp14035Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 35 is set"
	::= 14035

dpsRTUp15035Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 35 is cleared"
	::= 15035

dpsRTUp14036Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 36 is set"
	::= 14036

dpsRTUp15036Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 36 is cleared"
	::= 15036

dpsRTUp14037Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 37 is set"
	::= 14037

dpsRTUp15037Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 37 is cleared"
	::= 15037

dpsRTUp14038Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 38 is set"
	::= 14038

dpsRTUp15038Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 38 is cleared"
	::= 15038

dpsRTUp14039Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 39 is set"
	::= 14039

dpsRTUp15039Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 39 is cleared"
	::= 15039

dpsRTUp14040Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 40 is set"
	::= 14040

dpsRTUp15040Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 40 is cleared"
	::= 15040

dpsRTUp14041Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 41 is set"
	::= 14041

dpsRTUp15041Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 41 is cleared"
	::= 15041

dpsRTUp14042Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 42 is set"
	::= 14042

dpsRTUp15042Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 42 is cleared"
	::= 15042

dpsRTUp14043Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 43 is set"
	::= 14043

dpsRTUp15043Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 43 is cleared"
	::= 15043

dpsRTUp14044Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 44 is set"
	::= 14044

dpsRTUp15044Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 44 is cleared"
	::= 15044

dpsRTUp14045Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 45 is set"
	::= 14045

dpsRTUp15045Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 45 is cleared"
	::= 15045

dpsRTUp14046Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 46 is set"
	::= 14046

dpsRTUp15046Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 46 is cleared"
	::= 15046

dpsRTUp14047Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 47 is set"
	::= 14047

dpsRTUp15047Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 47 is cleared"
	::= 15047

dpsRTUp14048Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 48 is set"
	::= 14048

dpsRTUp15048Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 48 is cleared"
	::= 15048

dpsRTUp14049Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 49 is set"
	::= 14049

dpsRTUp15049Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 49 is cleared"
	::= 15049

dpsRTUp14050Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 50 is set"
	::= 14050

dpsRTUp15050Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 50 is cleared"
	::= 15050

dpsRTUp14051Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 51 is set"
	::= 14051

dpsRTUp15051Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 51 is cleared"
	::= 15051

dpsRTUp14052Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 52 is set"
	::= 14052

dpsRTUp15052Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 52 is cleared"
	::= 15052

dpsRTUp14053Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 53 is set"
	::= 14053

dpsRTUp15053Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 53 is cleared"
	::= 15053

dpsRTUp14054Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 54 is set"
	::= 14054

dpsRTUp15054Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 54 is cleared"
	::= 15054

dpsRTUp14055Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 55 is set"
	::= 14055

dpsRTUp15055Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 55 is cleared"
	::= 15055

dpsRTUp14056Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 56 is set"
	::= 14056

dpsRTUp15056Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 56 is cleared"
	::= 15056

dpsRTUp14057Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 57 is set"
	::= 14057

dpsRTUp15057Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 57 is cleared"
	::= 15057

dpsRTUp14058Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 58 is set"
	::= 14058

dpsRTUp15058Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 58 is cleared"
	::= 15058

dpsRTUp14059Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 59 is set"
	::= 14059

dpsRTUp15059Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 59 is cleared"
	::= 15059

dpsRTUp14060Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 60 is set"
	::= 14060

dpsRTUp15060Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 60 is cleared"
	::= 15060

dpsRTUp14061Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 61 is set"
	::= 14061

dpsRTUp15061Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 61 is cleared"
	::= 15061

dpsRTUp14062Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 62 is set"
	::= 14062

dpsRTUp15062Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 62 is cleared"
	::= 15062

dpsRTUp14063Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 63 is set"
	::= 14063

dpsRTUp15063Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 63 is cleared"
	::= 15063

dpsRTUp14064Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 64 is set"
	::= 14064

dpsRTUp15064Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 1 point 64 is cleared"
	::= 15064

dpsRTUp14065Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 1 is set"
	::= 14065

dpsRTUp15065Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 1 is cleared"
	::= 15065

dpsRTUp14066Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 2 is set"
	::= 14066

dpsRTUp15066Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 2 is cleared"
	::= 15066

dpsRTUp14067Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 3 is set"
	::= 14067

dpsRTUp15067Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 3 is cleared"
	::= 15067

dpsRTUp14068Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 4 is set"
	::= 14068

dpsRTUp15068Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 4 is cleared"
	::= 15068

dpsRTUp14069Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 5 is set"
	::= 14069

dpsRTUp15069Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 5 is cleared"
	::= 15069

dpsRTUp14070Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 6 is set"
	::= 14070

dpsRTUp15070Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 6 is cleared"
	::= 15070

dpsRTUp14071Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 7 is set"
	::= 14071

dpsRTUp15071Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 7 is cleared"
	::= 15071

dpsRTUp14072Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 8 is set"
	::= 14072

dpsRTUp15072Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 8 is cleared"
	::= 15072

dpsRTUp14073Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 9 is set"
	::= 14073

dpsRTUp15073Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 9 is cleared"
	::= 15073

dpsRTUp14074Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 10 is set"
	::= 14074

dpsRTUp15074Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 10 is cleared"
	::= 15074

dpsRTUp14075Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 11 is set"
	::= 14075

dpsRTUp15075Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 11 is cleared"
	::= 15075

dpsRTUp14076Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 12 is set"
	::= 14076

dpsRTUp15076Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 12 is cleared"
	::= 15076

dpsRTUp14077Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 13 is set"
	::= 14077

dpsRTUp15077Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 13 is cleared"
	::= 15077

dpsRTUp14078Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 14 is set"
	::= 14078

dpsRTUp15078Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 14 is cleared"
	::= 15078

dpsRTUp14079Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 15 is set"
	::= 14079

dpsRTUp15079Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 15 is cleared"
	::= 15079

dpsRTUp14080Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 16 is set"
	::= 14080

dpsRTUp15080Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 16 is cleared"
	::= 15080

dpsRTUp14081Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 17 is set"
	::= 14081

dpsRTUp15081Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 17 is cleared"
	::= 15081

dpsRTUp14082Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 18 is set"
	::= 14082

dpsRTUp15082Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 18 is cleared"
	::= 15082

dpsRTUp14083Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 19 is set"
	::= 14083

dpsRTUp15083Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 19 is cleared"
	::= 15083

dpsRTUp14084Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 20 is set"
	::= 14084

dpsRTUp15084Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 20 is cleared"
	::= 15084

dpsRTUp14085Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 21 is set"
	::= 14085

dpsRTUp15085Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 21 is cleared"
	::= 15085

dpsRTUp14086Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 22 is set"
	::= 14086

dpsRTUp15086Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 22 is cleared"
	::= 15086

dpsRTUp14087Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 23 is set"
	::= 14087

dpsRTUp15087Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 23 is cleared"
	::= 15087

dpsRTUp14088Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 24 is set"
	::= 14088

dpsRTUp15088Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 24 is cleared"
	::= 15088

dpsRTUp14089Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 25 is set"
	::= 14089

dpsRTUp15089Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 25 is cleared"
	::= 15089

dpsRTUp14090Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 26 is set"
	::= 14090

dpsRTUp15090Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 26 is cleared"
	::= 15090

dpsRTUp14091Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 27 is set"
	::= 14091

dpsRTUp15091Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 27 is cleared"
	::= 15091

dpsRTUp14092Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 28 is set"
	::= 14092

dpsRTUp15092Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 28 is cleared"
	::= 15092

dpsRTUp14093Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 29 is set"
	::= 14093

dpsRTUp15093Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 29 is cleared"
	::= 15093

dpsRTUp14094Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 30 is set"
	::= 14094

dpsRTUp15094Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 30 is cleared"
	::= 15094

dpsRTUp14095Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 31 is set"
	::= 14095

dpsRTUp15095Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 31 is cleared"
	::= 15095

dpsRTUp14096Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 32 is set"
	::= 14096

dpsRTUp15096Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 32 is cleared"
	::= 15096

dpsRTUp14097Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 33 is set"
	::= 14097

dpsRTUp15097Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 33 is cleared"
	::= 15097

dpsRTUp14098Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 34 is set"
	::= 14098

dpsRTUp15098Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 34 is cleared"
	::= 15098

dpsRTUp14099Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 35 is set"
	::= 14099

dpsRTUp15099Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 35 is cleared"
	::= 15099

dpsRTUp14100Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 36 is set"
	::= 14100

dpsRTUp15100Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 36 is cleared"
	::= 15100

dpsRTUp14101Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 37 is set"
	::= 14101

dpsRTUp15101Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 37 is cleared"
	::= 15101

dpsRTUp14102Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 38 is set"
	::= 14102

dpsRTUp15102Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 38 is cleared"
	::= 15102

dpsRTUp14103Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 39 is set"
	::= 14103

dpsRTUp15103Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 39 is cleared"
	::= 15103

dpsRTUp14104Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 40 is set"
	::= 14104

dpsRTUp15104Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 40 is cleared"
	::= 15104

dpsRTUp14105Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 41 is set"
	::= 14105

dpsRTUp15105Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 41 is cleared"
	::= 15105

dpsRTUp14106Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 42 is set"
	::= 14106

dpsRTUp15106Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 42 is cleared"
	::= 15106

dpsRTUp14107Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 43 is set"
	::= 14107

dpsRTUp15107Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 43 is cleared"
	::= 15107

dpsRTUp14108Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 44 is set"
	::= 14108

dpsRTUp15108Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 44 is cleared"
	::= 15108

dpsRTUp14109Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 45 is set"
	::= 14109

dpsRTUp15109Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 45 is cleared"
	::= 15109

dpsRTUp14110Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 46 is set"
	::= 14110

dpsRTUp15110Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 46 is cleared"
	::= 15110

dpsRTUp14111Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 47 is set"
	::= 14111

dpsRTUp15111Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 47 is cleared"
	::= 15111

dpsRTUp14112Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 48 is set"
	::= 14112

dpsRTUp15112Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 48 is cleared"
	::= 15112

dpsRTUp14113Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 49 is set"
	::= 14113

dpsRTUp15113Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 49 is cleared"
	::= 15113

dpsRTUp14114Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 50 is set"
	::= 14114

dpsRTUp15114Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 50 is cleared"
	::= 15114

dpsRTUp14115Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 51 is set"
	::= 14115

dpsRTUp15115Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 51 is cleared"
	::= 15115

dpsRTUp14116Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 52 is set"
	::= 14116

dpsRTUp15116Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 52 is cleared"
	::= 15116

dpsRTUp14117Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 53 is set"
	::= 14117

dpsRTUp15117Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 53 is cleared"
	::= 15117

dpsRTUp14118Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 54 is set"
	::= 14118

dpsRTUp15118Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 54 is cleared"
	::= 15118

dpsRTUp14119Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 55 is set"
	::= 14119

dpsRTUp15119Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 55 is cleared"
	::= 15119

dpsRTUp14120Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 56 is set"
	::= 14120

dpsRTUp15120Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 56 is cleared"
	::= 15120

dpsRTUp14121Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 57 is set"
	::= 14121

dpsRTUp15121Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 57 is cleared"
	::= 15121

dpsRTUp14122Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 58 is set"
	::= 14122

dpsRTUp15122Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 58 is cleared"
	::= 15122

dpsRTUp14123Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 59 is set"
	::= 14123

dpsRTUp15123Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 59 is cleared"
	::= 15123

dpsRTUp14124Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 60 is set"
	::= 14124

dpsRTUp15124Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 60 is cleared"
	::= 15124

dpsRTUp14125Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 61 is set"
	::= 14125

dpsRTUp15125Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 61 is cleared"
	::= 15125

dpsRTUp14126Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 62 is set"
	::= 14126

dpsRTUp15126Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 62 is cleared"
	::= 15126

dpsRTUp14127Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 63 is set"
	::= 14127

dpsRTUp15127Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 63 is cleared"
	::= 15127

dpsRTUp14128Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 64 is set"
	::= 14128

dpsRTUp15128Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 2 point 64 is cleared"
	::= 15128

dpsRTUp14129Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 1 is set"
	::= 14129

dpsRTUp15129Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 1 is cleared"
	::= 15129

dpsRTUp14130Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 2 is set"
	::= 14130

dpsRTUp15130Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 2 is cleared"
	::= 15130

dpsRTUp14131Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 3 is set"
	::= 14131

dpsRTUp15131Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 3 is cleared"
	::= 15131

dpsRTUp14132Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 4 is set"
	::= 14132

dpsRTUp15132Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 4 is cleared"
	::= 15132

dpsRTUp14133Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 5 is set"
	::= 14133

dpsRTUp15133Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 5 is cleared"
	::= 15133

dpsRTUp14134Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 6 is set"
	::= 14134

dpsRTUp15134Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 6 is cleared"
	::= 15134

dpsRTUp14135Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 7 is set"
	::= 14135

dpsRTUp15135Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 7 is cleared"
	::= 15135

dpsRTUp14136Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 8 is set"
	::= 14136

dpsRTUp15136Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 8 is cleared"
	::= 15136

dpsRTUp14137Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 9 is set"
	::= 14137

dpsRTUp15137Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 9 is cleared"
	::= 15137

dpsRTUp14138Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 10 is set"
	::= 14138

dpsRTUp15138Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 10 is cleared"
	::= 15138

dpsRTUp14139Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 11 is set"
	::= 14139

dpsRTUp15139Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 11 is cleared"
	::= 15139

dpsRTUp14140Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 12 is set"
	::= 14140

dpsRTUp15140Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 12 is cleared"
	::= 15140

dpsRTUp14141Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 13 is set"
	::= 14141

dpsRTUp15141Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 13 is cleared"
	::= 15141

dpsRTUp14142Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 14 is set"
	::= 14142

dpsRTUp15142Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 14 is cleared"
	::= 15142

dpsRTUp14143Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 15 is set"
	::= 14143

dpsRTUp15143Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 15 is cleared"
	::= 15143

dpsRTUp14144Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 16 is set"
	::= 14144

dpsRTUp15144Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 16 is cleared"
	::= 15144

dpsRTUp14145Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 17 is set"
	::= 14145

dpsRTUp15145Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 17 is cleared"
	::= 15145

dpsRTUp14146Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 18 is set"
	::= 14146

dpsRTUp15146Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 18 is cleared"
	::= 15146

dpsRTUp14147Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 19 is set"
	::= 14147

dpsRTUp15147Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 19 is cleared"
	::= 15147

dpsRTUp14148Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 20 is set"
	::= 14148

dpsRTUp15148Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 20 is cleared"
	::= 15148

dpsRTUp14149Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 21 is set"
	::= 14149

dpsRTUp15149Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 21 is cleared"
	::= 15149

dpsRTUp14150Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 22 is set"
	::= 14150

dpsRTUp15150Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 22 is cleared"
	::= 15150

dpsRTUp14151Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 23 is set"
	::= 14151

dpsRTUp15151Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 23 is cleared"
	::= 15151

dpsRTUp14152Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 24 is set"
	::= 14152

dpsRTUp15152Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 24 is cleared"
	::= 15152

dpsRTUp14153Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 25 is set"
	::= 14153

dpsRTUp15153Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 25 is cleared"
	::= 15153

dpsRTUp14154Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 26 is set"
	::= 14154

dpsRTUp15154Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 26 is cleared"
	::= 15154

dpsRTUp14155Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 27 is set"
	::= 14155

dpsRTUp15155Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 27 is cleared"
	::= 15155

dpsRTUp14156Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 28 is set"
	::= 14156

dpsRTUp15156Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 28 is cleared"
	::= 15156

dpsRTUp14157Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 29 is set"
	::= 14157

dpsRTUp15157Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 29 is cleared"
	::= 15157

dpsRTUp14158Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 30 is set"
	::= 14158

dpsRTUp15158Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 30 is cleared"
	::= 15158

dpsRTUp14159Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 31 is set"
	::= 14159

dpsRTUp15159Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 31 is cleared"
	::= 15159

dpsRTUp14160Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 32 is set"
	::= 14160

dpsRTUp15160Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 32 is cleared"
	::= 15160

dpsRTUp14161Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 33 is set"
	::= 14161

dpsRTUp15161Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 33 is cleared"
	::= 15161

dpsRTUp14162Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 34 is set"
	::= 14162

dpsRTUp15162Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 34 is cleared"
	::= 15162

dpsRTUp14163Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 35 is set"
	::= 14163

dpsRTUp15163Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 35 is cleared"
	::= 15163

dpsRTUp14164Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 36 is set"
	::= 14164

dpsRTUp15164Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 36 is cleared"
	::= 15164

dpsRTUp14165Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 37 is set"
	::= 14165

dpsRTUp15165Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 37 is cleared"
	::= 15165

dpsRTUp14166Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 38 is set"
	::= 14166

dpsRTUp15166Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 38 is cleared"
	::= 15166

dpsRTUp14167Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 39 is set"
	::= 14167

dpsRTUp15167Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 39 is cleared"
	::= 15167

dpsRTUp14168Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 40 is set"
	::= 14168

dpsRTUp15168Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 40 is cleared"
	::= 15168

dpsRTUp14169Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 41 is set"
	::= 14169

dpsRTUp15169Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 41 is cleared"
	::= 15169

dpsRTUp14170Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 42 is set"
	::= 14170

dpsRTUp15170Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 42 is cleared"
	::= 15170

dpsRTUp14171Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 43 is set"
	::= 14171

dpsRTUp15171Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 43 is cleared"
	::= 15171

dpsRTUp14172Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 44 is set"
	::= 14172

dpsRTUp15172Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 44 is cleared"
	::= 15172

dpsRTUp14173Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 45 is set"
	::= 14173

dpsRTUp15173Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 45 is cleared"
	::= 15173

dpsRTUp14174Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 46 is set"
	::= 14174

dpsRTUp15174Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 46 is cleared"
	::= 15174

dpsRTUp14175Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 47 is set"
	::= 14175

dpsRTUp15175Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 47 is cleared"
	::= 15175

dpsRTUp14176Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 48 is set"
	::= 14176

dpsRTUp15176Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 48 is cleared"
	::= 15176

dpsRTUp14177Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 49 is set"
	::= 14177

dpsRTUp15177Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 49 is cleared"
	::= 15177

dpsRTUp14178Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 50 is set"
	::= 14178

dpsRTUp15178Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 50 is cleared"
	::= 15178

dpsRTUp14179Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 51 is set"
	::= 14179

dpsRTUp15179Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 51 is cleared"
	::= 15179

dpsRTUp14180Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 52 is set"
	::= 14180

dpsRTUp15180Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 52 is cleared"
	::= 15180

dpsRTUp14181Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 53 is set"
	::= 14181

dpsRTUp15181Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 53 is cleared"
	::= 15181

dpsRTUp14182Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 54 is set"
	::= 14182

dpsRTUp15182Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 54 is cleared"
	::= 15182

dpsRTUp14183Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 55 is set"
	::= 14183

dpsRTUp15183Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 55 is cleared"
	::= 15183

dpsRTUp14184Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 56 is set"
	::= 14184

dpsRTUp15184Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 56 is cleared"
	::= 15184

dpsRTUp14185Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 57 is set"
	::= 14185

dpsRTUp15185Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 57 is cleared"
	::= 15185

dpsRTUp14186Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 58 is set"
	::= 14186

dpsRTUp15186Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 58 is cleared"
	::= 15186

dpsRTUp14187Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 59 is set"
	::= 14187

dpsRTUp15187Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 59 is cleared"
	::= 15187

dpsRTUp14188Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 60 is set"
	::= 14188

dpsRTUp15188Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 60 is cleared"
	::= 15188

dpsRTUp14189Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 61 is set"
	::= 14189

dpsRTUp15189Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 61 is cleared"
	::= 15189

dpsRTUp14190Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 62 is set"
	::= 14190

dpsRTUp15190Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 62 is cleared"
	::= 15190

dpsRTUp14191Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 63 is set"
	::= 14191

dpsRTUp15191Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 63 is cleared"
	::= 15191

dpsRTUp14192Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 64 is set"
	::= 14192

dpsRTUp15192Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 3 point 64 is cleared"
	::= 15192

dpsRTUp14193Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 1 is set"
	::= 14193

dpsRTUp15193Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 1 is cleared"
	::= 15193

dpsRTUp14194Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 2 is set"
	::= 14194

dpsRTUp15194Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 2 is cleared"
	::= 15194

dpsRTUp14195Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 3 is set"
	::= 14195

dpsRTUp15195Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 3 is cleared"
	::= 15195

dpsRTUp14196Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 4 is set"
	::= 14196

dpsRTUp15196Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 4 is cleared"
	::= 15196

dpsRTUp14197Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 5 is set"
	::= 14197

dpsRTUp15197Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 5 is cleared"
	::= 15197

dpsRTUp14198Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 6 is set"
	::= 14198

dpsRTUp15198Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 6 is cleared"
	::= 15198

dpsRTUp14199Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 7 is set"
	::= 14199

dpsRTUp15199Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 7 is cleared"
	::= 15199

dpsRTUp14200Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 8 is set"
	::= 14200

dpsRTUp15200Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 8 is cleared"
	::= 15200

dpsRTUp14201Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 9 is set"
	::= 14201

dpsRTUp15201Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 9 is cleared"
	::= 15201

dpsRTUp14202Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 10 is set"
	::= 14202

dpsRTUp15202Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 10 is cleared"
	::= 15202

dpsRTUp14203Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 11 is set"
	::= 14203

dpsRTUp15203Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 11 is cleared"
	::= 15203

dpsRTUp14204Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 12 is set"
	::= 14204

dpsRTUp15204Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 12 is cleared"
	::= 15204

dpsRTUp14205Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 13 is set"
	::= 14205

dpsRTUp15205Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 13 is cleared"
	::= 15205

dpsRTUp14206Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 14 is set"
	::= 14206

dpsRTUp15206Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 14 is cleared"
	::= 15206

dpsRTUp14207Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 15 is set"
	::= 14207

dpsRTUp15207Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 15 is cleared"
	::= 15207

dpsRTUp14208Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 16 is set"
	::= 14208

dpsRTUp15208Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 16 is cleared"
	::= 15208

dpsRTUp14209Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 17 is set"
	::= 14209

dpsRTUp15209Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 17 is cleared"
	::= 15209

dpsRTUp14210Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 18 is set"
	::= 14210

dpsRTUp15210Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 18 is cleared"
	::= 15210

dpsRTUp14211Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 19 is set"
	::= 14211

dpsRTUp15211Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 19 is cleared"
	::= 15211

dpsRTUp14212Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 20 is set"
	::= 14212

dpsRTUp15212Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 20 is cleared"
	::= 15212

dpsRTUp14213Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 21 is set"
	::= 14213

dpsRTUp15213Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 21 is cleared"
	::= 15213

dpsRTUp14214Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 22 is set"
	::= 14214

dpsRTUp15214Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 22 is cleared"
	::= 15214

dpsRTUp14215Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 23 is set"
	::= 14215

dpsRTUp15215Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 23 is cleared"
	::= 15215

dpsRTUp14216Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 24 is set"
	::= 14216

dpsRTUp15216Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 24 is cleared"
	::= 15216

dpsRTUp14217Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 25 is set"
	::= 14217

dpsRTUp15217Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 25 is cleared"
	::= 15217

dpsRTUp14218Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 26 is set"
	::= 14218

dpsRTUp15218Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 26 is cleared"
	::= 15218

dpsRTUp14219Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 27 is set"
	::= 14219

dpsRTUp15219Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 27 is cleared"
	::= 15219

dpsRTUp14220Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 28 is set"
	::= 14220

dpsRTUp15220Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 28 is cleared"
	::= 15220

dpsRTUp14221Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 29 is set"
	::= 14221

dpsRTUp15221Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 29 is cleared"
	::= 15221

dpsRTUp14222Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 30 is set"
	::= 14222

dpsRTUp15222Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 30 is cleared"
	::= 15222

dpsRTUp14223Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 31 is set"
	::= 14223

dpsRTUp15223Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 31 is cleared"
	::= 15223

dpsRTUp14224Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 32 is set"
	::= 14224

dpsRTUp15224Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 32 is cleared"
	::= 15224

dpsRTUp14225Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 33 is set"
	::= 14225

dpsRTUp15225Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 33 is cleared"
	::= 15225

dpsRTUp14226Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 34 is set"
	::= 14226

dpsRTUp15226Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 34 is cleared"
	::= 15226

dpsRTUp14227Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 35 is set"
	::= 14227

dpsRTUp15227Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 35 is cleared"
	::= 15227

dpsRTUp14228Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 36 is set"
	::= 14228

dpsRTUp15228Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 36 is cleared"
	::= 15228

dpsRTUp14229Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 37 is set"
	::= 14229

dpsRTUp15229Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 37 is cleared"
	::= 15229

dpsRTUp14230Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 38 is set"
	::= 14230

dpsRTUp15230Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 38 is cleared"
	::= 15230

dpsRTUp14231Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 39 is set"
	::= 14231

dpsRTUp15231Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 39 is cleared"
	::= 15231

dpsRTUp14232Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 40 is set"
	::= 14232

dpsRTUp15232Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 40 is cleared"
	::= 15232

dpsRTUp14233Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 41 is set"
	::= 14233

dpsRTUp15233Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 41 is cleared"
	::= 15233

dpsRTUp14234Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 42 is set"
	::= 14234

dpsRTUp15234Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 42 is cleared"
	::= 15234

dpsRTUp14235Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 43 is set"
	::= 14235

dpsRTUp15235Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 43 is cleared"
	::= 15235

dpsRTUp14236Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 44 is set"
	::= 14236

dpsRTUp15236Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 44 is cleared"
	::= 15236

dpsRTUp14237Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 45 is set"
	::= 14237

dpsRTUp15237Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 45 is cleared"
	::= 15237

dpsRTUp14238Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 46 is set"
	::= 14238

dpsRTUp15238Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 46 is cleared"
	::= 15238

dpsRTUp14239Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 47 is set"
	::= 14239

dpsRTUp15239Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 47 is cleared"
	::= 15239

dpsRTUp14240Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 48 is set"
	::= 14240

dpsRTUp15240Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 48 is cleared"
	::= 15240

dpsRTUp14241Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 49 is set"
	::= 14241

dpsRTUp15241Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 49 is cleared"
	::= 15241

dpsRTUp14242Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 50 is set"
	::= 14242

dpsRTUp15242Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 50 is cleared"
	::= 15242

dpsRTUp14243Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 51 is set"
	::= 14243

dpsRTUp15243Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 51 is cleared"
	::= 15243

dpsRTUp14244Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 52 is set"
	::= 14244

dpsRTUp15244Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 52 is cleared"
	::= 15244

dpsRTUp14245Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 53 is set"
	::= 14245

dpsRTUp15245Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 53 is cleared"
	::= 15245

dpsRTUp14246Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 54 is set"
	::= 14246

dpsRTUp15246Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 54 is cleared"
	::= 15246

dpsRTUp14247Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 55 is set"
	::= 14247

dpsRTUp15247Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 55 is cleared"
	::= 15247

dpsRTUp14248Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 56 is set"
	::= 14248

dpsRTUp15248Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 56 is cleared"
	::= 15248

dpsRTUp14249Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 57 is set"
	::= 14249

dpsRTUp15249Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 57 is cleared"
	::= 15249

dpsRTUp14250Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 58 is set"
	::= 14250

dpsRTUp15250Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 58 is cleared"
	::= 15250

dpsRTUp14251Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 59 is set"
	::= 14251

dpsRTUp15251Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 59 is cleared"
	::= 15251

dpsRTUp14252Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 60 is set"
	::= 14252

dpsRTUp15252Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 60 is cleared"
	::= 15252

dpsRTUp14253Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 61 is set"
	::= 14253

dpsRTUp15253Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 61 is cleared"
	::= 15253

dpsRTUp14254Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 62 is set"
	::= 14254

dpsRTUp15254Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 62 is cleared"
	::= 15254

dpsRTUp14255Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 63 is set"
	::= 14255

dpsRTUp15255Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 63 is cleared"
	::= 15255

dpsRTUp14256Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 64 is set"
	::= 14256

dpsRTUp15256Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 4 point 64 is cleared"
	::= 15256

dpsRTUp14257Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 1 is set"
	::= 14257

dpsRTUp15257Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 1 is cleared"
	::= 15257

dpsRTUp14258Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 2 is set"
	::= 14258

dpsRTUp15258Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 2 is cleared"
	::= 15258

dpsRTUp14259Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 3 is set"
	::= 14259

dpsRTUp15259Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 3 is cleared"
	::= 15259

dpsRTUp14260Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 4 is set"
	::= 14260

dpsRTUp15260Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 4 is cleared"
	::= 15260

dpsRTUp14261Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 5 is set"
	::= 14261

dpsRTUp15261Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 5 is cleared"
	::= 15261

dpsRTUp14262Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 6 is set"
	::= 14262

dpsRTUp15262Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 6 is cleared"
	::= 15262

dpsRTUp14263Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 7 is set"
	::= 14263

dpsRTUp15263Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 7 is cleared"
	::= 15263

dpsRTUp14264Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 8 is set"
	::= 14264

dpsRTUp15264Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 8 is cleared"
	::= 15264

dpsRTUp14265Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 9 is set"
	::= 14265

dpsRTUp15265Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 9 is cleared"
	::= 15265

dpsRTUp14266Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 10 is set"
	::= 14266

dpsRTUp15266Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 10 is cleared"
	::= 15266

dpsRTUp14267Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 11 is set"
	::= 14267

dpsRTUp15267Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 11 is cleared"
	::= 15267

dpsRTUp14268Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 12 is set"
	::= 14268

dpsRTUp15268Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 12 is cleared"
	::= 15268

dpsRTUp14269Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 13 is set"
	::= 14269

dpsRTUp15269Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 13 is cleared"
	::= 15269

dpsRTUp14270Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 14 is set"
	::= 14270

dpsRTUp15270Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 14 is cleared"
	::= 15270

dpsRTUp14271Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 15 is set"
	::= 14271

dpsRTUp15271Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 15 is cleared"
	::= 15271

dpsRTUp14272Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 16 is set"
	::= 14272

dpsRTUp15272Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 16 is cleared"
	::= 15272

dpsRTUp14273Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 17 is set"
	::= 14273

dpsRTUp15273Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 17 is cleared"
	::= 15273

dpsRTUp14274Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 18 is set"
	::= 14274

dpsRTUp15274Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 18 is cleared"
	::= 15274

dpsRTUp14275Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 19 is set"
	::= 14275

dpsRTUp15275Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 19 is cleared"
	::= 15275

dpsRTUp14276Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 20 is set"
	::= 14276

dpsRTUp15276Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 20 is cleared"
	::= 15276

dpsRTUp14277Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 21 is set"
	::= 14277

dpsRTUp15277Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 21 is cleared"
	::= 15277

dpsRTUp14278Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 22 is set"
	::= 14278

dpsRTUp15278Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 22 is cleared"
	::= 15278

dpsRTUp14279Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 23 is set"
	::= 14279

dpsRTUp15279Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 23 is cleared"
	::= 15279

dpsRTUp14280Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 24 is set"
	::= 14280

dpsRTUp15280Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 24 is cleared"
	::= 15280

dpsRTUp14281Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 25 is set"
	::= 14281

dpsRTUp15281Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 25 is cleared"
	::= 15281

dpsRTUp14282Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 26 is set"
	::= 14282

dpsRTUp15282Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 26 is cleared"
	::= 15282

dpsRTUp14283Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 27 is set"
	::= 14283

dpsRTUp15283Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 27 is cleared"
	::= 15283

dpsRTUp14284Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 28 is set"
	::= 14284

dpsRTUp15284Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 28 is cleared"
	::= 15284

dpsRTUp14285Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 29 is set"
	::= 14285

dpsRTUp15285Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 29 is cleared"
	::= 15285

dpsRTUp14286Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 30 is set"
	::= 14286

dpsRTUp15286Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 30 is cleared"
	::= 15286

dpsRTUp14287Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 31 is set"
	::= 14287

dpsRTUp15287Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 31 is cleared"
	::= 15287

dpsRTUp14288Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 32 is set"
	::= 14288

dpsRTUp15288Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 32 is cleared"
	::= 15288

dpsRTUp14289Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 33 is set"
	::= 14289

dpsRTUp15289Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 33 is cleared"
	::= 15289

dpsRTUp14290Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 34 is set"
	::= 14290

dpsRTUp15290Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 34 is cleared"
	::= 15290

dpsRTUp14291Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 35 is set"
	::= 14291

dpsRTUp15291Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 35 is cleared"
	::= 15291

dpsRTUp14292Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 36 is set"
	::= 14292

dpsRTUp15292Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 36 is cleared"
	::= 15292

dpsRTUp14293Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 37 is set"
	::= 14293

dpsRTUp15293Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 37 is cleared"
	::= 15293

dpsRTUp14294Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 38 is set"
	::= 14294

dpsRTUp15294Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 38 is cleared"
	::= 15294

dpsRTUp14295Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 39 is set"
	::= 14295

dpsRTUp15295Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 39 is cleared"
	::= 15295

dpsRTUp14296Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 40 is set"
	::= 14296

dpsRTUp15296Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 40 is cleared"
	::= 15296

dpsRTUp14297Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 41 is set"
	::= 14297

dpsRTUp15297Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 41 is cleared"
	::= 15297

dpsRTUp14298Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 42 is set"
	::= 14298

dpsRTUp15298Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 42 is cleared"
	::= 15298

dpsRTUp14299Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 43 is set"
	::= 14299

dpsRTUp15299Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 43 is cleared"
	::= 15299

dpsRTUp14300Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 44 is set"
	::= 14300

dpsRTUp15300Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 44 is cleared"
	::= 15300

dpsRTUp14301Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 45 is set"
	::= 14301

dpsRTUp15301Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 45 is cleared"
	::= 15301

dpsRTUp14302Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 46 is set"
	::= 14302

dpsRTUp15302Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 46 is cleared"
	::= 15302

dpsRTUp14303Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 47 is set"
	::= 14303

dpsRTUp15303Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 47 is cleared"
	::= 15303

dpsRTUp14304Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 48 is set"
	::= 14304

dpsRTUp15304Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 48 is cleared"
	::= 15304

dpsRTUp14305Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 49 is set"
	::= 14305

dpsRTUp15305Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 49 is cleared"
	::= 15305

dpsRTUp14306Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 50 is set"
	::= 14306

dpsRTUp15306Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 50 is cleared"
	::= 15306

dpsRTUp14307Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 51 is set"
	::= 14307

dpsRTUp15307Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 51 is cleared"
	::= 15307

dpsRTUp14308Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 52 is set"
	::= 14308

dpsRTUp15308Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 52 is cleared"
	::= 15308

dpsRTUp14309Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 53 is set"
	::= 14309

dpsRTUp15309Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 53 is cleared"
	::= 15309

dpsRTUp14310Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 54 is set"
	::= 14310

dpsRTUp15310Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 54 is cleared"
	::= 15310

dpsRTUp14311Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 55 is set"
	::= 14311

dpsRTUp15311Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 55 is cleared"
	::= 15311

dpsRTUp14312Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 56 is set"
	::= 14312

dpsRTUp15312Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 56 is cleared"
	::= 15312

dpsRTUp14313Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 57 is set"
	::= 14313

dpsRTUp15313Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 57 is cleared"
	::= 15313

dpsRTUp14314Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 58 is set"
	::= 14314

dpsRTUp15314Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 58 is cleared"
	::= 15314

dpsRTUp14315Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 59 is set"
	::= 14315

dpsRTUp15315Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 59 is cleared"
	::= 15315

dpsRTUp14316Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 60 is set"
	::= 14316

dpsRTUp15316Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 60 is cleared"
	::= 15316

dpsRTUp14317Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 61 is set"
	::= 14317

dpsRTUp15317Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 61 is cleared"
	::= 15317

dpsRTUp14318Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 62 is set"
	::= 14318

dpsRTUp15318Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 62 is cleared"
	::= 15318

dpsRTUp14319Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 63 is set"
	::= 14319

dpsRTUp15319Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 63 is cleared"
	::= 15319

dpsRTUp14320Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 64 is set"
	::= 14320

dpsRTUp15320Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 5 point 64 is cleared"
	::= 15320

dpsRTUp14321Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 1 is set"
	::= 14321

dpsRTUp15321Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 1 is cleared"
	::= 15321

dpsRTUp14322Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 2 is set"
	::= 14322

dpsRTUp15322Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 2 is cleared"
	::= 15322

dpsRTUp14323Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 3 is set"
	::= 14323

dpsRTUp15323Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 3 is cleared"
	::= 15323

dpsRTUp14324Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 4 is set"
	::= 14324

dpsRTUp15324Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 4 is cleared"
	::= 15324

dpsRTUp14325Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 5 is set"
	::= 14325

dpsRTUp15325Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 5 is cleared"
	::= 15325

dpsRTUp14326Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 6 is set"
	::= 14326

dpsRTUp15326Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 6 is cleared"
	::= 15326

dpsRTUp14327Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 7 is set"
	::= 14327

dpsRTUp15327Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 7 is cleared"
	::= 15327

dpsRTUp14328Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 8 is set"
	::= 14328

dpsRTUp15328Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 8 is cleared"
	::= 15328

dpsRTUp14329Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 9 is set"
	::= 14329

dpsRTUp15329Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 9 is cleared"
	::= 15329

dpsRTUp14330Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 10 is set"
	::= 14330

dpsRTUp15330Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 10 is cleared"
	::= 15330

dpsRTUp14331Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 11 is set"
	::= 14331

dpsRTUp15331Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 11 is cleared"
	::= 15331

dpsRTUp14332Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 12 is set"
	::= 14332

dpsRTUp15332Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 12 is cleared"
	::= 15332

dpsRTUp14333Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 13 is set"
	::= 14333

dpsRTUp15333Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 13 is cleared"
	::= 15333

dpsRTUp14334Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 14 is set"
	::= 14334

dpsRTUp15334Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 14 is cleared"
	::= 15334

dpsRTUp14335Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 15 is set"
	::= 14335

dpsRTUp15335Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 15 is cleared"
	::= 15335

dpsRTUp14336Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 16 is set"
	::= 14336

dpsRTUp15336Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 16 is cleared"
	::= 15336

dpsRTUp14337Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 17 is set"
	::= 14337

dpsRTUp15337Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 17 is cleared"
	::= 15337

dpsRTUp14338Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 18 is set"
	::= 14338

dpsRTUp15338Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 18 is cleared"
	::= 15338

dpsRTUp14339Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 19 is set"
	::= 14339

dpsRTUp15339Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 19 is cleared"
	::= 15339

dpsRTUp14340Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 20 is set"
	::= 14340

dpsRTUp15340Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 20 is cleared"
	::= 15340

dpsRTUp14341Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 21 is set"
	::= 14341

dpsRTUp15341Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 21 is cleared"
	::= 15341

dpsRTUp14342Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 22 is set"
	::= 14342

dpsRTUp15342Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 22 is cleared"
	::= 15342

dpsRTUp14343Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 23 is set"
	::= 14343

dpsRTUp15343Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 23 is cleared"
	::= 15343

dpsRTUp14344Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 24 is set"
	::= 14344

dpsRTUp15344Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 24 is cleared"
	::= 15344

dpsRTUp14345Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 25 is set"
	::= 14345

dpsRTUp15345Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 25 is cleared"
	::= 15345

dpsRTUp14346Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 26 is set"
	::= 14346

dpsRTUp15346Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 26 is cleared"
	::= 15346

dpsRTUp14347Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 27 is set"
	::= 14347

dpsRTUp15347Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 27 is cleared"
	::= 15347

dpsRTUp14348Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 28 is set"
	::= 14348

dpsRTUp15348Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 28 is cleared"
	::= 15348

dpsRTUp14349Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 29 is set"
	::= 14349

dpsRTUp15349Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 29 is cleared"
	::= 15349

dpsRTUp14350Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 30 is set"
	::= 14350

dpsRTUp15350Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 30 is cleared"
	::= 15350

dpsRTUp14351Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 31 is set"
	::= 14351

dpsRTUp15351Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 31 is cleared"
	::= 15351

dpsRTUp14352Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 32 is set"
	::= 14352

dpsRTUp15352Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 32 is cleared"
	::= 15352

dpsRTUp14353Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 33 is set"
	::= 14353

dpsRTUp15353Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 33 is cleared"
	::= 15353

dpsRTUp14354Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 34 is set"
	::= 14354

dpsRTUp15354Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 34 is cleared"
	::= 15354

dpsRTUp14355Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 35 is set"
	::= 14355

dpsRTUp15355Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 35 is cleared"
	::= 15355

dpsRTUp14356Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 36 is set"
	::= 14356

dpsRTUp15356Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 36 is cleared"
	::= 15356

dpsRTUp14357Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 37 is set"
	::= 14357

dpsRTUp15357Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 37 is cleared"
	::= 15357

dpsRTUp14358Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 38 is set"
	::= 14358

dpsRTUp15358Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 38 is cleared"
	::= 15358

dpsRTUp14359Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 39 is set"
	::= 14359

dpsRTUp15359Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 39 is cleared"
	::= 15359

dpsRTUp14360Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 40 is set"
	::= 14360

dpsRTUp15360Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 40 is cleared"
	::= 15360

dpsRTUp14361Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 41 is set"
	::= 14361

dpsRTUp15361Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 41 is cleared"
	::= 15361

dpsRTUp14362Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 42 is set"
	::= 14362

dpsRTUp15362Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 42 is cleared"
	::= 15362

dpsRTUp14363Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 43 is set"
	::= 14363

dpsRTUp15363Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 43 is cleared"
	::= 15363

dpsRTUp14364Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 44 is set"
	::= 14364

dpsRTUp15364Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 44 is cleared"
	::= 15364

dpsRTUp14365Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 45 is set"
	::= 14365

dpsRTUp15365Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 45 is cleared"
	::= 15365

dpsRTUp14366Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 46 is set"
	::= 14366

dpsRTUp15366Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 46 is cleared"
	::= 15366

dpsRTUp14367Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 47 is set"
	::= 14367

dpsRTUp15367Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 47 is cleared"
	::= 15367

dpsRTUp14368Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 48 is set"
	::= 14368

dpsRTUp15368Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 48 is cleared"
	::= 15368

dpsRTUp14369Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 49 is set"
	::= 14369

dpsRTUp15369Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 49 is cleared"
	::= 15369

dpsRTUp14370Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 50 is set"
	::= 14370

dpsRTUp15370Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 50 is cleared"
	::= 15370

dpsRTUp14371Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 51 is set"
	::= 14371

dpsRTUp15371Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 51 is cleared"
	::= 15371

dpsRTUp14372Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 52 is set"
	::= 14372

dpsRTUp15372Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 52 is cleared"
	::= 15372

dpsRTUp14373Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 53 is set"
	::= 14373

dpsRTUp15373Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 53 is cleared"
	::= 15373

dpsRTUp14374Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 54 is set"
	::= 14374

dpsRTUp15374Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 54 is cleared"
	::= 15374

dpsRTUp14375Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 55 is set"
	::= 14375

dpsRTUp15375Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 55 is cleared"
	::= 15375

dpsRTUp14376Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 56 is set"
	::= 14376

dpsRTUp15376Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 56 is cleared"
	::= 15376

dpsRTUp14377Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 57 is set"
	::= 14377

dpsRTUp15377Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 57 is cleared"
	::= 15377

dpsRTUp14378Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 58 is set"
	::= 14378

dpsRTUp15378Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 58 is cleared"
	::= 15378

dpsRTUp14379Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 59 is set"
	::= 14379

dpsRTUp15379Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 59 is cleared"
	::= 15379

dpsRTUp14380Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 60 is set"
	::= 14380

dpsRTUp15380Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 60 is cleared"
	::= 15380

dpsRTUp14381Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 61 is set"
	::= 14381

dpsRTUp15381Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 61 is cleared"
	::= 15381

dpsRTUp14382Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 62 is set"
	::= 14382

dpsRTUp15382Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 62 is cleared"
	::= 15382

dpsRTUp14383Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 63 is set"
	::= 14383

dpsRTUp15383Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 63 is cleared"
	::= 15383

dpsRTUp14384Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 64 is set"
	::= 14384

dpsRTUp15384Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 6 point 64 is cleared"
	::= 15384

dpsRTUp14385Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 1 is set"
	::= 14385

dpsRTUp15385Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 1 is cleared"
	::= 15385

dpsRTUp14386Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 2 is set"
	::= 14386

dpsRTUp15386Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 2 is cleared"
	::= 15386

dpsRTUp14387Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 3 is set"
	::= 14387

dpsRTUp15387Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 3 is cleared"
	::= 15387

dpsRTUp14388Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 4 is set"
	::= 14388

dpsRTUp15388Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 4 is cleared"
	::= 15388

dpsRTUp14389Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 5 is set"
	::= 14389

dpsRTUp15389Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 5 is cleared"
	::= 15389

dpsRTUp14390Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 6 is set"
	::= 14390

dpsRTUp15390Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 6 is cleared"
	::= 15390

dpsRTUp14391Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 7 is set"
	::= 14391

dpsRTUp15391Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 7 is cleared"
	::= 15391

dpsRTUp14392Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 8 is set"
	::= 14392

dpsRTUp15392Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 8 is cleared"
	::= 15392

dpsRTUp14393Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 9 is set"
	::= 14393

dpsRTUp15393Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 9 is cleared"
	::= 15393

dpsRTUp14394Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 10 is set"
	::= 14394

dpsRTUp15394Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 10 is cleared"
	::= 15394

dpsRTUp14395Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 11 is set"
	::= 14395

dpsRTUp15395Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 11 is cleared"
	::= 15395

dpsRTUp14396Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 12 is set"
	::= 14396

dpsRTUp15396Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 12 is cleared"
	::= 15396

dpsRTUp14397Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 13 is set"
	::= 14397

dpsRTUp15397Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 13 is cleared"
	::= 15397

dpsRTUp14398Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 14 is set"
	::= 14398

dpsRTUp15398Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 14 is cleared"
	::= 15398

dpsRTUp14399Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 15 is set"
	::= 14399

dpsRTUp15399Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 15 is cleared"
	::= 15399

dpsRTUp14400Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 16 is set"
	::= 14400

dpsRTUp15400Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 16 is cleared"
	::= 15400

dpsRTUp14401Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 17 is set"
	::= 14401

dpsRTUp15401Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 17 is cleared"
	::= 15401

dpsRTUp14402Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 18 is set"
	::= 14402

dpsRTUp15402Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 18 is cleared"
	::= 15402

dpsRTUp14403Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 19 is set"
	::= 14403

dpsRTUp15403Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 19 is cleared"
	::= 15403

dpsRTUp14404Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 20 is set"
	::= 14404

dpsRTUp15404Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 20 is cleared"
	::= 15404

dpsRTUp14405Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 21 is set"
	::= 14405

dpsRTUp15405Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 21 is cleared"
	::= 15405

dpsRTUp14406Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 22 is set"
	::= 14406

dpsRTUp15406Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 22 is cleared"
	::= 15406

dpsRTUp14407Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 23 is set"
	::= 14407

dpsRTUp15407Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 23 is cleared"
	::= 15407

dpsRTUp14408Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 24 is set"
	::= 14408

dpsRTUp15408Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 24 is cleared"
	::= 15408

dpsRTUp14409Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 25 is set"
	::= 14409

dpsRTUp15409Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 25 is cleared"
	::= 15409

dpsRTUp14410Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 26 is set"
	::= 14410

dpsRTUp15410Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 26 is cleared"
	::= 15410

dpsRTUp14411Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 27 is set"
	::= 14411

dpsRTUp15411Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 27 is cleared"
	::= 15411

dpsRTUp14412Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 28 is set"
	::= 14412

dpsRTUp15412Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 28 is cleared"
	::= 15412

dpsRTUp14413Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 29 is set"
	::= 14413

dpsRTUp15413Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 29 is cleared"
	::= 15413

dpsRTUp14414Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 30 is set"
	::= 14414

dpsRTUp15414Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 30 is cleared"
	::= 15414

dpsRTUp14415Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 31 is set"
	::= 14415

dpsRTUp15415Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 31 is cleared"
	::= 15415

dpsRTUp14416Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 32 is set"
	::= 14416

dpsRTUp15416Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 32 is cleared"
	::= 15416

dpsRTUp14417Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 33 is set"
	::= 14417

dpsRTUp15417Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 33 is cleared"
	::= 15417

dpsRTUp14418Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 34 is set"
	::= 14418

dpsRTUp15418Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 34 is cleared"
	::= 15418

dpsRTUp14419Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 35 is set"
	::= 14419

dpsRTUp15419Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 35 is cleared"
	::= 15419

dpsRTUp14420Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 36 is set"
	::= 14420

dpsRTUp15420Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 36 is cleared"
	::= 15420

dpsRTUp14421Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 37 is set"
	::= 14421

dpsRTUp15421Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 37 is cleared"
	::= 15421

dpsRTUp14422Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 38 is set"
	::= 14422

dpsRTUp15422Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 38 is cleared"
	::= 15422

dpsRTUp14423Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 39 is set"
	::= 14423

dpsRTUp15423Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 39 is cleared"
	::= 15423

dpsRTUp14424Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 40 is set"
	::= 14424

dpsRTUp15424Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 40 is cleared"
	::= 15424

dpsRTUp14425Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 41 is set"
	::= 14425

dpsRTUp15425Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 41 is cleared"
	::= 15425

dpsRTUp14426Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 42 is set"
	::= 14426

dpsRTUp15426Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 42 is cleared"
	::= 15426

dpsRTUp14427Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 43 is set"
	::= 14427

dpsRTUp15427Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 43 is cleared"
	::= 15427

dpsRTUp14428Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 44 is set"
	::= 14428

dpsRTUp15428Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 44 is cleared"
	::= 15428

dpsRTUp14429Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 45 is set"
	::= 14429

dpsRTUp15429Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 45 is cleared"
	::= 15429

dpsRTUp14430Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 46 is set"
	::= 14430

dpsRTUp15430Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 46 is cleared"
	::= 15430

dpsRTUp14431Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 47 is set"
	::= 14431

dpsRTUp15431Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 47 is cleared"
	::= 15431

dpsRTUp14432Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 48 is set"
	::= 14432

dpsRTUp15432Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 48 is cleared"
	::= 15432

dpsRTUp14433Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 49 is set"
	::= 14433

dpsRTUp15433Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 49 is cleared"
	::= 15433

dpsRTUp14434Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 50 is set"
	::= 14434

dpsRTUp15434Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 50 is cleared"
	::= 15434

dpsRTUp14435Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 51 is set"
	::= 14435

dpsRTUp15435Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 51 is cleared"
	::= 15435

dpsRTUp14436Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 52 is set"
	::= 14436

dpsRTUp15436Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 52 is cleared"
	::= 15436

dpsRTUp14437Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 53 is set"
	::= 14437

dpsRTUp15437Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 53 is cleared"
	::= 15437

dpsRTUp14438Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 54 is set"
	::= 14438

dpsRTUp15438Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 54 is cleared"
	::= 15438

dpsRTUp14439Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 55 is set"
	::= 14439

dpsRTUp15439Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 55 is cleared"
	::= 15439

dpsRTUp14440Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 56 is set"
	::= 14440

dpsRTUp15440Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 56 is cleared"
	::= 15440

dpsRTUp14441Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 57 is set"
	::= 14441

dpsRTUp15441Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 57 is cleared"
	::= 15441

dpsRTUp14442Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 58 is set"
	::= 14442

dpsRTUp15442Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 58 is cleared"
	::= 15442

dpsRTUp14443Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 59 is set"
	::= 14443

dpsRTUp15443Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 59 is cleared"
	::= 15443

dpsRTUp14444Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 60 is set"
	::= 14444

dpsRTUp15444Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 60 is cleared"
	::= 15444

dpsRTUp14445Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 61 is set"
	::= 14445

dpsRTUp15445Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 61 is cleared"
	::= 15445

dpsRTUp14446Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 62 is set"
	::= 14446

dpsRTUp15446Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 62 is cleared"
	::= 15446

dpsRTUp14447Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 63 is set"
	::= 14447

dpsRTUp15447Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 63 is cleared"
	::= 15447

dpsRTUp14448Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 64 is set"
	::= 14448

dpsRTUp15448Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 7 point 64 is cleared"
	::= 15448

dpsRTUp14449Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 1 is set"
	::= 14449

dpsRTUp15449Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 1 is cleared"
	::= 15449

dpsRTUp14450Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 2 is set"
	::= 14450

dpsRTUp15450Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 2 is cleared"
	::= 15450

dpsRTUp14451Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 3 is set"
	::= 14451

dpsRTUp15451Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 3 is cleared"
	::= 15451

dpsRTUp14452Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 4 is set"
	::= 14452

dpsRTUp15452Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 4 is cleared"
	::= 15452

dpsRTUp14453Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 5 is set"
	::= 14453

dpsRTUp15453Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 5 is cleared"
	::= 15453

dpsRTUp14454Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 6 is set"
	::= 14454

dpsRTUp15454Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 6 is cleared"
	::= 15454

dpsRTUp14455Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 7 is set"
	::= 14455

dpsRTUp15455Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 7 is cleared"
	::= 15455

dpsRTUp14456Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 8 is set"
	::= 14456

dpsRTUp15456Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 8 is cleared"
	::= 15456

dpsRTUp14457Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 9 is set"
	::= 14457

dpsRTUp15457Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 9 is cleared"
	::= 15457

dpsRTUp14458Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 10 is set"
	::= 14458

dpsRTUp15458Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 10 is cleared"
	::= 15458

dpsRTUp14459Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 11 is set"
	::= 14459

dpsRTUp15459Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 11 is cleared"
	::= 15459

dpsRTUp14460Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 12 is set"
	::= 14460

dpsRTUp15460Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 12 is cleared"
	::= 15460

dpsRTUp14461Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 13 is set"
	::= 14461

dpsRTUp15461Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 13 is cleared"
	::= 15461

dpsRTUp14462Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 14 is set"
	::= 14462

dpsRTUp15462Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 14 is cleared"
	::= 15462

dpsRTUp14463Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 15 is set"
	::= 14463

dpsRTUp15463Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 15 is cleared"
	::= 15463

dpsRTUp14464Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 16 is set"
	::= 14464

dpsRTUp15464Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 16 is cleared"
	::= 15464

dpsRTUp14465Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 17 is set"
	::= 14465

dpsRTUp15465Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 17 is cleared"
	::= 15465

dpsRTUp14466Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 18 is set"
	::= 14466

dpsRTUp15466Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 18 is cleared"
	::= 15466

dpsRTUp14467Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 19 is set"
	::= 14467

dpsRTUp15467Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 19 is cleared"
	::= 15467

dpsRTUp14468Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 20 is set"
	::= 14468

dpsRTUp15468Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 20 is cleared"
	::= 15468

dpsRTUp14469Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 21 is set"
	::= 14469

dpsRTUp15469Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 21 is cleared"
	::= 15469

dpsRTUp14470Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 22 is set"
	::= 14470

dpsRTUp15470Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 22 is cleared"
	::= 15470

dpsRTUp14471Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 23 is set"
	::= 14471

dpsRTUp15471Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 23 is cleared"
	::= 15471

dpsRTUp14472Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 24 is set"
	::= 14472

dpsRTUp15472Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 24 is cleared"
	::= 15472

dpsRTUp14473Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 25 is set"
	::= 14473

dpsRTUp15473Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 25 is cleared"
	::= 15473

dpsRTUp14474Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 26 is set"
	::= 14474

dpsRTUp15474Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 26 is cleared"
	::= 15474

dpsRTUp14475Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 27 is set"
	::= 14475

dpsRTUp15475Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 27 is cleared"
	::= 15475

dpsRTUp14476Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 28 is set"
	::= 14476

dpsRTUp15476Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 28 is cleared"
	::= 15476

dpsRTUp14477Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 29 is set"
	::= 14477

dpsRTUp15477Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 29 is cleared"
	::= 15477

dpsRTUp14478Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 30 is set"
	::= 14478

dpsRTUp15478Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 30 is cleared"
	::= 15478

dpsRTUp14479Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 31 is set"
	::= 14479

dpsRTUp15479Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 31 is cleared"
	::= 15479

dpsRTUp14480Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 32 is set"
	::= 14480

dpsRTUp15480Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 32 is cleared"
	::= 15480

dpsRTUp14481Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 33 is set"
	::= 14481

dpsRTUp15481Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 33 is cleared"
	::= 15481

dpsRTUp14482Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 34 is set"
	::= 14482

dpsRTUp15482Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 34 is cleared"
	::= 15482

dpsRTUp14483Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 35 is set"
	::= 14483

dpsRTUp15483Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 35 is cleared"
	::= 15483

dpsRTUp14484Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 36 is set"
	::= 14484

dpsRTUp15484Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 36 is cleared"
	::= 15484

dpsRTUp14485Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 37 is set"
	::= 14485

dpsRTUp15485Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 37 is cleared"
	::= 15485

dpsRTUp14486Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 38 is set"
	::= 14486

dpsRTUp15486Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 38 is cleared"
	::= 15486

dpsRTUp14487Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 39 is set"
	::= 14487

dpsRTUp15487Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 39 is cleared"
	::= 15487

dpsRTUp14488Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 40 is set"
	::= 14488

dpsRTUp15488Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 40 is cleared"
	::= 15488

dpsRTUp14489Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 41 is set"
	::= 14489

dpsRTUp15489Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 41 is cleared"
	::= 15489

dpsRTUp14490Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 42 is set"
	::= 14490

dpsRTUp15490Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 42 is cleared"
	::= 15490

dpsRTUp14491Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 43 is set"
	::= 14491

dpsRTUp15491Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 43 is cleared"
	::= 15491

dpsRTUp14492Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 44 is set"
	::= 14492

dpsRTUp15492Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 44 is cleared"
	::= 15492

dpsRTUp14493Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 45 is set"
	::= 14493

dpsRTUp15493Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 45 is cleared"
	::= 15493

dpsRTUp14494Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 46 is set"
	::= 14494

dpsRTUp15494Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 46 is cleared"
	::= 15494

dpsRTUp14495Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 47 is set"
	::= 14495

dpsRTUp15495Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 47 is cleared"
	::= 15495

dpsRTUp14496Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 48 is set"
	::= 14496

dpsRTUp15496Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 48 is cleared"
	::= 15496

dpsRTUp14497Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 49 is set"
	::= 14497

dpsRTUp15497Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 49 is cleared"
	::= 15497

dpsRTUp14498Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 50 is set"
	::= 14498

dpsRTUp15498Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 50 is cleared"
	::= 15498

dpsRTUp14499Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 51 is set"
	::= 14499

dpsRTUp15499Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 51 is cleared"
	::= 15499

dpsRTUp14500Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 52 is set"
	::= 14500

dpsRTUp15500Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 52 is cleared"
	::= 15500

dpsRTUp14501Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 53 is set"
	::= 14501

dpsRTUp15501Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 53 is cleared"
	::= 15501

dpsRTUp14502Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 54 is set"
	::= 14502

dpsRTUp15502Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 54 is cleared"
	::= 15502

dpsRTUp14503Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 55 is set"
	::= 14503

dpsRTUp15503Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 55 is cleared"
	::= 15503

dpsRTUp14504Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 56 is set"
	::= 14504

dpsRTUp15504Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 56 is cleared"
	::= 15504

dpsRTUp14505Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 57 is set"
	::= 14505

dpsRTUp15505Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 57 is cleared"
	::= 15505

dpsRTUp14506Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 58 is set"
	::= 14506

dpsRTUp15506Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 58 is cleared"
	::= 15506

dpsRTUp14507Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 59 is set"
	::= 14507

dpsRTUp15507Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 59 is cleared"
	::= 15507

dpsRTUp14508Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 60 is set"
	::= 14508

dpsRTUp15508Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 60 is cleared"
	::= 15508

dpsRTUp14509Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 61 is set"
	::= 14509

dpsRTUp15509Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 61 is cleared"
	::= 15509

dpsRTUp14510Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 62 is set"
	::= 14510

dpsRTUp15510Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 62 is cleared"
	::= 15510

dpsRTUp14511Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 63 is set"
	::= 14511

dpsRTUp15511Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 63 is cleared"
	::= 15511

dpsRTUp14512Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 64 is set"
	::= 14512

dpsRTUp15512Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 3 display 8 point 64 is cleared"
	::= 15512

dpsRTUp16001Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 1 is set"
	::= 16001

dpsRTUp17001Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 1 is cleared"
	::= 17001

dpsRTUp16002Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 2 is set"
	::= 16002

dpsRTUp17002Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 2 is cleared"
	::= 17002

dpsRTUp16003Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 3 is set"
	::= 16003

dpsRTUp17003Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 3 is cleared"
	::= 17003

dpsRTUp16004Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 4 is set"
	::= 16004

dpsRTUp17004Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 4 is cleared"
	::= 17004

dpsRTUp16005Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 5 is set"
	::= 16005

dpsRTUp17005Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 5 is cleared"
	::= 17005

dpsRTUp16006Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 6 is set"
	::= 16006

dpsRTUp17006Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 6 is cleared"
	::= 17006

dpsRTUp16007Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 7 is set"
	::= 16007

dpsRTUp17007Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 7 is cleared"
	::= 17007

dpsRTUp16008Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 8 is set"
	::= 16008

dpsRTUp17008Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 8 is cleared"
	::= 17008

dpsRTUp16009Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 9 is set"
	::= 16009

dpsRTUp17009Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 9 is cleared"
	::= 17009

dpsRTUp16010Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 10 is set"
	::= 16010

dpsRTUp17010Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 10 is cleared"
	::= 17010

dpsRTUp16011Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 11 is set"
	::= 16011

dpsRTUp17011Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 11 is cleared"
	::= 17011

dpsRTUp16012Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 12 is set"
	::= 16012

dpsRTUp17012Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 12 is cleared"
	::= 17012

dpsRTUp16013Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 13 is set"
	::= 16013

dpsRTUp17013Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 13 is cleared"
	::= 17013

dpsRTUp16014Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 14 is set"
	::= 16014

dpsRTUp17014Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 14 is cleared"
	::= 17014

dpsRTUp16015Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 15 is set"
	::= 16015

dpsRTUp17015Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 15 is cleared"
	::= 17015

dpsRTUp16016Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 16 is set"
	::= 16016

dpsRTUp17016Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 16 is cleared"
	::= 17016

dpsRTUp16017Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 17 is set"
	::= 16017

dpsRTUp17017Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 17 is cleared"
	::= 17017

dpsRTUp16018Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 18 is set"
	::= 16018

dpsRTUp17018Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 18 is cleared"
	::= 17018

dpsRTUp16019Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 19 is set"
	::= 16019

dpsRTUp17019Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 19 is cleared"
	::= 17019

dpsRTUp16020Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 20 is set"
	::= 16020

dpsRTUp17020Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 20 is cleared"
	::= 17020

dpsRTUp16021Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 21 is set"
	::= 16021

dpsRTUp17021Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 21 is cleared"
	::= 17021

dpsRTUp16022Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 22 is set"
	::= 16022

dpsRTUp17022Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 22 is cleared"
	::= 17022

dpsRTUp16023Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 23 is set"
	::= 16023

dpsRTUp17023Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 23 is cleared"
	::= 17023

dpsRTUp16024Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 24 is set"
	::= 16024

dpsRTUp17024Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 24 is cleared"
	::= 17024

dpsRTUp16025Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 25 is set"
	::= 16025

dpsRTUp17025Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 25 is cleared"
	::= 17025

dpsRTUp16026Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 26 is set"
	::= 16026

dpsRTUp17026Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 26 is cleared"
	::= 17026

dpsRTUp16027Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 27 is set"
	::= 16027

dpsRTUp17027Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 27 is cleared"
	::= 17027

dpsRTUp16028Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 28 is set"
	::= 16028

dpsRTUp17028Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 28 is cleared"
	::= 17028

dpsRTUp16029Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 29 is set"
	::= 16029

dpsRTUp17029Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 29 is cleared"
	::= 17029

dpsRTUp16030Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 30 is set"
	::= 16030

dpsRTUp17030Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 30 is cleared"
	::= 17030

dpsRTUp16031Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 31 is set"
	::= 16031

dpsRTUp17031Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 31 is cleared"
	::= 17031

dpsRTUp16032Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 32 is set"
	::= 16032

dpsRTUp17032Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 32 is cleared"
	::= 17032

dpsRTUp16033Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 33 is set"
	::= 16033

dpsRTUp17033Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 33 is cleared"
	::= 17033

dpsRTUp16034Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 34 is set"
	::= 16034

dpsRTUp17034Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 34 is cleared"
	::= 17034

dpsRTUp16035Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 35 is set"
	::= 16035

dpsRTUp17035Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 35 is cleared"
	::= 17035

dpsRTUp16036Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 36 is set"
	::= 16036

dpsRTUp17036Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 36 is cleared"
	::= 17036

dpsRTUp16037Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 37 is set"
	::= 16037

dpsRTUp17037Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 37 is cleared"
	::= 17037

dpsRTUp16038Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 38 is set"
	::= 16038

dpsRTUp17038Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 38 is cleared"
	::= 17038

dpsRTUp16039Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 39 is set"
	::= 16039

dpsRTUp17039Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 39 is cleared"
	::= 17039

dpsRTUp16040Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 40 is set"
	::= 16040

dpsRTUp17040Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 40 is cleared"
	::= 17040

dpsRTUp16041Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 41 is set"
	::= 16041

dpsRTUp17041Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 41 is cleared"
	::= 17041

dpsRTUp16042Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 42 is set"
	::= 16042

dpsRTUp17042Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 42 is cleared"
	::= 17042

dpsRTUp16043Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 43 is set"
	::= 16043

dpsRTUp17043Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 43 is cleared"
	::= 17043

dpsRTUp16044Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 44 is set"
	::= 16044

dpsRTUp17044Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 44 is cleared"
	::= 17044

dpsRTUp16045Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 45 is set"
	::= 16045

dpsRTUp17045Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 45 is cleared"
	::= 17045

dpsRTUp16046Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 46 is set"
	::= 16046

dpsRTUp17046Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 46 is cleared"
	::= 17046

dpsRTUp16047Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 47 is set"
	::= 16047

dpsRTUp17047Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 47 is cleared"
	::= 17047

dpsRTUp16048Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 48 is set"
	::= 16048

dpsRTUp17048Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 48 is cleared"
	::= 17048

dpsRTUp16049Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 49 is set"
	::= 16049

dpsRTUp17049Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 49 is cleared"
	::= 17049

dpsRTUp16050Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 50 is set"
	::= 16050

dpsRTUp17050Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 50 is cleared"
	::= 17050

dpsRTUp16051Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 51 is set"
	::= 16051

dpsRTUp17051Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 51 is cleared"
	::= 17051

dpsRTUp16052Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 52 is set"
	::= 16052

dpsRTUp17052Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 52 is cleared"
	::= 17052

dpsRTUp16053Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 53 is set"
	::= 16053

dpsRTUp17053Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 53 is cleared"
	::= 17053

dpsRTUp16054Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 54 is set"
	::= 16054

dpsRTUp17054Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 54 is cleared"
	::= 17054

dpsRTUp16055Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 55 is set"
	::= 16055

dpsRTUp17055Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 55 is cleared"
	::= 17055

dpsRTUp16056Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 56 is set"
	::= 16056

dpsRTUp17056Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 56 is cleared"
	::= 17056

dpsRTUp16057Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 57 is set"
	::= 16057

dpsRTUp17057Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 57 is cleared"
	::= 17057

dpsRTUp16058Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 58 is set"
	::= 16058

dpsRTUp17058Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 58 is cleared"
	::= 17058

dpsRTUp16059Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 59 is set"
	::= 16059

dpsRTUp17059Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 59 is cleared"
	::= 17059

dpsRTUp16060Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 60 is set"
	::= 16060

dpsRTUp17060Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 60 is cleared"
	::= 17060

dpsRTUp16061Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 61 is set"
	::= 16061

dpsRTUp17061Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 61 is cleared"
	::= 17061

dpsRTUp16062Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 62 is set"
	::= 16062

dpsRTUp17062Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 62 is cleared"
	::= 17062

dpsRTUp16063Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 63 is set"
	::= 16063

dpsRTUp17063Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 63 is cleared"
	::= 17063

dpsRTUp16064Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 64 is set"
	::= 16064

dpsRTUp17064Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 1 point 64 is cleared"
	::= 17064

dpsRTUp16065Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 1 is set"
	::= 16065

dpsRTUp17065Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 1 is cleared"
	::= 17065

dpsRTUp16066Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 2 is set"
	::= 16066

dpsRTUp17066Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 2 is cleared"
	::= 17066

dpsRTUp16067Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 3 is set"
	::= 16067

dpsRTUp17067Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 3 is cleared"
	::= 17067

dpsRTUp16068Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 4 is set"
	::= 16068

dpsRTUp17068Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 4 is cleared"
	::= 17068

dpsRTUp16069Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 5 is set"
	::= 16069

dpsRTUp17069Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 5 is cleared"
	::= 17069

dpsRTUp16070Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 6 is set"
	::= 16070

dpsRTUp17070Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 6 is cleared"
	::= 17070

dpsRTUp16071Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 7 is set"
	::= 16071

dpsRTUp17071Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 7 is cleared"
	::= 17071

dpsRTUp16072Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 8 is set"
	::= 16072

dpsRTUp17072Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 8 is cleared"
	::= 17072

dpsRTUp16073Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 9 is set"
	::= 16073

dpsRTUp17073Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 9 is cleared"
	::= 17073

dpsRTUp16074Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 10 is set"
	::= 16074

dpsRTUp17074Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 10 is cleared"
	::= 17074

dpsRTUp16075Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 11 is set"
	::= 16075

dpsRTUp17075Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 11 is cleared"
	::= 17075

dpsRTUp16076Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 12 is set"
	::= 16076

dpsRTUp17076Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 12 is cleared"
	::= 17076

dpsRTUp16077Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 13 is set"
	::= 16077

dpsRTUp17077Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 13 is cleared"
	::= 17077

dpsRTUp16078Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 14 is set"
	::= 16078

dpsRTUp17078Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 14 is cleared"
	::= 17078

dpsRTUp16079Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 15 is set"
	::= 16079

dpsRTUp17079Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 15 is cleared"
	::= 17079

dpsRTUp16080Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 16 is set"
	::= 16080

dpsRTUp17080Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 16 is cleared"
	::= 17080

dpsRTUp16081Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 17 is set"
	::= 16081

dpsRTUp17081Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 17 is cleared"
	::= 17081

dpsRTUp16082Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 18 is set"
	::= 16082

dpsRTUp17082Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 18 is cleared"
	::= 17082

dpsRTUp16083Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 19 is set"
	::= 16083

dpsRTUp17083Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 19 is cleared"
	::= 17083

dpsRTUp16084Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 20 is set"
	::= 16084

dpsRTUp17084Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 20 is cleared"
	::= 17084

dpsRTUp16085Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 21 is set"
	::= 16085

dpsRTUp17085Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 21 is cleared"
	::= 17085

dpsRTUp16086Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 22 is set"
	::= 16086

dpsRTUp17086Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 22 is cleared"
	::= 17086

dpsRTUp16087Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 23 is set"
	::= 16087

dpsRTUp17087Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 23 is cleared"
	::= 17087

dpsRTUp16088Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 24 is set"
	::= 16088

dpsRTUp17088Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 24 is cleared"
	::= 17088

dpsRTUp16089Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 25 is set"
	::= 16089

dpsRTUp17089Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 25 is cleared"
	::= 17089

dpsRTUp16090Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 26 is set"
	::= 16090

dpsRTUp17090Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 26 is cleared"
	::= 17090

dpsRTUp16091Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 27 is set"
	::= 16091

dpsRTUp17091Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 27 is cleared"
	::= 17091

dpsRTUp16092Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 28 is set"
	::= 16092

dpsRTUp17092Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 28 is cleared"
	::= 17092

dpsRTUp16093Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 29 is set"
	::= 16093

dpsRTUp17093Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 29 is cleared"
	::= 17093

dpsRTUp16094Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 30 is set"
	::= 16094

dpsRTUp17094Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 30 is cleared"
	::= 17094

dpsRTUp16095Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 31 is set"
	::= 16095

dpsRTUp17095Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 31 is cleared"
	::= 17095

dpsRTUp16096Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 32 is set"
	::= 16096

dpsRTUp17096Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 32 is cleared"
	::= 17096

dpsRTUp16097Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 33 is set"
	::= 16097

dpsRTUp17097Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 33 is cleared"
	::= 17097

dpsRTUp16098Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 34 is set"
	::= 16098

dpsRTUp17098Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 34 is cleared"
	::= 17098

dpsRTUp16099Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 35 is set"
	::= 16099

dpsRTUp17099Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 35 is cleared"
	::= 17099

dpsRTUp16100Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 36 is set"
	::= 16100

dpsRTUp17100Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 36 is cleared"
	::= 17100

dpsRTUp16101Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 37 is set"
	::= 16101

dpsRTUp17101Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 37 is cleared"
	::= 17101

dpsRTUp16102Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 38 is set"
	::= 16102

dpsRTUp17102Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 38 is cleared"
	::= 17102

dpsRTUp16103Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 39 is set"
	::= 16103

dpsRTUp17103Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 39 is cleared"
	::= 17103

dpsRTUp16104Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 40 is set"
	::= 16104

dpsRTUp17104Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 40 is cleared"
	::= 17104

dpsRTUp16105Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 41 is set"
	::= 16105

dpsRTUp17105Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 41 is cleared"
	::= 17105

dpsRTUp16106Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 42 is set"
	::= 16106

dpsRTUp17106Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 42 is cleared"
	::= 17106

dpsRTUp16107Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 43 is set"
	::= 16107

dpsRTUp17107Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 43 is cleared"
	::= 17107

dpsRTUp16108Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 44 is set"
	::= 16108

dpsRTUp17108Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 44 is cleared"
	::= 17108

dpsRTUp16109Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 45 is set"
	::= 16109

dpsRTUp17109Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 45 is cleared"
	::= 17109

dpsRTUp16110Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 46 is set"
	::= 16110

dpsRTUp17110Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 46 is cleared"
	::= 17110

dpsRTUp16111Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 47 is set"
	::= 16111

dpsRTUp17111Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 47 is cleared"
	::= 17111

dpsRTUp16112Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 48 is set"
	::= 16112

dpsRTUp17112Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 48 is cleared"
	::= 17112

dpsRTUp16113Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 49 is set"
	::= 16113

dpsRTUp17113Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 49 is cleared"
	::= 17113

dpsRTUp16114Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 50 is set"
	::= 16114

dpsRTUp17114Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 50 is cleared"
	::= 17114

dpsRTUp16115Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 51 is set"
	::= 16115

dpsRTUp17115Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 51 is cleared"
	::= 17115

dpsRTUp16116Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 52 is set"
	::= 16116

dpsRTUp17116Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 52 is cleared"
	::= 17116

dpsRTUp16117Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 53 is set"
	::= 16117

dpsRTUp17117Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 53 is cleared"
	::= 17117

dpsRTUp16118Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 54 is set"
	::= 16118

dpsRTUp17118Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 54 is cleared"
	::= 17118

dpsRTUp16119Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 55 is set"
	::= 16119

dpsRTUp17119Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 55 is cleared"
	::= 17119

dpsRTUp16120Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 56 is set"
	::= 16120

dpsRTUp17120Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 56 is cleared"
	::= 17120

dpsRTUp16121Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 57 is set"
	::= 16121

dpsRTUp17121Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 57 is cleared"
	::= 17121

dpsRTUp16122Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 58 is set"
	::= 16122

dpsRTUp17122Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 58 is cleared"
	::= 17122

dpsRTUp16123Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 59 is set"
	::= 16123

dpsRTUp17123Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 59 is cleared"
	::= 17123

dpsRTUp16124Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 60 is set"
	::= 16124

dpsRTUp17124Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 60 is cleared"
	::= 17124

dpsRTUp16125Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 61 is set"
	::= 16125

dpsRTUp17125Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 61 is cleared"
	::= 17125

dpsRTUp16126Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 62 is set"
	::= 16126

dpsRTUp17126Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 62 is cleared"
	::= 17126

dpsRTUp16127Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 63 is set"
	::= 16127

dpsRTUp17127Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 63 is cleared"
	::= 17127

dpsRTUp16128Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 64 is set"
	::= 16128

dpsRTUp17128Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 2 point 64 is cleared"
	::= 17128

dpsRTUp16129Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 1 is set"
	::= 16129

dpsRTUp17129Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 1 is cleared"
	::= 17129

dpsRTUp16130Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 2 is set"
	::= 16130

dpsRTUp17130Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 2 is cleared"
	::= 17130

dpsRTUp16131Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 3 is set"
	::= 16131

dpsRTUp17131Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 3 is cleared"
	::= 17131

dpsRTUp16132Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 4 is set"
	::= 16132

dpsRTUp17132Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 4 is cleared"
	::= 17132

dpsRTUp16133Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 5 is set"
	::= 16133

dpsRTUp17133Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 5 is cleared"
	::= 17133

dpsRTUp16134Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 6 is set"
	::= 16134

dpsRTUp17134Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 6 is cleared"
	::= 17134

dpsRTUp16135Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 7 is set"
	::= 16135

dpsRTUp17135Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 7 is cleared"
	::= 17135

dpsRTUp16136Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 8 is set"
	::= 16136

dpsRTUp17136Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 8 is cleared"
	::= 17136

dpsRTUp16137Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 9 is set"
	::= 16137

dpsRTUp17137Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 9 is cleared"
	::= 17137

dpsRTUp16138Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 10 is set"
	::= 16138

dpsRTUp17138Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 10 is cleared"
	::= 17138

dpsRTUp16139Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 11 is set"
	::= 16139

dpsRTUp17139Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 11 is cleared"
	::= 17139

dpsRTUp16140Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 12 is set"
	::= 16140

dpsRTUp17140Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 12 is cleared"
	::= 17140

dpsRTUp16141Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 13 is set"
	::= 16141

dpsRTUp17141Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 13 is cleared"
	::= 17141

dpsRTUp16142Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 14 is set"
	::= 16142

dpsRTUp17142Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 14 is cleared"
	::= 17142

dpsRTUp16143Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 15 is set"
	::= 16143

dpsRTUp17143Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 15 is cleared"
	::= 17143

dpsRTUp16144Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 16 is set"
	::= 16144

dpsRTUp17144Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 16 is cleared"
	::= 17144

dpsRTUp16145Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 17 is set"
	::= 16145

dpsRTUp17145Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 17 is cleared"
	::= 17145

dpsRTUp16146Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 18 is set"
	::= 16146

dpsRTUp17146Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 18 is cleared"
	::= 17146

dpsRTUp16147Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 19 is set"
	::= 16147

dpsRTUp17147Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 19 is cleared"
	::= 17147

dpsRTUp16148Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 20 is set"
	::= 16148

dpsRTUp17148Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 20 is cleared"
	::= 17148

dpsRTUp16149Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 21 is set"
	::= 16149

dpsRTUp17149Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 21 is cleared"
	::= 17149

dpsRTUp16150Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 22 is set"
	::= 16150

dpsRTUp17150Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 22 is cleared"
	::= 17150

dpsRTUp16151Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 23 is set"
	::= 16151

dpsRTUp17151Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 23 is cleared"
	::= 17151

dpsRTUp16152Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 24 is set"
	::= 16152

dpsRTUp17152Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 24 is cleared"
	::= 17152

dpsRTUp16153Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 25 is set"
	::= 16153

dpsRTUp17153Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 25 is cleared"
	::= 17153

dpsRTUp16154Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 26 is set"
	::= 16154

dpsRTUp17154Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 26 is cleared"
	::= 17154

dpsRTUp16155Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 27 is set"
	::= 16155

dpsRTUp17155Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 27 is cleared"
	::= 17155

dpsRTUp16156Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 28 is set"
	::= 16156

dpsRTUp17156Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 28 is cleared"
	::= 17156

dpsRTUp16157Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 29 is set"
	::= 16157

dpsRTUp17157Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 29 is cleared"
	::= 17157

dpsRTUp16158Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 30 is set"
	::= 16158

dpsRTUp17158Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 30 is cleared"
	::= 17158

dpsRTUp16159Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 31 is set"
	::= 16159

dpsRTUp17159Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 31 is cleared"
	::= 17159

dpsRTUp16160Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 32 is set"
	::= 16160

dpsRTUp17160Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 32 is cleared"
	::= 17160

dpsRTUp16161Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 33 is set"
	::= 16161

dpsRTUp17161Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 33 is cleared"
	::= 17161

dpsRTUp16162Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 34 is set"
	::= 16162

dpsRTUp17162Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 34 is cleared"
	::= 17162

dpsRTUp16163Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 35 is set"
	::= 16163

dpsRTUp17163Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 35 is cleared"
	::= 17163

dpsRTUp16164Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 36 is set"
	::= 16164

dpsRTUp17164Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 36 is cleared"
	::= 17164

dpsRTUp16165Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 37 is set"
	::= 16165

dpsRTUp17165Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 37 is cleared"
	::= 17165

dpsRTUp16166Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 38 is set"
	::= 16166

dpsRTUp17166Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 38 is cleared"
	::= 17166

dpsRTUp16167Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 39 is set"
	::= 16167

dpsRTUp17167Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 39 is cleared"
	::= 17167

dpsRTUp16168Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 40 is set"
	::= 16168

dpsRTUp17168Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 40 is cleared"
	::= 17168

dpsRTUp16169Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 41 is set"
	::= 16169

dpsRTUp17169Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 41 is cleared"
	::= 17169

dpsRTUp16170Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 42 is set"
	::= 16170

dpsRTUp17170Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 42 is cleared"
	::= 17170

dpsRTUp16171Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 43 is set"
	::= 16171

dpsRTUp17171Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 43 is cleared"
	::= 17171

dpsRTUp16172Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 44 is set"
	::= 16172

dpsRTUp17172Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 44 is cleared"
	::= 17172

dpsRTUp16173Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 45 is set"
	::= 16173

dpsRTUp17173Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 45 is cleared"
	::= 17173

dpsRTUp16174Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 46 is set"
	::= 16174

dpsRTUp17174Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 46 is cleared"
	::= 17174

dpsRTUp16175Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 47 is set"
	::= 16175

dpsRTUp17175Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 47 is cleared"
	::= 17175

dpsRTUp16176Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 48 is set"
	::= 16176

dpsRTUp17176Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 48 is cleared"
	::= 17176

dpsRTUp16177Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 49 is set"
	::= 16177

dpsRTUp17177Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 49 is cleared"
	::= 17177

dpsRTUp16178Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 50 is set"
	::= 16178

dpsRTUp17178Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 50 is cleared"
	::= 17178

dpsRTUp16179Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 51 is set"
	::= 16179

dpsRTUp17179Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 51 is cleared"
	::= 17179

dpsRTUp16180Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 52 is set"
	::= 16180

dpsRTUp17180Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 52 is cleared"
	::= 17180

dpsRTUp16181Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 53 is set"
	::= 16181

dpsRTUp17181Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 53 is cleared"
	::= 17181

dpsRTUp16182Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 54 is set"
	::= 16182

dpsRTUp17182Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 54 is cleared"
	::= 17182

dpsRTUp16183Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 55 is set"
	::= 16183

dpsRTUp17183Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 55 is cleared"
	::= 17183

dpsRTUp16184Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 56 is set"
	::= 16184

dpsRTUp17184Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 56 is cleared"
	::= 17184

dpsRTUp16185Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 57 is set"
	::= 16185

dpsRTUp17185Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 57 is cleared"
	::= 17185

dpsRTUp16186Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 58 is set"
	::= 16186

dpsRTUp17186Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 58 is cleared"
	::= 17186

dpsRTUp16187Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 59 is set"
	::= 16187

dpsRTUp17187Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 59 is cleared"
	::= 17187

dpsRTUp16188Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 60 is set"
	::= 16188

dpsRTUp17188Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 60 is cleared"
	::= 17188

dpsRTUp16189Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 61 is set"
	::= 16189

dpsRTUp17189Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 61 is cleared"
	::= 17189

dpsRTUp16190Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 62 is set"
	::= 16190

dpsRTUp17190Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 62 is cleared"
	::= 17190

dpsRTUp16191Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 63 is set"
	::= 16191

dpsRTUp17191Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 63 is cleared"
	::= 17191

dpsRTUp16192Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 64 is set"
	::= 16192

dpsRTUp17192Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 3 point 64 is cleared"
	::= 17192

dpsRTUp16193Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 1 is set"
	::= 16193

dpsRTUp17193Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 1 is cleared"
	::= 17193

dpsRTUp16194Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 2 is set"
	::= 16194

dpsRTUp17194Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 2 is cleared"
	::= 17194

dpsRTUp16195Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 3 is set"
	::= 16195

dpsRTUp17195Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 3 is cleared"
	::= 17195

dpsRTUp16196Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 4 is set"
	::= 16196

dpsRTUp17196Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 4 is cleared"
	::= 17196

dpsRTUp16197Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 5 is set"
	::= 16197

dpsRTUp17197Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 5 is cleared"
	::= 17197

dpsRTUp16198Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 6 is set"
	::= 16198

dpsRTUp17198Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 6 is cleared"
	::= 17198

dpsRTUp16199Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 7 is set"
	::= 16199

dpsRTUp17199Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 7 is cleared"
	::= 17199

dpsRTUp16200Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 8 is set"
	::= 16200

dpsRTUp17200Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 8 is cleared"
	::= 17200

dpsRTUp16201Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 9 is set"
	::= 16201

dpsRTUp17201Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 9 is cleared"
	::= 17201

dpsRTUp16202Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 10 is set"
	::= 16202

dpsRTUp17202Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 10 is cleared"
	::= 17202

dpsRTUp16203Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 11 is set"
	::= 16203

dpsRTUp17203Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 11 is cleared"
	::= 17203

dpsRTUp16204Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 12 is set"
	::= 16204

dpsRTUp17204Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 12 is cleared"
	::= 17204

dpsRTUp16205Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 13 is set"
	::= 16205

dpsRTUp17205Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 13 is cleared"
	::= 17205

dpsRTUp16206Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 14 is set"
	::= 16206

dpsRTUp17206Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 14 is cleared"
	::= 17206

dpsRTUp16207Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 15 is set"
	::= 16207

dpsRTUp17207Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 15 is cleared"
	::= 17207

dpsRTUp16208Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 16 is set"
	::= 16208

dpsRTUp17208Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 16 is cleared"
	::= 17208

dpsRTUp16209Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 17 is set"
	::= 16209

dpsRTUp17209Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 17 is cleared"
	::= 17209

dpsRTUp16210Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 18 is set"
	::= 16210

dpsRTUp17210Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 18 is cleared"
	::= 17210

dpsRTUp16211Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 19 is set"
	::= 16211

dpsRTUp17211Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 19 is cleared"
	::= 17211

dpsRTUp16212Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 20 is set"
	::= 16212

dpsRTUp17212Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 20 is cleared"
	::= 17212

dpsRTUp16213Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 21 is set"
	::= 16213

dpsRTUp17213Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 21 is cleared"
	::= 17213

dpsRTUp16214Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 22 is set"
	::= 16214

dpsRTUp17214Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 22 is cleared"
	::= 17214

dpsRTUp16215Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 23 is set"
	::= 16215

dpsRTUp17215Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 23 is cleared"
	::= 17215

dpsRTUp16216Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 24 is set"
	::= 16216

dpsRTUp17216Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 24 is cleared"
	::= 17216

dpsRTUp16217Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 25 is set"
	::= 16217

dpsRTUp17217Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 25 is cleared"
	::= 17217

dpsRTUp16218Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 26 is set"
	::= 16218

dpsRTUp17218Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 26 is cleared"
	::= 17218

dpsRTUp16219Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 27 is set"
	::= 16219

dpsRTUp17219Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 27 is cleared"
	::= 17219

dpsRTUp16220Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 28 is set"
	::= 16220

dpsRTUp17220Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 28 is cleared"
	::= 17220

dpsRTUp16221Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 29 is set"
	::= 16221

dpsRTUp17221Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 29 is cleared"
	::= 17221

dpsRTUp16222Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 30 is set"
	::= 16222

dpsRTUp17222Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 30 is cleared"
	::= 17222

dpsRTUp16223Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 31 is set"
	::= 16223

dpsRTUp17223Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 31 is cleared"
	::= 17223

dpsRTUp16224Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 32 is set"
	::= 16224

dpsRTUp17224Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 32 is cleared"
	::= 17224

dpsRTUp16225Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 33 is set"
	::= 16225

dpsRTUp17225Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 33 is cleared"
	::= 17225

dpsRTUp16226Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 34 is set"
	::= 16226

dpsRTUp17226Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 34 is cleared"
	::= 17226

dpsRTUp16227Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 35 is set"
	::= 16227

dpsRTUp17227Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 35 is cleared"
	::= 17227

dpsRTUp16228Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 36 is set"
	::= 16228

dpsRTUp17228Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 36 is cleared"
	::= 17228

dpsRTUp16229Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 37 is set"
	::= 16229

dpsRTUp17229Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 37 is cleared"
	::= 17229

dpsRTUp16230Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 38 is set"
	::= 16230

dpsRTUp17230Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 38 is cleared"
	::= 17230

dpsRTUp16231Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 39 is set"
	::= 16231

dpsRTUp17231Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 39 is cleared"
	::= 17231

dpsRTUp16232Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 40 is set"
	::= 16232

dpsRTUp17232Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 40 is cleared"
	::= 17232

dpsRTUp16233Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 41 is set"
	::= 16233

dpsRTUp17233Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 41 is cleared"
	::= 17233

dpsRTUp16234Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 42 is set"
	::= 16234

dpsRTUp17234Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 42 is cleared"
	::= 17234

dpsRTUp16235Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 43 is set"
	::= 16235

dpsRTUp17235Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 43 is cleared"
	::= 17235

dpsRTUp16236Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 44 is set"
	::= 16236

dpsRTUp17236Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 44 is cleared"
	::= 17236

dpsRTUp16237Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 45 is set"
	::= 16237

dpsRTUp17237Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 45 is cleared"
	::= 17237

dpsRTUp16238Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 46 is set"
	::= 16238

dpsRTUp17238Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 46 is cleared"
	::= 17238

dpsRTUp16239Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 47 is set"
	::= 16239

dpsRTUp17239Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 47 is cleared"
	::= 17239

dpsRTUp16240Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 48 is set"
	::= 16240

dpsRTUp17240Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 48 is cleared"
	::= 17240

dpsRTUp16241Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 49 is set"
	::= 16241

dpsRTUp17241Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 49 is cleared"
	::= 17241

dpsRTUp16242Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 50 is set"
	::= 16242

dpsRTUp17242Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 50 is cleared"
	::= 17242

dpsRTUp16243Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 51 is set"
	::= 16243

dpsRTUp17243Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 51 is cleared"
	::= 17243

dpsRTUp16244Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 52 is set"
	::= 16244

dpsRTUp17244Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 52 is cleared"
	::= 17244

dpsRTUp16245Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 53 is set"
	::= 16245

dpsRTUp17245Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 53 is cleared"
	::= 17245

dpsRTUp16246Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 54 is set"
	::= 16246

dpsRTUp17246Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 54 is cleared"
	::= 17246

dpsRTUp16247Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 55 is set"
	::= 16247

dpsRTUp17247Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 55 is cleared"
	::= 17247

dpsRTUp16248Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 56 is set"
	::= 16248

dpsRTUp17248Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 56 is cleared"
	::= 17248

dpsRTUp16249Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 57 is set"
	::= 16249

dpsRTUp17249Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 57 is cleared"
	::= 17249

dpsRTUp16250Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 58 is set"
	::= 16250

dpsRTUp17250Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 58 is cleared"
	::= 17250

dpsRTUp16251Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 59 is set"
	::= 16251

dpsRTUp17251Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 59 is cleared"
	::= 17251

dpsRTUp16252Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 60 is set"
	::= 16252

dpsRTUp17252Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 60 is cleared"
	::= 17252

dpsRTUp16253Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 61 is set"
	::= 16253

dpsRTUp17253Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 61 is cleared"
	::= 17253

dpsRTUp16254Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 62 is set"
	::= 16254

dpsRTUp17254Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 62 is cleared"
	::= 17254

dpsRTUp16255Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 63 is set"
	::= 16255

dpsRTUp17255Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 63 is cleared"
	::= 17255

dpsRTUp16256Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 64 is set"
	::= 16256

dpsRTUp17256Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 4 point 64 is cleared"
	::= 17256

dpsRTUp16257Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 1 is set"
	::= 16257

dpsRTUp17257Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 1 is cleared"
	::= 17257

dpsRTUp16258Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 2 is set"
	::= 16258

dpsRTUp17258Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 2 is cleared"
	::= 17258

dpsRTUp16259Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 3 is set"
	::= 16259

dpsRTUp17259Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 3 is cleared"
	::= 17259

dpsRTUp16260Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 4 is set"
	::= 16260

dpsRTUp17260Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 4 is cleared"
	::= 17260

dpsRTUp16261Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 5 is set"
	::= 16261

dpsRTUp17261Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 5 is cleared"
	::= 17261

dpsRTUp16262Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 6 is set"
	::= 16262

dpsRTUp17262Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 6 is cleared"
	::= 17262

dpsRTUp16263Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 7 is set"
	::= 16263

dpsRTUp17263Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 7 is cleared"
	::= 17263

dpsRTUp16264Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 8 is set"
	::= 16264

dpsRTUp17264Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 8 is cleared"
	::= 17264

dpsRTUp16265Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 9 is set"
	::= 16265

dpsRTUp17265Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 9 is cleared"
	::= 17265

dpsRTUp16266Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 10 is set"
	::= 16266

dpsRTUp17266Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 10 is cleared"
	::= 17266

dpsRTUp16267Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 11 is set"
	::= 16267

dpsRTUp17267Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 11 is cleared"
	::= 17267

dpsRTUp16268Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 12 is set"
	::= 16268

dpsRTUp17268Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 12 is cleared"
	::= 17268

dpsRTUp16269Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 13 is set"
	::= 16269

dpsRTUp17269Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 13 is cleared"
	::= 17269

dpsRTUp16270Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 14 is set"
	::= 16270

dpsRTUp17270Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 14 is cleared"
	::= 17270

dpsRTUp16271Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 15 is set"
	::= 16271

dpsRTUp17271Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 15 is cleared"
	::= 17271

dpsRTUp16272Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 16 is set"
	::= 16272

dpsRTUp17272Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 16 is cleared"
	::= 17272

dpsRTUp16273Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 17 is set"
	::= 16273

dpsRTUp17273Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 17 is cleared"
	::= 17273

dpsRTUp16274Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 18 is set"
	::= 16274

dpsRTUp17274Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 18 is cleared"
	::= 17274

dpsRTUp16275Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 19 is set"
	::= 16275

dpsRTUp17275Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 19 is cleared"
	::= 17275

dpsRTUp16276Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 20 is set"
	::= 16276

dpsRTUp17276Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 20 is cleared"
	::= 17276

dpsRTUp16277Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 21 is set"
	::= 16277

dpsRTUp17277Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 21 is cleared"
	::= 17277

dpsRTUp16278Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 22 is set"
	::= 16278

dpsRTUp17278Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 22 is cleared"
	::= 17278

dpsRTUp16279Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 23 is set"
	::= 16279

dpsRTUp17279Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 23 is cleared"
	::= 17279

dpsRTUp16280Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 24 is set"
	::= 16280

dpsRTUp17280Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 24 is cleared"
	::= 17280

dpsRTUp16281Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 25 is set"
	::= 16281

dpsRTUp17281Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 25 is cleared"
	::= 17281

dpsRTUp16282Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 26 is set"
	::= 16282

dpsRTUp17282Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 26 is cleared"
	::= 17282

dpsRTUp16283Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 27 is set"
	::= 16283

dpsRTUp17283Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 27 is cleared"
	::= 17283

dpsRTUp16284Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 28 is set"
	::= 16284

dpsRTUp17284Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 28 is cleared"
	::= 17284

dpsRTUp16285Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 29 is set"
	::= 16285

dpsRTUp17285Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 29 is cleared"
	::= 17285

dpsRTUp16286Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 30 is set"
	::= 16286

dpsRTUp17286Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 30 is cleared"
	::= 17286

dpsRTUp16287Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 31 is set"
	::= 16287

dpsRTUp17287Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 31 is cleared"
	::= 17287

dpsRTUp16288Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 32 is set"
	::= 16288

dpsRTUp17288Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 32 is cleared"
	::= 17288

dpsRTUp16289Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 33 is set"
	::= 16289

dpsRTUp17289Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 33 is cleared"
	::= 17289

dpsRTUp16290Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 34 is set"
	::= 16290

dpsRTUp17290Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 34 is cleared"
	::= 17290

dpsRTUp16291Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 35 is set"
	::= 16291

dpsRTUp17291Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 35 is cleared"
	::= 17291

dpsRTUp16292Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 36 is set"
	::= 16292

dpsRTUp17292Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 36 is cleared"
	::= 17292

dpsRTUp16293Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 37 is set"
	::= 16293

dpsRTUp17293Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 37 is cleared"
	::= 17293

dpsRTUp16294Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 38 is set"
	::= 16294

dpsRTUp17294Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 38 is cleared"
	::= 17294

dpsRTUp16295Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 39 is set"
	::= 16295

dpsRTUp17295Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 39 is cleared"
	::= 17295

dpsRTUp16296Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 40 is set"
	::= 16296

dpsRTUp17296Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 40 is cleared"
	::= 17296

dpsRTUp16297Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 41 is set"
	::= 16297

dpsRTUp17297Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 41 is cleared"
	::= 17297

dpsRTUp16298Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 42 is set"
	::= 16298

dpsRTUp17298Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 42 is cleared"
	::= 17298

dpsRTUp16299Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 43 is set"
	::= 16299

dpsRTUp17299Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 43 is cleared"
	::= 17299

dpsRTUp16300Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 44 is set"
	::= 16300

dpsRTUp17300Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 44 is cleared"
	::= 17300

dpsRTUp16301Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 45 is set"
	::= 16301

dpsRTUp17301Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 45 is cleared"
	::= 17301

dpsRTUp16302Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 46 is set"
	::= 16302

dpsRTUp17302Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 46 is cleared"
	::= 17302

dpsRTUp16303Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 47 is set"
	::= 16303

dpsRTUp17303Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 47 is cleared"
	::= 17303

dpsRTUp16304Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 48 is set"
	::= 16304

dpsRTUp17304Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 48 is cleared"
	::= 17304

dpsRTUp16305Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 49 is set"
	::= 16305

dpsRTUp17305Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 49 is cleared"
	::= 17305

dpsRTUp16306Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 50 is set"
	::= 16306

dpsRTUp17306Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 50 is cleared"
	::= 17306

dpsRTUp16307Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 51 is set"
	::= 16307

dpsRTUp17307Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 51 is cleared"
	::= 17307

dpsRTUp16308Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 52 is set"
	::= 16308

dpsRTUp17308Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 52 is cleared"
	::= 17308

dpsRTUp16309Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 53 is set"
	::= 16309

dpsRTUp17309Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 53 is cleared"
	::= 17309

dpsRTUp16310Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 54 is set"
	::= 16310

dpsRTUp17310Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 54 is cleared"
	::= 17310

dpsRTUp16311Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 55 is set"
	::= 16311

dpsRTUp17311Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 55 is cleared"
	::= 17311

dpsRTUp16312Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 56 is set"
	::= 16312

dpsRTUp17312Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 56 is cleared"
	::= 17312

dpsRTUp16313Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 57 is set"
	::= 16313

dpsRTUp17313Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 57 is cleared"
	::= 17313

dpsRTUp16314Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 58 is set"
	::= 16314

dpsRTUp17314Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 58 is cleared"
	::= 17314

dpsRTUp16315Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 59 is set"
	::= 16315

dpsRTUp17315Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 59 is cleared"
	::= 17315

dpsRTUp16316Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 60 is set"
	::= 16316

dpsRTUp17316Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 60 is cleared"
	::= 17316

dpsRTUp16317Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 61 is set"
	::= 16317

dpsRTUp17317Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 61 is cleared"
	::= 17317

dpsRTUp16318Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 62 is set"
	::= 16318

dpsRTUp17318Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 62 is cleared"
	::= 17318

dpsRTUp16319Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 63 is set"
	::= 16319

dpsRTUp17319Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 63 is cleared"
	::= 17319

dpsRTUp16320Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 64 is set"
	::= 16320

dpsRTUp17320Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 5 point 64 is cleared"
	::= 17320

dpsRTUp16321Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 1 is set"
	::= 16321

dpsRTUp17321Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 1 is cleared"
	::= 17321

dpsRTUp16322Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 2 is set"
	::= 16322

dpsRTUp17322Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 2 is cleared"
	::= 17322

dpsRTUp16323Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 3 is set"
	::= 16323

dpsRTUp17323Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 3 is cleared"
	::= 17323

dpsRTUp16324Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 4 is set"
	::= 16324

dpsRTUp17324Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 4 is cleared"
	::= 17324

dpsRTUp16325Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 5 is set"
	::= 16325

dpsRTUp17325Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 5 is cleared"
	::= 17325

dpsRTUp16326Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 6 is set"
	::= 16326

dpsRTUp17326Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 6 is cleared"
	::= 17326

dpsRTUp16327Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 7 is set"
	::= 16327

dpsRTUp17327Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 7 is cleared"
	::= 17327

dpsRTUp16328Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 8 is set"
	::= 16328

dpsRTUp17328Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 8 is cleared"
	::= 17328

dpsRTUp16329Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 9 is set"
	::= 16329

dpsRTUp17329Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 9 is cleared"
	::= 17329

dpsRTUp16330Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 10 is set"
	::= 16330

dpsRTUp17330Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 10 is cleared"
	::= 17330

dpsRTUp16331Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 11 is set"
	::= 16331

dpsRTUp17331Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 11 is cleared"
	::= 17331

dpsRTUp16332Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 12 is set"
	::= 16332

dpsRTUp17332Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 12 is cleared"
	::= 17332

dpsRTUp16333Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 13 is set"
	::= 16333

dpsRTUp17333Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 13 is cleared"
	::= 17333

dpsRTUp16334Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 14 is set"
	::= 16334

dpsRTUp17334Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 14 is cleared"
	::= 17334

dpsRTUp16335Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 15 is set"
	::= 16335

dpsRTUp17335Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 15 is cleared"
	::= 17335

dpsRTUp16336Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 16 is set"
	::= 16336

dpsRTUp17336Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 16 is cleared"
	::= 17336

dpsRTUp16337Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 17 is set"
	::= 16337

dpsRTUp17337Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 17 is cleared"
	::= 17337

dpsRTUp16338Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 18 is set"
	::= 16338

dpsRTUp17338Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 18 is cleared"
	::= 17338

dpsRTUp16339Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 19 is set"
	::= 16339

dpsRTUp17339Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 19 is cleared"
	::= 17339

dpsRTUp16340Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 20 is set"
	::= 16340

dpsRTUp17340Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 20 is cleared"
	::= 17340

dpsRTUp16341Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 21 is set"
	::= 16341

dpsRTUp17341Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 21 is cleared"
	::= 17341

dpsRTUp16342Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 22 is set"
	::= 16342

dpsRTUp17342Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 22 is cleared"
	::= 17342

dpsRTUp16343Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 23 is set"
	::= 16343

dpsRTUp17343Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 23 is cleared"
	::= 17343

dpsRTUp16344Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 24 is set"
	::= 16344

dpsRTUp17344Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 24 is cleared"
	::= 17344

dpsRTUp16345Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 25 is set"
	::= 16345

dpsRTUp17345Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 25 is cleared"
	::= 17345

dpsRTUp16346Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 26 is set"
	::= 16346

dpsRTUp17346Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 26 is cleared"
	::= 17346

dpsRTUp16347Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 27 is set"
	::= 16347

dpsRTUp17347Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 27 is cleared"
	::= 17347

dpsRTUp16348Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 28 is set"
	::= 16348

dpsRTUp17348Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 28 is cleared"
	::= 17348

dpsRTUp16349Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 29 is set"
	::= 16349

dpsRTUp17349Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 29 is cleared"
	::= 17349

dpsRTUp16350Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 30 is set"
	::= 16350

dpsRTUp17350Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 30 is cleared"
	::= 17350

dpsRTUp16351Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 31 is set"
	::= 16351

dpsRTUp17351Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 31 is cleared"
	::= 17351

dpsRTUp16352Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 32 is set"
	::= 16352

dpsRTUp17352Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 32 is cleared"
	::= 17352

dpsRTUp16353Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 33 is set"
	::= 16353

dpsRTUp17353Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 33 is cleared"
	::= 17353

dpsRTUp16354Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 34 is set"
	::= 16354

dpsRTUp17354Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 34 is cleared"
	::= 17354

dpsRTUp16355Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 35 is set"
	::= 16355

dpsRTUp17355Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 35 is cleared"
	::= 17355

dpsRTUp16356Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 36 is set"
	::= 16356

dpsRTUp17356Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 36 is cleared"
	::= 17356

dpsRTUp16357Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 37 is set"
	::= 16357

dpsRTUp17357Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 37 is cleared"
	::= 17357

dpsRTUp16358Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 38 is set"
	::= 16358

dpsRTUp17358Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 38 is cleared"
	::= 17358

dpsRTUp16359Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 39 is set"
	::= 16359

dpsRTUp17359Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 39 is cleared"
	::= 17359

dpsRTUp16360Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 40 is set"
	::= 16360

dpsRTUp17360Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 40 is cleared"
	::= 17360

dpsRTUp16361Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 41 is set"
	::= 16361

dpsRTUp17361Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 41 is cleared"
	::= 17361

dpsRTUp16362Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 42 is set"
	::= 16362

dpsRTUp17362Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 42 is cleared"
	::= 17362

dpsRTUp16363Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 43 is set"
	::= 16363

dpsRTUp17363Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 43 is cleared"
	::= 17363

dpsRTUp16364Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 44 is set"
	::= 16364

dpsRTUp17364Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 44 is cleared"
	::= 17364

dpsRTUp16365Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 45 is set"
	::= 16365

dpsRTUp17365Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 45 is cleared"
	::= 17365

dpsRTUp16366Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 46 is set"
	::= 16366

dpsRTUp17366Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 46 is cleared"
	::= 17366

dpsRTUp16367Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 47 is set"
	::= 16367

dpsRTUp17367Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 47 is cleared"
	::= 17367

dpsRTUp16368Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 48 is set"
	::= 16368

dpsRTUp17368Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 48 is cleared"
	::= 17368

dpsRTUp16369Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 49 is set"
	::= 16369

dpsRTUp17369Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 49 is cleared"
	::= 17369

dpsRTUp16370Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 50 is set"
	::= 16370

dpsRTUp17370Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 50 is cleared"
	::= 17370

dpsRTUp16371Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 51 is set"
	::= 16371

dpsRTUp17371Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 51 is cleared"
	::= 17371

dpsRTUp16372Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 52 is set"
	::= 16372

dpsRTUp17372Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 52 is cleared"
	::= 17372

dpsRTUp16373Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 53 is set"
	::= 16373

dpsRTUp17373Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 53 is cleared"
	::= 17373

dpsRTUp16374Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 54 is set"
	::= 16374

dpsRTUp17374Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 54 is cleared"
	::= 17374

dpsRTUp16375Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 55 is set"
	::= 16375

dpsRTUp17375Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 55 is cleared"
	::= 17375

dpsRTUp16376Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 56 is set"
	::= 16376

dpsRTUp17376Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 56 is cleared"
	::= 17376

dpsRTUp16377Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 57 is set"
	::= 16377

dpsRTUp17377Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 57 is cleared"
	::= 17377

dpsRTUp16378Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 58 is set"
	::= 16378

dpsRTUp17378Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 58 is cleared"
	::= 17378

dpsRTUp16379Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 59 is set"
	::= 16379

dpsRTUp17379Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 59 is cleared"
	::= 17379

dpsRTUp16380Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 60 is set"
	::= 16380

dpsRTUp17380Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 60 is cleared"
	::= 17380

dpsRTUp16381Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 61 is set"
	::= 16381

dpsRTUp17381Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 61 is cleared"
	::= 17381

dpsRTUp16382Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 62 is set"
	::= 16382

dpsRTUp17382Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 62 is cleared"
	::= 17382

dpsRTUp16383Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 63 is set"
	::= 16383

dpsRTUp17383Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 63 is cleared"
	::= 17383

dpsRTUp16384Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 64 is set"
	::= 16384

dpsRTUp17384Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 6 point 64 is cleared"
	::= 17384

dpsRTUp16385Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 1 is set"
	::= 16385

dpsRTUp17385Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 1 is cleared"
	::= 17385

dpsRTUp16386Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 2 is set"
	::= 16386

dpsRTUp17386Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 2 is cleared"
	::= 17386

dpsRTUp16387Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 3 is set"
	::= 16387

dpsRTUp17387Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 3 is cleared"
	::= 17387

dpsRTUp16388Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 4 is set"
	::= 16388

dpsRTUp17388Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 4 is cleared"
	::= 17388

dpsRTUp16389Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 5 is set"
	::= 16389

dpsRTUp17389Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 5 is cleared"
	::= 17389

dpsRTUp16390Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 6 is set"
	::= 16390

dpsRTUp17390Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 6 is cleared"
	::= 17390

dpsRTUp16391Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 7 is set"
	::= 16391

dpsRTUp17391Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 7 is cleared"
	::= 17391

dpsRTUp16392Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 8 is set"
	::= 16392

dpsRTUp17392Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 8 is cleared"
	::= 17392

dpsRTUp16393Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 9 is set"
	::= 16393

dpsRTUp17393Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 9 is cleared"
	::= 17393

dpsRTUp16394Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 10 is set"
	::= 16394

dpsRTUp17394Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 10 is cleared"
	::= 17394

dpsRTUp16395Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 11 is set"
	::= 16395

dpsRTUp17395Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 11 is cleared"
	::= 17395

dpsRTUp16396Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 12 is set"
	::= 16396

dpsRTUp17396Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 12 is cleared"
	::= 17396

dpsRTUp16397Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 13 is set"
	::= 16397

dpsRTUp17397Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 13 is cleared"
	::= 17397

dpsRTUp16398Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 14 is set"
	::= 16398

dpsRTUp17398Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 14 is cleared"
	::= 17398

dpsRTUp16399Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 15 is set"
	::= 16399

dpsRTUp17399Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 15 is cleared"
	::= 17399

dpsRTUp16400Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 16 is set"
	::= 16400

dpsRTUp17400Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 16 is cleared"
	::= 17400

dpsRTUp16401Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 17 is set"
	::= 16401

dpsRTUp17401Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 17 is cleared"
	::= 17401

dpsRTUp16402Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 18 is set"
	::= 16402

dpsRTUp17402Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 18 is cleared"
	::= 17402

dpsRTUp16403Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 19 is set"
	::= 16403

dpsRTUp17403Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 19 is cleared"
	::= 17403

dpsRTUp16404Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 20 is set"
	::= 16404

dpsRTUp17404Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 20 is cleared"
	::= 17404

dpsRTUp16405Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 21 is set"
	::= 16405

dpsRTUp17405Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 21 is cleared"
	::= 17405

dpsRTUp16406Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 22 is set"
	::= 16406

dpsRTUp17406Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 22 is cleared"
	::= 17406

dpsRTUp16407Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 23 is set"
	::= 16407

dpsRTUp17407Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 23 is cleared"
	::= 17407

dpsRTUp16408Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 24 is set"
	::= 16408

dpsRTUp17408Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 24 is cleared"
	::= 17408

dpsRTUp16409Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 25 is set"
	::= 16409

dpsRTUp17409Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 25 is cleared"
	::= 17409

dpsRTUp16410Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 26 is set"
	::= 16410

dpsRTUp17410Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 26 is cleared"
	::= 17410

dpsRTUp16411Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 27 is set"
	::= 16411

dpsRTUp17411Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 27 is cleared"
	::= 17411

dpsRTUp16412Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 28 is set"
	::= 16412

dpsRTUp17412Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 28 is cleared"
	::= 17412

dpsRTUp16413Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 29 is set"
	::= 16413

dpsRTUp17413Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 29 is cleared"
	::= 17413

dpsRTUp16414Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 30 is set"
	::= 16414

dpsRTUp17414Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 30 is cleared"
	::= 17414

dpsRTUp16415Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 31 is set"
	::= 16415

dpsRTUp17415Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 31 is cleared"
	::= 17415

dpsRTUp16416Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 32 is set"
	::= 16416

dpsRTUp17416Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 32 is cleared"
	::= 17416

dpsRTUp16417Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 33 is set"
	::= 16417

dpsRTUp17417Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 33 is cleared"
	::= 17417

dpsRTUp16418Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 34 is set"
	::= 16418

dpsRTUp17418Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 34 is cleared"
	::= 17418

dpsRTUp16419Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 35 is set"
	::= 16419

dpsRTUp17419Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 35 is cleared"
	::= 17419

dpsRTUp16420Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 36 is set"
	::= 16420

dpsRTUp17420Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 36 is cleared"
	::= 17420

dpsRTUp16421Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 37 is set"
	::= 16421

dpsRTUp17421Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 37 is cleared"
	::= 17421

dpsRTUp16422Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 38 is set"
	::= 16422

dpsRTUp17422Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 38 is cleared"
	::= 17422

dpsRTUp16423Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 39 is set"
	::= 16423

dpsRTUp17423Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 39 is cleared"
	::= 17423

dpsRTUp16424Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 40 is set"
	::= 16424

dpsRTUp17424Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 40 is cleared"
	::= 17424

dpsRTUp16425Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 41 is set"
	::= 16425

dpsRTUp17425Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 41 is cleared"
	::= 17425

dpsRTUp16426Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 42 is set"
	::= 16426

dpsRTUp17426Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 42 is cleared"
	::= 17426

dpsRTUp16427Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 43 is set"
	::= 16427

dpsRTUp17427Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 43 is cleared"
	::= 17427

dpsRTUp16428Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 44 is set"
	::= 16428

dpsRTUp17428Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 44 is cleared"
	::= 17428

dpsRTUp16429Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 45 is set"
	::= 16429

dpsRTUp17429Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 45 is cleared"
	::= 17429

dpsRTUp16430Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 46 is set"
	::= 16430

dpsRTUp17430Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 46 is cleared"
	::= 17430

dpsRTUp16431Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 47 is set"
	::= 16431

dpsRTUp17431Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 47 is cleared"
	::= 17431

dpsRTUp16432Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 48 is set"
	::= 16432

dpsRTUp17432Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 48 is cleared"
	::= 17432

dpsRTUp16433Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 49 is set"
	::= 16433

dpsRTUp17433Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 49 is cleared"
	::= 17433

dpsRTUp16434Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 50 is set"
	::= 16434

dpsRTUp17434Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 50 is cleared"
	::= 17434

dpsRTUp16435Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 51 is set"
	::= 16435

dpsRTUp17435Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 51 is cleared"
	::= 17435

dpsRTUp16436Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 52 is set"
	::= 16436

dpsRTUp17436Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 52 is cleared"
	::= 17436

dpsRTUp16437Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 53 is set"
	::= 16437

dpsRTUp17437Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 53 is cleared"
	::= 17437

dpsRTUp16438Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 54 is set"
	::= 16438

dpsRTUp17438Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 54 is cleared"
	::= 17438

dpsRTUp16439Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 55 is set"
	::= 16439

dpsRTUp17439Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 55 is cleared"
	::= 17439

dpsRTUp16440Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 56 is set"
	::= 16440

dpsRTUp17440Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 56 is cleared"
	::= 17440

dpsRTUp16441Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 57 is set"
	::= 16441

dpsRTUp17441Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 57 is cleared"
	::= 17441

dpsRTUp16442Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 58 is set"
	::= 16442

dpsRTUp17442Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 58 is cleared"
	::= 17442

dpsRTUp16443Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 59 is set"
	::= 16443

dpsRTUp17443Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 59 is cleared"
	::= 17443

dpsRTUp16444Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 60 is set"
	::= 16444

dpsRTUp17444Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 60 is cleared"
	::= 17444

dpsRTUp16445Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 61 is set"
	::= 16445

dpsRTUp17445Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 61 is cleared"
	::= 17445

dpsRTUp16446Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 62 is set"
	::= 16446

dpsRTUp17446Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 62 is cleared"
	::= 17446

dpsRTUp16447Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 63 is set"
	::= 16447

dpsRTUp17447Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 63 is cleared"
	::= 17447

dpsRTUp16448Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 64 is set"
	::= 16448

dpsRTUp17448Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 7 point 64 is cleared"
	::= 17448

dpsRTUp16449Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 1 is set"
	::= 16449

dpsRTUp17449Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 1 is cleared"
	::= 17449

dpsRTUp16450Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 2 is set"
	::= 16450

dpsRTUp17450Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 2 is cleared"
	::= 17450

dpsRTUp16451Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 3 is set"
	::= 16451

dpsRTUp17451Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 3 is cleared"
	::= 17451

dpsRTUp16452Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 4 is set"
	::= 16452

dpsRTUp17452Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 4 is cleared"
	::= 17452

dpsRTUp16453Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 5 is set"
	::= 16453

dpsRTUp17453Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 5 is cleared"
	::= 17453

dpsRTUp16454Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 6 is set"
	::= 16454

dpsRTUp17454Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 6 is cleared"
	::= 17454

dpsRTUp16455Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 7 is set"
	::= 16455

dpsRTUp17455Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 7 is cleared"
	::= 17455

dpsRTUp16456Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 8 is set"
	::= 16456

dpsRTUp17456Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 8 is cleared"
	::= 17456

dpsRTUp16457Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 9 is set"
	::= 16457

dpsRTUp17457Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 9 is cleared"
	::= 17457

dpsRTUp16458Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 10 is set"
	::= 16458

dpsRTUp17458Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 10 is cleared"
	::= 17458

dpsRTUp16459Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 11 is set"
	::= 16459

dpsRTUp17459Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 11 is cleared"
	::= 17459

dpsRTUp16460Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 12 is set"
	::= 16460

dpsRTUp17460Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 12 is cleared"
	::= 17460

dpsRTUp16461Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 13 is set"
	::= 16461

dpsRTUp17461Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 13 is cleared"
	::= 17461

dpsRTUp16462Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 14 is set"
	::= 16462

dpsRTUp17462Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 14 is cleared"
	::= 17462

dpsRTUp16463Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 15 is set"
	::= 16463

dpsRTUp17463Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 15 is cleared"
	::= 17463

dpsRTUp16464Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 16 is set"
	::= 16464

dpsRTUp17464Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 16 is cleared"
	::= 17464

dpsRTUp16465Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 17 is set"
	::= 16465

dpsRTUp17465Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 17 is cleared"
	::= 17465

dpsRTUp16466Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 18 is set"
	::= 16466

dpsRTUp17466Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 18 is cleared"
	::= 17466

dpsRTUp16467Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 19 is set"
	::= 16467

dpsRTUp17467Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 19 is cleared"
	::= 17467

dpsRTUp16468Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 20 is set"
	::= 16468

dpsRTUp17468Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 20 is cleared"
	::= 17468

dpsRTUp16469Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 21 is set"
	::= 16469

dpsRTUp17469Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 21 is cleared"
	::= 17469

dpsRTUp16470Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 22 is set"
	::= 16470

dpsRTUp17470Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 22 is cleared"
	::= 17470

dpsRTUp16471Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 23 is set"
	::= 16471

dpsRTUp17471Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 23 is cleared"
	::= 17471

dpsRTUp16472Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 24 is set"
	::= 16472

dpsRTUp17472Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 24 is cleared"
	::= 17472

dpsRTUp16473Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 25 is set"
	::= 16473

dpsRTUp17473Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 25 is cleared"
	::= 17473

dpsRTUp16474Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 26 is set"
	::= 16474

dpsRTUp17474Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 26 is cleared"
	::= 17474

dpsRTUp16475Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 27 is set"
	::= 16475

dpsRTUp17475Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 27 is cleared"
	::= 17475

dpsRTUp16476Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 28 is set"
	::= 16476

dpsRTUp17476Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 28 is cleared"
	::= 17476

dpsRTUp16477Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 29 is set"
	::= 16477

dpsRTUp17477Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 29 is cleared"
	::= 17477

dpsRTUp16478Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 30 is set"
	::= 16478

dpsRTUp17478Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 30 is cleared"
	::= 17478

dpsRTUp16479Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 31 is set"
	::= 16479

dpsRTUp17479Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 31 is cleared"
	::= 17479

dpsRTUp16480Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 32 is set"
	::= 16480

dpsRTUp17480Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 32 is cleared"
	::= 17480

dpsRTUp16481Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 33 is set"
	::= 16481

dpsRTUp17481Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 33 is cleared"
	::= 17481

dpsRTUp16482Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 34 is set"
	::= 16482

dpsRTUp17482Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 34 is cleared"
	::= 17482

dpsRTUp16483Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 35 is set"
	::= 16483

dpsRTUp17483Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 35 is cleared"
	::= 17483

dpsRTUp16484Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 36 is set"
	::= 16484

dpsRTUp17484Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 36 is cleared"
	::= 17484

dpsRTUp16485Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 37 is set"
	::= 16485

dpsRTUp17485Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 37 is cleared"
	::= 17485

dpsRTUp16486Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 38 is set"
	::= 16486

dpsRTUp17486Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 38 is cleared"
	::= 17486

dpsRTUp16487Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 39 is set"
	::= 16487

dpsRTUp17487Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 39 is cleared"
	::= 17487

dpsRTUp16488Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 40 is set"
	::= 16488

dpsRTUp17488Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 40 is cleared"
	::= 17488

dpsRTUp16489Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 41 is set"
	::= 16489

dpsRTUp17489Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 41 is cleared"
	::= 17489

dpsRTUp16490Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 42 is set"
	::= 16490

dpsRTUp17490Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 42 is cleared"
	::= 17490

dpsRTUp16491Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 43 is set"
	::= 16491

dpsRTUp17491Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 43 is cleared"
	::= 17491

dpsRTUp16492Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 44 is set"
	::= 16492

dpsRTUp17492Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 44 is cleared"
	::= 17492

dpsRTUp16493Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 45 is set"
	::= 16493

dpsRTUp17493Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 45 is cleared"
	::= 17493

dpsRTUp16494Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 46 is set"
	::= 16494

dpsRTUp17494Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 46 is cleared"
	::= 17494

dpsRTUp16495Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 47 is set"
	::= 16495

dpsRTUp17495Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 47 is cleared"
	::= 17495

dpsRTUp16496Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 48 is set"
	::= 16496

dpsRTUp17496Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 48 is cleared"
	::= 17496

dpsRTUp16497Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 49 is set"
	::= 16497

dpsRTUp17497Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 49 is cleared"
	::= 17497

dpsRTUp16498Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 50 is set"
	::= 16498

dpsRTUp17498Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 50 is cleared"
	::= 17498

dpsRTUp16499Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 51 is set"
	::= 16499

dpsRTUp17499Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 51 is cleared"
	::= 17499

dpsRTUp16500Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 52 is set"
	::= 16500

dpsRTUp17500Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 52 is cleared"
	::= 17500

dpsRTUp16501Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 53 is set"
	::= 16501

dpsRTUp17501Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 53 is cleared"
	::= 17501

dpsRTUp16502Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 54 is set"
	::= 16502

dpsRTUp17502Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 54 is cleared"
	::= 17502

dpsRTUp16503Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 55 is set"
	::= 16503

dpsRTUp17503Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 55 is cleared"
	::= 17503

dpsRTUp16504Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 56 is set"
	::= 16504

dpsRTUp17504Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 56 is cleared"
	::= 17504

dpsRTUp16505Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 57 is set"
	::= 16505

dpsRTUp17505Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 57 is cleared"
	::= 17505

dpsRTUp16506Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 58 is set"
	::= 16506

dpsRTUp17506Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 58 is cleared"
	::= 17506

dpsRTUp16507Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 59 is set"
	::= 16507

dpsRTUp17507Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 59 is cleared"
	::= 17507

dpsRTUp16508Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 60 is set"
	::= 16508

dpsRTUp17508Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 60 is cleared"
	::= 17508

dpsRTUp16509Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 61 is set"
	::= 16509

dpsRTUp17509Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 61 is cleared"
	::= 17509

dpsRTUp16510Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 62 is set"
	::= 16510

dpsRTUp17510Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 62 is cleared"
	::= 17510

dpsRTUp16511Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 63 is set"
	::= 16511

dpsRTUp17511Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 63 is cleared"
	::= 17511

dpsRTUp16512Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 64 is set"
	::= 16512

dpsRTUp17512Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Generated when TBOS port 4 display 8 point 64 is cleared"
	::= 17512
END
