ATT-VPN-GATEWAY-MIB DEFINITIONS ::= BEGIN

IMPORTS
MODULE-IDENTITY, OBJECT-TYPE, enterprises,
Integer32, TimeTicks, IpAddress,
Unsigned32, NOTIFICATION-TYPE             FROM SNMPv2-SMI

DisplayString, DateAndTime                FROM SNMPv2-TC

InetAddressIPv6                           FROM INET-ADDRESS-MIB

MODULE-COMPLIANCE, OBJECT-GROUP, 
NOTIFICATION-GROUP                        FROM SNMPv2-CONF;

--     NOTE!!! If you have any older versions of this mib
--     (including ATT-NETGATE-MIB.txt) they should be deleted
--     from your local MIB directory. Having more than one copy
--     could cause issues with your SNMP polling.
--
--
--     Copyright (C) 2016 AT&T
--
--     Copyright (C) 2016 AT&T Intellectual Property. All rights reserved. 
--     AT&T, the AT&T logo and all other AT&T marks contained herein are trademarks
--     of AT&T Intellectual Property and/or AT&T affiliated companies. 
--
--     NETGATE is a registered trademark of Rubicon Communications L.P., and is used 
--     by AT&T by permission of Rubicon. All other marks contained herein are the 
--     property of their respective owners. The information contained herein is not
--     an offer, commitment, representation or warranty by AT&T and is subject to change.
--
--     Title: AT&T VPN Gateway Definitions
--
--     This file may be freely copied and distributed as
--     long as no changes are made to it.
--
--     This file should only be used with AT&T VPN Gateways running
--     version 4.7 (or later).

attVpnGatewayMIB MODULE-IDENTITY
    LAST-UPDATED "201603030000Z"
    ORGANIZATION "AT&T"
    CONTACT-INFO
            "Please contact your AT&T Account Representative."
    DESCRIPTION
            "The MIB module for the AT&T VPN Gateway."

    REVISION      "201603030000Z"
    DESCRIPTION
            "Added reporting of data usage statistics, support a ping
             list, return the circuit speed, tunnel enhancements.

             Supported by AT&T VPN Gateways running at least
             version 6.2."
    REVISION      "201501220000Z"
    DESCRIPTION
            "Changes to reflect device name change from AT&T NetGate to
             AT&T VPN Gateway. 'attVpnGateway' is the preferred subtree
             name instead of 'attNetGate'.

             Added evVrrpStateChange trap for VRRP state changes.
             Added several new items to the ng3GInfo section. The
             naming convention in this section now has items starting
             with 'cell' instead of 'ng3g'. Existing OIDs will not be 
             renamed to maintain compatibility.

             Adding reporting of tunnel automation to the ngTunnelInfo
             section. The naming convention in this section now has items 
             starting with 'tun' instead of 'ngtu'. Existing OIDs will not 
             be renamed to maintain compatibility.

             Adding reporting of time in backup to the interface section.
             The naming convention in this section now has items 
             starting with 'if' instead of 'ngif'. Existing OIDs will not 
             be renamed to maintain compatibility.

             Supported by AT&T VPN Gateways running at least
             version 6.1."
    REVISION      "201402180000Z"
    DESCRIPTION
            "Changed nghwWanConnectionMethod and nghwCurrentWanConnectionMethod
             so that wanAnalogDial is used instead of wanConfigDialPri. Also
             wanConfigCellularDial is now used instead of wanConfigCellularPri.

             Supported by AT&T VPN Gateways running at least
             version 6.0."
    REVISION      "201108020000Z"
    DESCRIPTION
            "Added the ngevCellModemRequired trap to alert when
             the cell modem is not found or removed.  Added cell
             modem status to the ng3GInfo section. Remove the range
             from the syntax for ng3gSlotNum because a -1 is returned
             when no card is found. Added support for IPv6 for
             polling and traps/informs.
             Added active WAN interface to excessive dial trap.

             Supported by AT&T VPN Gateways running at least
             version 5.3."
    REVISION      "201003150000Z"
    DESCRIPTION
            "Changed timestamps in polling fields to use the 
             standard DateAndTime format. Previously only fields
             in traps could be in DateAndTime format.
             Added nghwPorts section for more detailed info about
             hardware ports. Added ngev8200VPortDown trap.
             Supported by AT&T VPN Gateways running at least
             version 5.0."
    REVISION      "201003120000Z"
    DESCRIPTION
            "Added free-format customer field.
             Supported by AT&T VPN Gateways running at least
             version 4.10."
    REVISION      "200904290000Z"
    DESCRIPTION
            "Added traps for secondary authentication and switch
             user attempts.  These traps are supported by 
             AT&T VPN Gateways running at least version 4.9.
             Added max threshold to excessive dial trap.
             Changes made for strict MIB compliance.
             More OIDs added to ng3GInfo section.
             Added a new section called ngDialInfo that
             contains some of the dial configuration 
             information (regardless of whether a cellular card
             is in use or not).
             Supported by AT&T VPN Gateways running at least
             version 4.9."
    REVISION      "200807070000Z"
    DESCRIPTION
            "Added traps that the AT&T VPN Gateways can send.
             Added firewall sections that report on the firewall
             tables, chains, and rules active on the device.
             Added total time the dial connection has been active.
             Added current number and max number of ip_conntrack entries.
             Supported by AT&T VPN Gateways running at least
             version 4.8."
    REVISION      "200805120000Z"
    DESCRIPTION
            "Added compliance and conformance groups."
    REVISION      "200805090000Z"
    DESCRIPTION
            "Initial revision."
    ::= { attVpnGateway 8 }

att-2                OBJECT IDENTIFIER ::= { enterprises 74 }
att-products         OBJECT IDENTIFIER ::= { att-2 1 }

attVpnGateway        OBJECT IDENTIFIER ::= { att-products 30 }

ngHardwareInfo       OBJECT IDENTIFIER ::= { attVpnGateway 1 }
ngInterfaceInfo      OBJECT IDENTIFIER ::= { attVpnGateway 2 }
ngVlanInfo           OBJECT IDENTIFIER ::= { attVpnGateway 3 }
ngVrrpInfo           OBJECT IDENTIFIER ::= { attVpnGateway 4 }
ng3GInfo             OBJECT IDENTIFIER ::= { attVpnGateway 5 }
ngTunnelInfo         OBJECT IDENTIFIER ::= { attVpnGateway 6 }
ngCosInfo            OBJECT IDENTIFIER ::= { attVpnGateway 7 }
-- attVpnGateway 8 used above for MODULE-IDENTITY
ngFirewallInfo       OBJECT IDENTIFIER ::= { attVpnGateway 9 }
ngRogueMacInfo       OBJECT IDENTIFIER ::= { attVpnGateway 10 }
ngDialInfo           OBJECT IDENTIFIER ::= { attVpnGateway 11 }
ngDhcpLeaseInfo      OBJECT IDENTIFIER ::= { attVpnGateway 12 }
ngCaptPortalInfo     OBJECT IDENTIFIER ::= { attVpnGateway 13 }
attInbTunInfo        OBJECT IDENTIFIER ::= { attVpnGateway 14 }

ngMIBConformance     OBJECT IDENTIFIER ::= { attVpnGatewayMIB 1 }
ngMIBCompliances     OBJECT IDENTIFIER ::= { ngMIBConformance 1 }
ngMIBGroups          OBJECT IDENTIFIER ::= { ngMIBConformance 2 }

ngEvents             OBJECT IDENTIFIER ::= { attVpnGatewayMIB 2 }
ngEventNotification  OBJECT IDENTIFIER ::= { ngEvents 0 }
ngEventObjects       OBJECT IDENTIFIER ::= { ngEvents 1 }
ngEventConformance   OBJECT IDENTIFIER ::= { ngEvents 2 }
ngEventDataUsageObjects  OBJECT IDENTIFIER ::= { ngEvents 3 }
ngEventCompliances   OBJECT IDENTIFIER ::= { ngEventConformance 1 }
ngEventGroups        OBJECT IDENTIFIER ::= { ngEventConformance 2 }

--ngPlatforms OBJECT-IDENTITY
--	STATUS	current
--	DESCRIPTION
--		"Used for returning sysObjectID based on what 
--               hardware platform the device is."
--	::= { attVpnGatewayMIB 3 }

ngPlatforms          OBJECT IDENTIFIER ::= { attVpnGatewayMIB 3 }

--
-- Hardware Info
--
nghwHardwareVersion OBJECT-TYPE
    SYNTAX  DisplayString
    MAX-ACCESS  read-only
    STATUS      current
    DESCRIPTION
      "Hardware Version."
    ::= { ngHardwareInfo 1 }

nghwCodeVersion OBJECT-TYPE
    SYNTAX  DisplayString
    MAX-ACCESS  read-only
    STATUS      current
    DESCRIPTION
      "Software code version."
    ::= { ngHardwareInfo 2 }

nghwAccount OBJECT-TYPE
    SYNTAX  DisplayString (SIZE (1..8))
    MAX-ACCESS  read-only
    STATUS      current
    DESCRIPTION
      "The account in Service Manager this device
       is registered under."
    ::= { ngHardwareInfo 3 }

nghwUtcOffset OBJECT-TYPE
    SYNTAX  Integer32(-840..840)
    MAX-ACCESS  read-only
    STATUS      current
    DESCRIPTION
      "Indicates how many minutes away from UTC time the
       device is located. Values must be in 30 minute
       increments.  Valid range is -840 to 840."
    ::= { ngHardwareInfo 4 }

nghwDstAllowed OBJECT-TYPE
    SYNTAX  INTEGER {
      dstNotAllowed(0),
      dstAllowed(1)
    }
    MAX-ACCESS  read-only
    STATUS      current
    DESCRIPTION
      "Indicates if the device is located in an area that
       observes daylight savings time."
    ::= { ngHardwareInfo 5 }

nghwDstActive OBJECT-TYPE
    SYNTAX  INTEGER {
      dstNotActive(0),
      dstActive(1)
    }
    MAX-ACCESS  read-only
    STATUS      current
    DESCRIPTION
      "Indicates if daylight savings time is current active
       at this date and time."
    ::= { ngHardwareInfo 6 }

nghwWanConnectionMethod OBJECT-TYPE
    SYNTAX  INTEGER {
     wanConfigUnknown(0),
     wanConfigStatic(1),
     wanConfigDHCP(2),
     wanConfigPPPoE(3),
     wanConfigAnalogDial(4),
     wanConfigISDNPri(5),
     wanConfigPPPoA(6),
     wanConfigCellularPer(7),
     wanConfigCellularDial(8)
    }     
    MAX-ACCESS  read-only
    STATUS      current
    DESCRIPTION
      "The current primary IPv4 WAN connection setting. This is configured
       via the web interface and is not read from Service Manager."
    ::= { ngHardwareInfo 7 }

nghwHostname OBJECT-TYPE
    SYNTAX  DisplayString
    MAX-ACCESS  read-only
    STATUS      current
    DESCRIPTION
      "The name of the current host."
    ::= { ngHardwareInfo 8 }

--
-- IPv4 DNS Servers
--
nghwDnsServers       OBJECT IDENTIFIER ::= { ngHardwareInfo 9 }

ngDnsTable OBJECT-TYPE
    SYNTAX     SEQUENCE OF NgDnsEntry
    MAX-ACCESS not-accessible
    STATUS     current
    DESCRIPTION
        "The (conceptual) table of DNS on the device.
        An entry shall be placed in the storage table for each
        DNS."
    ::= { nghwDnsServers 1 }

ngDnsEntry OBJECT-TYPE
    SYNTAX     NgDnsEntry
    MAX-ACCESS not-accessible
    STATUS     current
    DESCRIPTION
        "A (conceptual) entry for one logical DNS area on
        the host."
    INDEX { ngdnIndex }
    ::= { ngDnsTable 1 }

NgDnsEntry ::= SEQUENCE {
        ngdnIndex            Integer32,
        ngdnServer           IpAddress
    }

ngdnIndex OBJECT-TYPE
    SYNTAX     Integer32 (1..65535)
    MAX-ACCESS not-accessible
    STATUS     current
    DESCRIPTION
        "A unique value for each logical DNS
         contained on the device."
    ::= { ngDnsEntry 1 }

ngdnServer OBJECT-TYPE
    SYNTAX      IpAddress
    MAX-ACCESS  read-only
    STATUS      current
    DESCRIPTION
      "The IP address of an indivdual name server in use."
    ::= { ngDnsEntry 2 }

--
-- IPv6 DNS Servers
--
ngDnsIPv6Table OBJECT-TYPE
    SYNTAX     SEQUENCE OF NgDnsIPv6Entry
    MAX-ACCESS not-accessible
    STATUS     current
    DESCRIPTION
        "The (conceptual) table of IPv6 DNS on the device.
         An entry shall be placed in the storage table for each
         DNS."
    ::= { nghwDnsServers 2 }

ngDnsIPv6Entry OBJECT-TYPE
    SYNTAX     NgDnsIPv6Entry
    MAX-ACCESS not-accessible
    STATUS     current
    DESCRIPTION
        "A (conceptual) entry for one logical IPv6 DNS area on
         the host."
    INDEX { ngdnIPv6Index }
    ::= { ngDnsIPv6Table 1 }

NgDnsIPv6Entry ::= SEQUENCE {
        ngdnIPv6Index            Integer32,
        ngdnIPv6Server           InetAddressIPv6
    }

ngdnIPv6Index OBJECT-TYPE
    SYNTAX     Integer32 (1..65535)
    MAX-ACCESS not-accessible
    STATUS     current
    DESCRIPTION
        "A unique value for each logical IPv6 DNS
         contained on the device."
    ::= { ngDnsIPv6Entry 1 }

ngdnIPv6Server OBJECT-TYPE
    SYNTAX      InetAddressIPv6
    MAX-ACCESS  read-only
    STATUS      current
    DESCRIPTION
      "The IPv6 IP address of an indivdual name server in use."
    ::= { ngDnsIPv6Entry 2 }
--
-- end IPv4 Iv6 DNS Servers 
--

nghwDeviceStatus OBJECT-TYPE
    SYNTAX  INTEGER {
      deviceActive        (0), 
      deviceInActive      (1), 
      deviceDiscontinued  (2), 
      deviceNotConfigured (3), 
      deviceBadVlanSwitch (4)
    }
    MAX-ACCESS  read-only
    STATUS      current
    DESCRIPTION
      "The current device status."
    ::= { ngHardwareInfo 10 }

nghwLanguage OBJECT-TYPE
    SYNTAX  DisplayString (SIZE (1..2))
    MAX-ACCESS  read-only
    STATUS      current
    DESCRIPTION
      "The language that will be displayed on the CGI web
       interface.
       The valid values are:                          
         EN = English                                 
         JA = Japanese                                
         ES = Spanish                                 
         BP = Brazil Portuguese                       
         FC = French Canadian                        
         TC = Traditional Chinese                    
         SC = Simplified Chinese"
    ::= { ngHardwareInfo 11 }

-- // start customer comment info
nghwCustComm OBJECT IDENTIFIER ::= { ngHardwareInfo 12 }

ngCustCommTable OBJECT-TYPE
    SYNTAX     SEQUENCE OF NgCustCommEntry
    MAX-ACCESS not-accessible
    STATUS     current
    DESCRIPTION
        "The (conceptual) table of customer info (such as 
         comments) on the device.  An entry shall be placed 
         in the storage table for each one."
    ::= { nghwCustComm 1 }

ngCustCommEntry OBJECT-TYPE
    SYNTAX     NgCustCommEntry
    MAX-ACCESS not-accessible
    STATUS     current
    DESCRIPTION
        "A (conceptual) entry for one logical customer comment 
         area on the host."
    INDEX { ngcuIndex }
    ::= { ngCustCommTable 1 }

NgCustCommEntry ::= SEQUENCE {
        ngcuIndex            Integer32,
        ngcuCustComment      DisplayString
    }

ngcuIndex OBJECT-TYPE
    SYNTAX     Integer32 (1..65535)
    MAX-ACCESS not-accessible
    STATUS     current
    DESCRIPTION
        "A unique value for each logical customer info."
    ::= { ngCustCommEntry 1 }

ngcuCustComment OBJECT-TYPE
    SYNTAX  DisplayString
    MAX-ACCESS  read-only
    STATUS      current
    DESCRIPTION
      "A free-format field that can be added to the AT&T VPN Gateway's
       profile at a customer's request.
       Currently only one comment field can be specified."
    ::= { ngCustCommEntry 2 }

-- // end customer comment info

-- // start port info
nghwPorts            OBJECT IDENTIFIER ::= { ngHardwareInfo 13 }

ngPortTable OBJECT-TYPE
    SYNTAX     SEQUENCE OF NgPortEntry
    MAX-ACCESS not-accessible
    STATUS     current
    DESCRIPTION
        "The (conceptual) table of ports on the device.
        An entry shall be placed in the storage table for each
        port."
    ::= { nghwPorts 1 }

ngPortEntry OBJECT-TYPE
    SYNTAX     NgPortEntry
    MAX-ACCESS not-accessible
    STATUS     current
    DESCRIPTION
        "A (conceptual) entry for one logical port area on
        the host."
    INDEX { ngpoIndex }
    ::= { ngPortTable 1 }

NgPortEntry ::= SEQUENCE {
        ngpoIndex            Integer32,
        ngpoStatus           INTEGER
    }

ngpoIndex OBJECT-TYPE
    SYNTAX     Integer32 (1..65535)
    MAX-ACCESS not-accessible
    STATUS     current
    DESCRIPTION
        "A unique value for each logical port
         contained on the device."
    ::= { ngPortEntry 1 }

ngpoStatus OBJECT-TYPE
    SYNTAX  INTEGER {
                inactive(0),
                active(1),
                unknown(2)
            }
    MAX-ACCESS  read-only
    STATUS      current
    DESCRIPTION
      "The link status of an individual hardware port."
    ::= { ngPortEntry 2 }

-- // end port info

nghwCurrentWanConnectionMethod OBJECT-TYPE
    SYNTAX  INTEGER {
     wanConfigUnknown(0),
     wanConfigStatic(1),
     wanConfigDHCP(2),
     wanConfigPPPoE(3),
     wanConfigAnalogDial(4),
     wanConfigISDNPri(5),
     wanConfigPPPoA(6),
     wanConfigCellularPer(7),
     wanConfigCellularDial(8),
     wanConfigStatic2(9),
     wanConfigDHCP2(10),
     wanConfigPPPoE2(11)
    }
    MAX-ACCESS  read-only
    STATUS      current
    DESCRIPTION
      "The currently active IPv4 WAN connection, which may differ from the configured
       primary IPv4 WAN connection setting.  For example, the primary IPv4 WAN is
       configured for DHCP (wanConfigDHCP), but because of a network outage the 
       PPPoE secondary WAN connection (wanConfigPPPoE2) is currently providing 
       connectivity."
    ::= { ngHardwareInfo 14 }

nghwIPv6WanConnectionMethod OBJECT-TYPE
    SYNTAX  INTEGER {
     wanConfigUnknown(0),
     wanConfigIPv6Static(12),
     wanConfigIPv6DHCP(13),
     wanConfigIPv6Stateless(14),
     wanConfigOff(15),
     wanConfigIPv6PPPoEDHCP(19)
    }
    MAX-ACCESS  read-only
    STATUS      current
    DESCRIPTION
      "The current primary IPv6 WAN connection setting. This is configured
       via the web interface and is not read from Service Manager."
    ::= { ngHardwareInfo 15 }

nghwIPv6CurrentWanConnectionMethod OBJECT-TYPE
    SYNTAX  INTEGER {
     wanConfigUnknown(0),
     wanConfigIPv6Static(12),
     wanConfigIPv6DHCP(13),
     wanConfigIPv6Stateless(14),
     wanConfigOff(15),
     wanConfigIPv6Static2(16),
     wanConfigIPv6DHCP2(17),
     wanConfigIPv6Stateless2(18),
     wanConfigIPv6PPPoEDHCP(19),
     wanConfigIPv6PPPoEDHCP2(20)
    }
    MAX-ACCESS  read-only
    STATUS      current
    DESCRIPTION
      "The currently active IPv6 WAN connection, which may differ from the configured
       primary IPv6 WAN connection setting.  For example, the primary IPv4 WAN is
       configured for DHCP (wanConfigIPv6DHCP), but because of a network outage the 
       static IP secondary WAN connection (wanConfigIPv6Static2) is currently providing 
       connectivity."
    ::= { ngHardwareInfo 16 }

nghwLastFullQueryTimeDAT OBJECT-TYPE
    SYNTAX      DateAndTime
    MAX-ACCESS  read-only
    STATUS      current
    DESCRIPTION
      "The last time when the AT&T VPN Gateway was successfully able to retrieve its full
       profile from an AT&T Administration Server."
    ::= { ngHardwareInfo 17 }

nghwLastAnyQueryTimeDAT OBJECT-TYPE
    SYNTAX      DateAndTime
    MAX-ACCESS  read-only
    STATUS      current
    DESCRIPTION
      "The last time when the AT&T VPN Gateway was successfully able to retrieve
       its profile from an AT&T Administration Server.  If this time
       does not match nghwLastFullQueryTimeDAT then that means only part of the 
       profile was retrieved. This is to prevent any possible reboots if critical 
       portions of the profile were to change."
    ::= { ngHardwareInfo 18 }

nghwLastUpgradeTimeDAT OBJECT-TYPE
    SYNTAX      DateAndTime
    MAX-ACCESS  read-only
    STATUS      current
    DESCRIPTION
      "The last time when the software version of AT&T VPN Gateway was successfully
       upgraded. Returns January 1 year 0 time 0 when this cannot be determined."
    ::= { ngHardwareInfo 19 }

hwMac OBJECT-TYPE
    SYNTAX     DisplayString
    MAX-ACCESS read-only
    STATUS     current
    DESCRIPTION
        "The main WAN MAC address of this device used to identify its profile in 
         Service Manager."
    ::= { ngHardwareInfo 20 }

hwRollbackVersion OBJECT-TYPE
    SYNTAX  DisplayString
    MAX-ACCESS  read-only
    STATUS      current
    DESCRIPTION
      "Software code version that will be used if the rollback feature
       is activated."
    ::= { ngHardwareInfo 21 }

hwDualWan OBJECT-TYPE
    SYNTAX  INTEGER {
     notEnabled(0),
     wan1AndWan2BackupEachOther(1),
     noInetIfEitherWanIsDown(2)
    }
    MAX-ACCESS  read-only
    STATUS      current
    DESCRIPTION
      "Ties to the 'Use as Internet Primary' field in Service Manager. Controls
       the Dual WAN configuration."
    ::= { ngHardwareInfo 22 }

hwWan2ConnectionMethod OBJECT-TYPE
    SYNTAX  INTEGER {
     wanConfigUnknown(0),
     wanConfigStatic(1),
     wanConfigDHCP(2),
     wanConfigPPPoE(3),
     wanConfigAnalogDial(4),
     wanConfigISDNPri(5),
     wanConfigPPPoA(6),
     wanConfigCellularPer(7),
     wanConfigCellularDial(8),
     wanConfigStatic2(9),
     wanConfigDHCP2(10),
     wanConfigPPPoE2(11)
    }
    MAX-ACCESS  read-only
    STATUS      current
    DESCRIPTION
      "The current WAN2 IPv4 WAN connection setting. This is not configured
       via the web interface and is read from Service Manager."
    ::= { ngHardwareInfo 23 }

hwIPv6Wan2ConnectionMethod OBJECT-TYPE
    SYNTAX  INTEGER {
     wanConfigOff(0),
     wanConfigIPv6Static(1),
     wanConfigIPv6DHCP(2),
     wanConfigIPv6Stateless(3),
     wanConfigIPv6PPPoEDHCP(4)
    }
    MAX-ACCESS  read-only
    STATUS      current
    DESCRIPTION
      "The current WAN2 IPv6 WAN connection setting. This is not configured
       via the web interface and is read from Service Manager."
    ::= { ngHardwareInfo 24 }

hwWan1GwayMac OBJECT-TYPE
    SYNTAX     DisplayString
    MAX-ACCESS read-only
    STATUS     current
    DESCRIPTION
        "This is the MAC Address of the WAN1 Gateway router if it is in use.
         For MAC Address range from 002704000000 to 002704009999, it
         is a NetBridge (SX) device.
         For MAC Address range from 002704010000 to 002704010425, it
         is a NetBridge (FX) device.
         For MAC Address range from 002704010426 to 002704019999, it
         is a Cell Extender (6200-FX) device.
         For MAC Address range from 002704270000 to 002704279999, it
         is a Cell Extender (6300-CX) device."
    ::= { ngHardwareInfo 25 }

hwWan2Mac OBJECT-TYPE
    SYNTAX     DisplayString
    MAX-ACCESS read-only
    STATUS     current
    DESCRIPTION
        "This is the MAC Address of the WAN2 interface if it is in use."
    ::= { ngHardwareInfo 26 }

hwWan2GwayMac OBJECT-TYPE
    SYNTAX     DisplayString
    MAX-ACCESS read-only
    STATUS     current
    DESCRIPTION
        "This is the MAC Address of the WAN2 Gateway router if it is in use.
         For MAC Address range from 002704000000 to 002704009999, it
         is a NetBridge (SX) device.
         For MAC Address range from 002704010000 to 002704010425, it
         is a NetBridge (FX) device.
         For MAC Address range from 002704010426 to 002704019999, it
         is a Cell Extender (6200-FX) device.
         For MAC Address range from 002704270000 to 002704279999, it
         is a Cell Extender (6300-CX) device."
    ::= { ngHardwareInfo 27 }

--
-- Interface Info
--
ngifActiveWanIface OBJECT-TYPE
    SYNTAX  DisplayString
    MAX-ACCESS  read-only
    STATUS      current
    DESCRIPTION
      "The interface that is currently in use for the
       primary connection."
    ::= { ngInterfaceInfo 1 }

ngifTotalBytesIn OBJECT-TYPE
    SYNTAX  Unsigned32
    MAX-ACCESS  read-only
    STATUS      current
    DESCRIPTION
      "Total bytes in on the active WAN interface."
    ::= { ngInterfaceInfo 2 }

ngifTotalBytesOut OBJECT-TYPE
    SYNTAX  Unsigned32
    MAX-ACCESS  read-only
    STATUS      current
    DESCRIPTION
      "Total bytes out on the active WAN interface."
    ::= { ngInterfaceInfo 3 }

ngifTimeInDial OBJECT-TYPE
    SYNTAX     TimeTicks
    MAX-ACCESS read-only
    STATUS     current
    DESCRIPTION
        "How long the current dial connection has been up."
    ::= { ngInterfaceInfo 4 }

ifTimeInBackup OBJECT-TYPE
    SYNTAX     TimeTicks
    MAX-ACCESS read-only
    STATUS     current
    DESCRIPTION
        "How long the backup connection has been up. This is 
         very similar to ngifTimeInDial. The difference is
         that ngifTimeInDial isn't necessarily measuring a
         backup connection.  For example, when configured
         for 'Dial As Primary' ifTimeInBackup will always
         remain zero because there is no backup for Dial As
         Primary but ngifTimeInDial will be non-zero when
         the connection is up.  In other WAN configurations
         (such as DHCP, for example) both ngifTimeInDial
         and ifTimeInBackup will be non-zero when the 
         backup connection is in use."
    ::= { ngInterfaceInfo 5 }

ifInterfaceFormat OBJECT-TYPE
    SYNTAX  INTEGER {
     none(0),
     standard(3),
     accountANRKSIonly(4)
    }
    MAX-ACCESS  read-only
    STATUS      current
    DESCRIPTION
      "Setting from the Service Manager profile that controls 
       SNMP interface persistence. Zero indicates that this feature
       is not in use."
    ::= { ngInterfaceInfo 6 }

--
-- Interface statistics that are not in the standard MIBs
--
ifIfaceStats       OBJECT IDENTIFIER ::= { ngInterfaceInfo 7 }

ifStatTable OBJECT-TYPE
    SYNTAX     SEQUENCE OF IfStatEntry
    MAX-ACCESS not-accessible
    STATUS     current
    DESCRIPTION
        "The (conceptual) table of interface statistics on the device.
        An entry shall be placed in the storage table for each
        interface statistic."
    ::= { ifIfaceStats 1 }

ifStatEntry OBJECT-TYPE
    SYNTAX     IfStatEntry
    MAX-ACCESS not-accessible
    STATUS     current
    DESCRIPTION
        "A (conceptual) entry for one logical interface statistic area."
    INDEX { ifStatsMainIndex }
    ::= { ifStatTable 1 }

IfStatEntry ::= SEQUENCE {
        ifStatsMainIndex        Integer32,
        ifStatsifIndex          Integer32,
        ifStatsifDescr          DisplayString,
        ifStatsRxCrcErr         Unsigned32
    }

ifStatsMainIndex OBJECT-TYPE
    SYNTAX     Integer32 (1..65535)
    MAX-ACCESS not-accessible
    STATUS     current
    DESCRIPTION
        "A unique value for each logical interface statistic."
    ::= { ifStatEntry 1 }

ifStatsifIndex OBJECT-TYPE
    SYNTAX     Integer32 (1..65535)
    MAX-ACCESS read-only
    STATUS     current
    DESCRIPTION
        "The value of this index reported by ifIndex in the standard
         MIBs. This is needed because index numbers can be skipped
         in the standard MIBs."
    ::= { ifStatEntry 2 }

ifStatsifDescr OBJECT-TYPE
    SYNTAX      DisplayString
    MAX-ACCESS  read-only
    STATUS      current
    DESCRIPTION
      "A textual string containing information about the interface."
    ::= { ifStatEntry 3 }

ifStatsRxCrcErr OBJECT-TYPE
    SYNTAX  Unsigned32
    MAX-ACCESS  read-only
    STATUS      current
    DESCRIPTION
      "Received CRC errors for the interface."
    ::= { ifStatEntry 4 }
--
-- end Interface statistics that are not in the standard MIBs
--

ifCircuitSpeed OBJECT-TYPE
    SYNTAX  DisplayString
    MAX-ACCESS  read-only
    STATUS      current
    DESCRIPTION
      "Informational string that is pulled from the device profile.
       Useful for the scenario where the physical connection to the 
       WAN interface will be 10, 100 or 1000 Mbps (depending on the 
       ISP modem/router) but the speed allocated by the ISP will be 
       much lower (2, 4, or 8 Mbps). This field does not control
       speed and does not indicate a measurement of speed.
       It is manually entered by an administrator for informational
       purposes only."
    ::= { ngInterfaceInfo 8 }

--
-- VLAN Info
--
ngVlanTable OBJECT-TYPE
    SYNTAX     SEQUENCE OF NgVlanEntry
    MAX-ACCESS not-accessible
    STATUS     current
    DESCRIPTION
        "The (conceptual) table of VLANs on the device.
        An entry shall be placed in the storage table for each
        VLAN."
    ::= { ngVlanInfo 1 }

ngVlanEntry OBJECT-TYPE
    SYNTAX     NgVlanEntry
    MAX-ACCESS not-accessible
    STATUS     current
    DESCRIPTION
        "A (conceptual) entry for one logical VLAN area on
        the host."
    INDEX { ngvlIndex }
    ::= { ngVlanTable 1 }

NgVlanEntry ::= SEQUENCE {
        ngvlIndex            Integer32,
        ngvlId               Integer32,
        ngvlPorts            DisplayString,
        ngvlSpeed            INTEGER,
        ngvlIpRange          DisplayString,
        ngvlDhcpRelayAddr    DisplayString,
        ngvlDhcpDefRoute     IpAddress,
        ngvlLanAddr          IpAddress,
        ngvlLanSubAddr       IpAddress,
        ngvlIPv6IpRangeStart InetAddressIPv6,
        ngvlIPv6IpRangeEnd   InetAddressIPv6,
        ngvlIPv6DhcpRelayAddrPri InetAddressIPv6,
        ngvlIPv6DhcpRelayAddrBak InetAddressIPv6,
        ngvlIPv6LanAddr      InetAddressIPv6,
        ngvlIPv6LanPrefix    Integer32,
        ngvlSpeedCurrent     INTEGER
    }

ngvlIndex OBJECT-TYPE
    SYNTAX     Integer32 (1..65535)
    MAX-ACCESS not-accessible
    STATUS     current
    DESCRIPTION
        "A unique value for each logical VLAN
        contained by the device."
    ::= { ngVlanEntry 1 }

ngvlId OBJECT-TYPE
    SYNTAX      Integer32 (0..65535)
    MAX-ACCESS  read-only
    STATUS      current
    DESCRIPTION
      "This is the number assigned to the VLAN. 
       Please note: A VLAN with an ID of 4070 is a special
       VLAN used to hold ports that are disabled."
    ::= { ngVlanEntry 2 }

ngvlPorts OBJECT-TYPE
    SYNTAX     DisplayString
    MAX-ACCESS read-only
    STATUS     current
    DESCRIPTION
      "The ports assigned to the VLAN."
    ::= { ngVlanEntry 3 }

-- Had to add "speed" to the front of some because enumerated
-- types cannot start with a number.  5/9/2008 

ngvlSpeed OBJECT-TYPE
    SYNTAX  INTEGER {
      notActive(0),
      autoNegot(1),
      speed10MbitHalfDuplex(2),
      speed10MbitFullDuplex(3),
      speed100MbitHalfDuplex(4),
      speed100MbitFullDuplex(5),
      speed1000MbitHalfDuplex(6),
      speed1000MbitFullDuplex(7)
    }
    MAX-ACCESS  read-only
    STATUS      current
    DESCRIPTION
     "This is the speed supported on the VLAN Ethernet interfaces. If the VLAN
      Ethernet speed is configured for auto negotiation then autoNegot will be 
      reported and the negotiated speed will be reported by ngvlSpeedCurrent. 
      If the VLAN Ethernet speed is configured for a specific speed that speed
      will be reported."
    ::= { ngVlanEntry 4 }

ngvlIpRange OBJECT-TYPE
    SYNTAX     DisplayString
    MAX-ACCESS read-only
    STATUS     current
    DESCRIPTION
        "The range of IP addresses handed out via
         DHCP on this VLAN.  Values will be 0.0.0.0 0.0.0.0
         if DHCP is not enabled on this VLAN.  Followed by
         number of addresses assigned and number of total
         addresses.
         NOTE: As of AT&T VPN Gateway version 5.3 the number of 
         addresses assigned will no longer be returned.  A 
         zero will be returned for that field."
    ::= { ngVlanEntry 5 }

ngvlDhcpRelayAddr OBJECT-TYPE
    SYNTAX     DisplayString
    MAX-ACCESS read-only
    STATUS     current
    DESCRIPTION
       "When the DHCP Type is 'R', this is the address the AT&T VPN Gateway      
        devices uses to relay DHCP requests. This field is required     
        when the DHCP Type is 'R'. A second address can be specified."
    ::= { ngVlanEntry 6 }

ngvlDhcpDefRoute OBJECT-TYPE
    SYNTAX      IpAddress
    MAX-ACCESS  read-only
    STATUS      current
    DESCRIPTION
      "This field is required when VRRP Active Indicator is 'Y' and         
       is optional otherwise.  If specified, it must be within the          
       local LAN subnet of the AT&T VPN Gateway but cannot fall within the           
       DHCP pool start and end addresses.                                   
                                                                        
       For the DHCP Default Route on the AT&T VPN Gateway device profile,            
       if entered, the address must be within the network specified         
       by the LAN Address and LAN Subnet, but not within the address        
       range specified by the DHCP Start Address and DHCP End               
       Address."
    ::= { ngVlanEntry 7 }

ngvlLanAddr OBJECT-TYPE
    SYNTAX      IpAddress
    MAX-ACCESS  read-only
    STATUS      current
    DESCRIPTION
            "This is the LAN address for the device on the VLAN. "
    ::= { ngVlanEntry 8 }

ngvlLanSubAddr OBJECT-TYPE
    SYNTAX      IpAddress
    MAX-ACCESS  read-only
    STATUS      current
    DESCRIPTION
            "This is the LAN subnet address for the device on the VLAN. "
    ::= { ngVlanEntry 9 }

ngvlIPv6IpRangeStart OBJECT-TYPE
    SYNTAX      InetAddressIPv6
    MAX-ACCESS  read-only
    STATUS      current
    DESCRIPTION
        "The start of the range of IPv6 IP addresses handed out via
         DHCP on this VLAN.  Value will be all zeroes
         if DHCP is not enabled on this VLAN."
    ::= { ngVlanEntry 10 }

ngvlIPv6IpRangeEnd OBJECT-TYPE
    SYNTAX      InetAddressIPv6
    MAX-ACCESS  read-only
    STATUS      current
    DESCRIPTION
        "The end of the range of IPv6 IP addresses handed out via
         DHCP on this VLAN.  Value will be all zeroes
         if DHCP is not enabled on this VLAN." 
    ::= { ngVlanEntry 11 }

ngvlIPv6DhcpRelayAddrPri OBJECT-TYPE
    SYNTAX     InetAddressIPv6
    MAX-ACCESS read-only
    STATUS     current
    DESCRIPTION
       "When the DHCP Type is 'R', this is the primary address the AT&T VPN Gateway
        devices uses to relay DHCP requests. This field is required
        when the DHCP Type is 'R' and IPv6 is in use."
    ::= { ngVlanEntry 12 }

ngvlIPv6DhcpRelayAddrBak OBJECT-TYPE
    SYNTAX     InetAddressIPv6
    MAX-ACCESS read-only
    STATUS     current
    DESCRIPTION
       "When the DHCP Type is 'R', this is the primary address the AT&T VPN Gateway
        devices uses to relay DHCP requests."
    ::= { ngVlanEntry 13 }

ngvlIPv6LanAddr OBJECT-TYPE 
    SYNTAX      InetAddressIPv6
    MAX-ACCESS  read-only
    STATUS      current
    DESCRIPTION 
            "This is the IPv6 LAN address for the device on the VLAN. "
    ::= { ngVlanEntry 14 }
      
ngvlIPv6LanPrefix OBJECT-TYPE
    SYNTAX      Integer32 (0..65535)
    MAX-ACCESS  read-only
    STATUS      current
    DESCRIPTION
            "This is the IPv6 LAN prefix for the device on the VLAN."
    ::= { ngVlanEntry 15 }

ngvlSpeedCurrent OBJECT-TYPE
    SYNTAX  INTEGER {
      noLink(0),
      speed10MbitHalfDuplex(2),
      speed10MbitFullDuplex(3),
      speed100MbitHalfDuplex(4),
      speed100MbitFullDuplex(5),
      speed1000MbitHalfDuplex(6),
      speed1000MbitFullDuplex(7)
    }
    MAX-ACCESS  read-only
    STATUS      current
    DESCRIPTION
     "This is the current speed in use on the VLAN Ethernet interfaces.
      This is helpful to determine what was chosen if the speed was set to 
      auto negotiate.
      If the VLAN Ethernet speed is configured for auto negotiation then
      the negotiated speed will be reported.  If the VLAN Ethernet speed is 
      configured for auto negotiation and there is no link then noLink will be 
      reported. If the VLAN Ethernet speed is configured for a specific 
      speed that speed will be reported."
    ::= { ngVlanEntry 16 }

--
-- end VLAN IPv4 IPv6 Info
--


--
-- VRRP Info
--
ngVrrpTable OBJECT-TYPE
    SYNTAX     SEQUENCE OF NgVrrpEntry
    MAX-ACCESS not-accessible
    STATUS     current
    DESCRIPTION
        "The (conceptual) table of VRRPs on the device.
        An entry shall be placed in the storage table for each
        VRRP."
    ::= { ngVrrpInfo 1 }

ngVrrpEntry OBJECT-TYPE
    SYNTAX     NgVrrpEntry
    MAX-ACCESS not-accessible
    STATUS     current
    DESCRIPTION
        "A (conceptual) entry for one logical VRRP area on
        the host."
    INDEX { ngvrIndex }
    ::= { ngVrrpTable 1 }

NgVrrpEntry ::= SEQUENCE {
        ngvrIndex            Integer32,
        ngvrIface            DisplayString,
        ngvrId               Integer32,
        ngvrMasterStatus     INTEGER,
        ngvrPriority         INTEGER
    }

ngvrIndex OBJECT-TYPE
    SYNTAX     Integer32 (1..65535)
    MAX-ACCESS not-accessible
    STATUS     current
    DESCRIPTION
        "A unique value for each logical VRRP
        contained by the device."
    ::= { ngVrrpEntry 1 }

ngvrIface OBJECT-TYPE
    SYNTAX     DisplayString
    MAX-ACCESS read-only
    STATUS     current
    DESCRIPTION
        "The interface associated with this VRRP."
    ::= { ngVrrpEntry 2 }

ngvrId OBJECT-TYPE
    SYNTAX     Integer32 (0..65535)
    MAX-ACCESS read-only
    STATUS     current
    DESCRIPTION
        "Virtual router ID."
    ::= { ngVrrpEntry 3 }

ngvrMasterStatus OBJECT-TYPE
    SYNTAX     INTEGER {
      vrrpNotRunning(0),
      vrrpMasterState(1),   
      vrrpBackupState(2),   
      vrrpFaultState(3)    
    }
    MAX-ACCESS read-only
    STATUS     current
    DESCRIPTION
        "Shows what the status is (master, backup, not active)."
    ::= { ngVrrpEntry 4 }

ngvrPriority OBJECT-TYPE
    SYNTAX     INTEGER {
      stop(0),
      default(100),
      owner(255)
    }
    MAX-ACCESS read-only
    STATUS     current
    DESCRIPTION
        "VRRP_PRIO_OWNER	255	/* priority of the ip owner -- rfc2338.5.3.4 */
         VRRP_PRIO_DFL	100	/* default priority -- rfc2338.5.3.4 */
         VRRP_PRIO_STOP	0	/* priority to stop -- rfc2338.5.3.4 */"
    ::= { ngVrrpEntry 5 }

--
-- Cellular Modem Info
-- This section details information about each cellular modem that is in use by the AT&T VPN Gateway.
--
ng3GTable OBJECT-TYPE
    SYNTAX     SEQUENCE OF Ng3GEntry
    MAX-ACCESS not-accessible
    STATUS     current
    DESCRIPTION
        "The (conceptual) table of 3G cards on the device.
        An entry shall be placed in the storage table for each
        3G card."
    ::= { ng3GInfo 1 }

ng3GEntry OBJECT-TYPE
    SYNTAX     Ng3GEntry
    MAX-ACCESS not-accessible
    STATUS     current
    DESCRIPTION
        "A (conceptual) entry for one logical 3G card area on
        the host."
    INDEX { ng3gIndex }
    ::= { ng3GTable 1 }

Ng3GEntry ::= SEQUENCE {
        ng3gIndex            Integer32,
        ng3gSlotNum          Integer32,
        ng3gModemType        DisplayString,
        ng3gManufacturer     DisplayString,
        ng3gModel            DisplayString,
        ng3gRevision         DisplayString,
        ng3gID               DisplayString,
        ng3gSignalStrength   Integer32,
        ng3gCarrier          DisplayString,
        ng3gImsiStatus       DisplayString,
        ng3gCellConnNetwork  DisplayString,
        ng3gPhoneNum         DisplayString,
        ng3gApn              DisplayString,
        ng3gApnUser          DisplayString,
        ng3gApnPassword      DisplayString,
        ng3gCellModemPresent INTEGER,
        ng3gSIMCardNumber    DisplayString,
        ng3gDeviceType       INTEGER,
        cellCollectionTimeDAT DateAndTime,
        cellConnStatus       DisplayString,
        cellNetworkTech      DisplayString,
        cellCarrier          DisplayString,
        cellMCC              DisplayString,
        cellMNC              DisplayString,
        cellLAC              DisplayString,
        cellCID              DisplayString,
        cellBars             Integer32,
        cellRSSI             DisplayString,
        cellECIO             DisplayString,
        cellRSRP             DisplayString,
        cellRSRQ             DisplayString,
        cellSINR             DisplayString,
        cellSNR              DisplayString,
        cellIface            DisplayString
    }

ng3gIndex OBJECT-TYPE
    SYNTAX     Integer32 (1..65535)
    MAX-ACCESS not-accessible
    STATUS     current
    DESCRIPTION
        "A unique value for each logical 3G card
        contained by the device."
    ::= { ng3GEntry 1 }

ng3gSlotNum OBJECT-TYPE
    SYNTAX     Integer32
    MAX-ACCESS read-only
    STATUS     current
    DESCRIPTION
        "The slot the card is plugged into. Returns -1 if no card is found.
         NOTE: this refers to PCMCIA slots, not USB ports."
    ::= { ng3GEntry 2 }

ng3gModemType OBJECT-TYPE
    SYNTAX     DisplayString
    MAX-ACCESS read-only
    STATUS     current
    DESCRIPTION
        "The modem type."
    ::= { ng3GEntry 3 }

ng3gManufacturer OBJECT-TYPE
    SYNTAX     DisplayString
    MAX-ACCESS read-only
    STATUS     current
    DESCRIPTION
        "The 3G card manufacturer."
    ::= { ng3GEntry 4 }

ng3gModel OBJECT-TYPE
    SYNTAX     DisplayString
    MAX-ACCESS read-only
    STATUS     current
    DESCRIPTION
        "The 3G card model."
    ::= { ng3GEntry 5 }

ng3gRevision OBJECT-TYPE
    SYNTAX     DisplayString
    MAX-ACCESS read-only
    STATUS     current
    DESCRIPTION
        "The 3G card revision."
    ::= { ng3GEntry 6 }

ng3gID OBJECT-TYPE
    SYNTAX     DisplayString
    MAX-ACCESS read-only
    STATUS     current
    DESCRIPTION
        "Either the IMEI or ESN depending on the card."
    ::= { ng3GEntry 7 }

ng3gSignalStrength OBJECT-TYPE
    SYNTAX     Integer32 (0..65535)
    MAX-ACCESS read-only
    STATUS     current
    DESCRIPTION
        "Signal Strength at the connect. This value will 
         remain zero if cellBars is non-zero."
    ::= { ng3GEntry 8 }

ng3gCarrier      OBJECT-TYPE
    SYNTAX     DisplayString
    MAX-ACCESS read-only
    STATUS     current
    DESCRIPTION
        "Information about the carrier."
    ::= { ng3GEntry 9 }

ng3gImsiStatus OBJECT-TYPE
    SYNTAX     DisplayString
    MAX-ACCESS read-only
    STATUS     current
    DESCRIPTION
        "The IMSI attach status."
    ::= { ng3GEntry 10 }

ng3gCellConnNetwork OBJECT-TYPE
    SYNTAX     DisplayString
    MAX-ACCESS read-only
    STATUS     current
    DESCRIPTION
        "The connected network."
    ::= { ng3GEntry 11 }

ng3gPhoneNum OBJECT-TYPE
    SYNTAX     DisplayString
    MAX-ACCESS read-only
    STATUS     current
    DESCRIPTION
        "The cell phone number."
    ::= { ng3GEntry 12 }

ng3gApn OBJECT-TYPE
    SYNTAX     DisplayString
    MAX-ACCESS read-only
    STATUS     current
    DESCRIPTION
        "The access point name."
    ::= { ng3GEntry 13 }

ng3gApnUser OBJECT-TYPE
    SYNTAX     DisplayString
    MAX-ACCESS read-only
    STATUS     current
    DESCRIPTION
        "The APN userid.  Only populated when the access point name exists."
    ::= { ng3GEntry 14 }

ng3gApnPassword OBJECT-TYPE
    SYNTAX     DisplayString
    MAX-ACCESS read-only
    STATUS     current
    DESCRIPTION
        "The APN password.  Only populated when the access point name exists."
    ::= { ng3GEntry 15 }

ng3gCellModemPresent OBJECT-TYPE
    SYNTAX     INTEGER {
      unknown(0),
      present(1),
      missing(2)
    }
    MAX-ACCESS read-only
    STATUS     current
    DESCRIPTION
        "If the cellular modem is a supported unit that allows the AT&T VPN Gateway to
         query its current status then this value will indicate whether or not
         the unit is physically present.  Unsupported units will always have a
         value of 'unknown'."
    ::= { ng3GEntry 16 }

ng3gSIMCardNumber OBJECT-TYPE     
    SYNTAX     DisplayString 
    MAX-ACCESS read-only     
    STATUS     current
    DESCRIPTION
        "The SIM number of the card."
    ::= { ng3GEntry 17 }

ng3gDeviceType OBJECT-TYPE
    SYNTAX     INTEGER {
      unknown(0),
      pcmcia(1),
      usb(2)
    }
    MAX-ACCESS read-only
    STATUS     current
    DESCRIPTION
        "The type of hardware of the cellular modem."
    ::= { ng3GEntry 18 }

cellCollectionTimeDAT OBJECT-TYPE
    SYNTAX      DateAndTime
    MAX-ACCESS  read-only
    STATUS      current
    DESCRIPTION
      "The date and time the cell stats were collected. Not set if
       the date and time on the device hasn't been set yet."
    ::= { ng3GEntry 19 }

cellConnStatus OBJECT-TYPE
    SYNTAX     DisplayString
    MAX-ACCESS read-only
    STATUS     current
    DESCRIPTION
        "The current status of the cellular connection."
    ::= { ng3GEntry 20 }

cellNetworkTech OBJECT-TYPE
    SYNTAX     DisplayString
    MAX-ACCESS read-only
    STATUS     current
    DESCRIPTION
        "Cell network technology."
    ::= { ng3GEntry 21 }

cellCarrier OBJECT-TYPE
    SYNTAX     DisplayString
    MAX-ACCESS read-only
    STATUS     current
    DESCRIPTION
        "Cellular carrier."
    ::= { ng3GEntry 22 }

cellMCC OBJECT-TYPE
    SYNTAX     DisplayString
    MAX-ACCESS read-only
    STATUS     current
    DESCRIPTION
        "A mobile country code (MCC) is used in combination with 
         a mobile network code (MNC) (also known as a MCC / MNC tuple)
         to uniquely identify a mobile phone operator (carrier) using 
         the GSM, UMTS, LTE, and iDEN public land mobile networks as 
         well as some CDMA, TETRA, and satellite mobile networks."
    ::= { ng3GEntry 23 }

cellMNC OBJECT-TYPE
    SYNTAX     DisplayString
    MAX-ACCESS read-only
    STATUS     current
    DESCRIPTION
        "Mobile network code"
    ::= { ng3GEntry 24 }

cellLAC OBJECT-TYPE
    SYNTAX     DisplayString
    MAX-ACCESS read-only
    STATUS     current
    DESCRIPTION
        "Tower location area code."
    ::= { ng3GEntry 25 }

cellCID OBJECT-TYPE
    SYNTAX     DisplayString
    MAX-ACCESS read-only
    STATUS     current
    DESCRIPTION
        "A GSM Cell ID (CID) is a generally unique number used to 
         identify each Base transceiver station (BTS) or sector of 
         a BTS within a Location area code (LAC) if not within a GSM 
         network. In some cases the last digit of CID represents 
         cells' Sector ID. A valid CID ranges from 0 to 65535 on GSM 
         and CDMA networks and from 0 to 268435455 on UMTS and 
         LTE networks."
    ::= { ng3GEntry 26 }

cellBars OBJECT-TYPE
    SYNTAX     Integer32
    MAX-ACCESS read-only
    STATUS     current
    DESCRIPTION
        "A number indicating the signal strength as a bar count. If this value
         is non-zero then ng3gSignalStrength will return zero."
    ::= { ng3GEntry 27 }

cellRSSI OBJECT-TYPE
    SYNTAX     DisplayString
    MAX-ACCESS read-only
    STATUS     current
    DESCRIPTION
        "Received signal strength indicator."
    ::= { ng3GEntry 28 }

cellECIO OBJECT-TYPE
    SYNTAX     DisplayString
    MAX-ACCESS read-only
    STATUS     current
    DESCRIPTION
        "EC/IO measurement."
    ::= { ng3GEntry 29 }

cellRSRP OBJECT-TYPE
    SYNTAX     DisplayString
    MAX-ACCESS read-only
    STATUS     current
    DESCRIPTION
        "References LTE signals: Reference Signal Received Power is the 
         average power of resource elements that carry cellular specific 
         reference signals over the entire bandwidth.
         Valid values : all values are valid. Typical values are 
         between -199 and -85. The larger the number (-85 for instance) 
         the better the signal."
    ::= { ng3GEntry 30 }

cellRSRQ OBJECT-TYPE
    SYNTAX     DisplayString
    MAX-ACCESS read-only
    STATUS     current
    DESCRIPTION
        "References LTE Signals: represents the Cell Quality."
    ::= { ng3GEntry 31 }

cellSINR OBJECT-TYPE
    SYNTAX     DisplayString
    MAX-ACCESS read-only
    STATUS     current
    DESCRIPTION
        "References LTE signals: LTE - The signal-to-interference-plus-noise ratio of the modem."
    ::= { ng3GEntry 32 }

cellSNR OBJECT-TYPE
    SYNTAX     DisplayString
    MAX-ACCESS read-only
    STATUS     current
    DESCRIPTION
        "References LTE signals: The signal-to-noise ratio of the modem."
    ::= { ng3GEntry 33 }

cellIface OBJECT-TYPE
    SYNTAX     DisplayString
    MAX-ACCESS read-only
    STATUS     current
    DESCRIPTION
        "The interface on the device associated with this cell modem."
    ::= { ng3GEntry 34 }

--
-- Tunnel Info
--
ngTunnelTable OBJECT-TYPE
    SYNTAX     SEQUENCE OF NgTunnelEntry
    MAX-ACCESS not-accessible
    STATUS     current
    DESCRIPTION
        "The (conceptual) table of tunnels on the device.
        An entry shall be placed in the storage table for each
        tunnel."
    ::= { ngTunnelInfo 1 }

ngTunnelEntry OBJECT-TYPE
    SYNTAX     NgTunnelEntry
    MAX-ACCESS not-accessible
    STATUS     current
    DESCRIPTION
        "A (conceptual) entry for one logical tunnel area on
        the host."
    INDEX { ngtuIndex }
    ::= { ngTunnelTable 1 }

NgTunnelEntry ::= SEQUENCE {
        ngtuIndex            Integer32,
        ngtuIpsecIface       DisplayString,
        ngtuAuthState        INTEGER,
        ngtuState            INTEGER,
        ngtuDuration         TimeTicks,
        ngtuEndpoint         IpAddress,
        ngtuEndpointType     INTEGER,
        ngtuBulkEncryptMode  INTEGER,
        ngtuCurrEncryptCeIp  IpAddress,
        ngtuEspAlg           DisplayString,
        ngtuAuthAlg          DisplayString,
        ngtuCompressionAlg   DisplayString,
        ngtuAuthType         INTEGER,
        ngtuAuthProt         INTEGER,
        ngtuReasonCode       INTEGER,
        ngtuServerMgmt       INTEGER,
        ngtuTunInitiator     INTEGER,
        ngtuTunMode          INTEGER,
        ngtuIPv6Endpoint     InetAddressIPv6,
        tunCurrAutomation    INTEGER,
        tunInitVpnCon        INTEGER,
        tunInitVpnBkupCon    INTEGER,
        tunConnectionId      DisplayString,
        tunName              DisplayString,
        tunDirection         INTEGER
    }

ngtuIndex OBJECT-TYPE
    SYNTAX     Integer32 (1..65535)
    MAX-ACCESS not-accessible
    STATUS     current
    DESCRIPTION
        "A unique value for each logical tunnel
        contained by the device."
    ::= { ngTunnelEntry 1 }

ngtuIpsecIface OBJECT-TYPE
    SYNTAX     DisplayString
    MAX-ACCESS read-only
    STATUS     current
    DESCRIPTION
        "The ipsec interface associated with the tunnel."
    ::= { ngTunnelEntry 2 }

ngtuAuthState OBJECT-TYPE
    SYNTAX     INTEGER {
     attNotSetYet(0),
     attReset(1),
     attSentLogon(2),
     attRigAuthPending(3),
     attCertLoginPending(4),
     attISAKMPNegPending(5),
     attProtocolNegPending(6),
     attAuthReqAckPending(7),
     attAuthReqPending(8),
     attRunning(9),
     attLogoffPending(10),
     attQuiesed(11),
     attXAuthPending(12),
     attXAuthFailedPendingResp(13),
     attXAuthReqPending(14),
     attDialing(15),
     attDialingDone(16),
     attSASetup(17),
     attXAuthTimeout(18),
     attDialPendingResponse(19),
     attDialRequestingTok(20),
     attRetrySIG(21),
     attTryNextTun(22),
     attModeCfgPending(23),
     attAllTunPingsFailed(24),
     attRigAuthFailedPendingResp(25),
     attRigAuthReqPending(26)
    }
    MAX-ACCESS read-only
    STATUS     current
    DESCRIPTION
        "An internal state used to indicate the tunnel's
	 current operation."
    ::= { ngTunnelEntry 3 }

ngtuState OBJECT-TYPE
    SYNTAX     INTEGER {
      attTunnelDown(0),
      attTunnelComingUp(1),                  
      attTunnelPendingDialConnection(2),
      attTunnelUp(3),
      attTunnelComingDown(4),
      attTunnelRestarting(5)
    }
    MAX-ACCESS read-only
    STATUS     current
    DESCRIPTION
        "An internal state used to indicate the tunnel's
	 status.  This state was created because the 
	 ngtuAuthState can change while the tunnel is still up.
	 For example, when the clock is being set.  This state
	 is always attTunnelUp when the tunnel is up."
    ::= { ngTunnelEntry 4 }

ngtuDuration OBJECT-TYPE
    SYNTAX     TimeTicks
    MAX-ACCESS read-only
    STATUS     current
    DESCRIPTION
        "How long the tunnel has been up."
    ::= { ngTunnelEntry 5 }

ngtuEndpoint OBJECT-TYPE
    SYNTAX     IpAddress
    MAX-ACCESS read-only
    STATUS     current
    DESCRIPTION
        "IP of the endpoint the tunnel is connected to.
	 Populated if the ngtuState is 'up'."
    ::= { ngTunnelEntry 6 }

ngtuEndpointType OBJECT-TYPE
    SYNTAX     INTEGER {
        none(0),
        nortel(3),
        linuxFrameSig(4),
        gig(5),
        linuxSig(6),
        cisco(9),
        vig(20),
        generic(21)
    }
    MAX-ACCESS read-only
    STATUS     current
    DESCRIPTION
        "Type of the endpoint the tunnel is connected to.
	 Populated if the ngtuState is 'up'."
    ::= { ngTunnelEntry 7 }

ngtuBulkEncryptMode OBJECT-TYPE
    SYNTAX     INTEGER {
      disabled(0),
      enabled(1)
    }
    MAX-ACCESS read-only
    STATUS     current
    DESCRIPTION
        "Bulk encryption mode."
    ::= { ngTunnelEntry 8 }

ngtuCurrEncryptCeIp OBJECT-TYPE
    SYNTAX     IpAddress
    MAX-ACCESS read-only
    STATUS     current
    DESCRIPTION
        "Bulk encryption CE address."
    ::= { ngTunnelEntry 9 }

ngtuEspAlg OBJECT-TYPE
    SYNTAX     DisplayString
    MAX-ACCESS read-only
    STATUS     current
    DESCRIPTION
        "ESP algorithm."
    ::= { ngTunnelEntry 10 }

ngtuAuthAlg OBJECT-TYPE
    SYNTAX     DisplayString
    MAX-ACCESS read-only
    STATUS     current
    DESCRIPTION
        "AUTH algorithm."
    ::= { ngTunnelEntry 11 }

ngtuCompressionAlg OBJECT-TYPE
    SYNTAX     DisplayString
    MAX-ACCESS read-only
    STATUS     current
    DESCRIPTION
        "COMPRESSION algorithm."
    ::= { ngTunnelEntry 12 }

ngtuAuthType OBJECT-TYPE
    SYNTAX     INTEGER {
      internetOnly(0),
      serviceManager(1),
      customerDirect(2),
      branchOffice(3),
      customerDirectSm(4),
      noTunnelYet(999)
    }
    MAX-ACCESS read-only
    STATUS     current
    DESCRIPTION
        "Indicates the authentication server that
	 will be used by the tunnel endpoint."
    ::= { ngTunnelEntry 13 }

ngtuAuthProt OBJECT-TYPE
    SYNTAX     INTEGER {
      none(0),
      custRadius(1),
      custSecureID(2),
      custAxent(3),
      custCert(4),
      custLDAP(5),
      custInternal(6),
      branchSharedSecret(7),
      agnsManaged(8)
    }
    MAX-ACCESS read-only
    STATUS     current
    DESCRIPTION
        "The authentication protocol."
    ::= { ngTunnelEntry 14 }

ngtuReasonCode OBJECT-TYPE
    SYNTAX     INTEGER {
      discoButton(0),
      tnlInitiatedDisco(226),
      missedHeartBts(227),
      eth1Lost(258),
      eth1Restored(259),
      powerLost(503),
      tnlAlive(504),
      deviceStatusInactiveWasActive(506),
      noTunnInInetOnlyMode(507),
      tnlIdleTimeout(508),
      dialIdleTimeout(509),
      maxSessionTimeout(510),
      vrrpStateChange(553),
      inbShutdownMsg(555),
      inbLostKeepalives(562),
      inbIdleTimeout(563),
      inbIpsecSaDelMsgFromClient(564),
      inbIsakmpDelMsgFromClient(565),
      noReasonGiven(599)
    }
    MAX-ACCESS read-only
    STATUS     current
    DESCRIPTION
        "A numeric value that indicates why an inbound or
         outbound tunnel came down. 
         The one exception is tnlAlive, which is sent for the
         tunnel 'alive' message for a tunnel that is still up."
    ::= { ngTunnelEntry 15 }

ngtuServerMgmt OBJECT-TYPE
    SYNTAX     INTEGER {
      nonAgnsManaged(0),
      agnsManaged(1)
    }
    MAX-ACCESS read-only
    STATUS     current
    DESCRIPTION
        "AGNS managed or not."
    ::= { ngTunnelEntry 16 }

ngtuTunInitiator OBJECT-TYPE
    SYNTAX     INTEGER {
      attUnknown(0),
      attFromUser(1),
      attAutoLogon(2),
      attPersistentLogon(3),
      attVpnctl(4)
    }
    MAX-ACCESS read-only
    STATUS     current
    DESCRIPTION
        "What initiated the tunnel."
    ::= { ngTunnelEntry 17 }

ngtuTunMode OBJECT-TYPE
    SYNTAX     INTEGER {
      tunnelUnknown(0),
      tunnelUserControl(1),
      tunnelUserViewOnly(2),
      tunnelHidden(3),
      tunnelMaintenance(4),
      tunnelWSSInternet(5)
    }
    MAX-ACCESS read-only
    STATUS     current
    DESCRIPTION
        "The tunnel control mode."
    ::= { ngTunnelEntry 18 }

ngtuIPv6Endpoint OBJECT-TYPE
    SYNTAX     InetAddressIPv6
    MAX-ACCESS read-only
    STATUS     current
    DESCRIPTION
        "IPv6 IP of the endpoint the tunnel is connected to.
         Populated if the ngtuState is 'up' and IPv6 is in use."
    ::= { ngTunnelEntry 19 }

tunCurrAutomation OBJECT-TYPE
    SYNTAX     INTEGER {
      tunCurNone(0),
      tunCurUserInit(1),
      tunCurTrafficInitActive(2),
      tunCurTrafficInitNotActive(3),
      tunCurPersistentActive(4),
      tunCurPersistentNotActive(5),
      tunCurVrrpActive(6),
      tunCurVrrpActiveNotMaster(7),
      tunCurVrrpNotActive(8)
    }
    MAX-ACCESS read-only
    STATUS     current
    DESCRIPTION
        "The tunnel automation that is currently in use and
         whether or not it is currently active.
         NOTE: Active does not necessarily mean that the tunnel
         is up. It could mean that the tunnel is up, in the 
         process of coming up, or is in a state where it will
         be brought up if the right conditions are met. There
         is no automation for User Initiated mode."
    ::= { ngTunnelEntry 20 }

tunInitVpnCon OBJECT-TYPE
    SYNTAX     INTEGER {
      tunInitNotSet(-1),
      tunInitNeverConnected(0),
      tunInitUserInitiated(1),
      tunInitTrafficInitiated(2),
      tunInitPersistent(3),
      tunInitVrrp(4),
      tunInitUserOverridePersist(5),
      tunInitUserOverrideTraffic(6),
      tunInitUnknown(7)
    }
    MAX-ACCESS read-only
    STATUS     current
    DESCRIPTION
        "The tunnel automation (if any) configured for the
         primary connection in Service Manager. If configured
         for User Initiated the user can choose to override
         that setting from the CGI interface and select
         Persistent or Traffic Initiated instead."
    ::= { ngTunnelEntry 21 }

tunInitVpnBkupCon OBJECT-TYPE
    SYNTAX     INTEGER {
      tunInitNotSet(-1),
      tunInitNeverConnected(0),
      tunInitUserInitiated(1),
      tunInitTrafficInitiated(2),
      tunInitPersistent(3),
      tunInitVrrp(4),
      tunInitUserOverridePersist(5),
      tunInitUserOverrideTraffic(6),
      tunInitUnknown(7)
    }
    MAX-ACCESS read-only
    STATUS     current
    DESCRIPTION
        "Similar to tunInitVpnCon except that this controls
         tunnel automation via the backup connection."
    ::= { ngTunnelEntry 22 }

tunConnectionId   OBJECT-TYPE
    SYNTAX      DisplayString
    MAX-ACCESS  accessible-for-notify
    STATUS      current
    DESCRIPTION
      "The tunnel connection ID is a unique value assigned to each instance of a tunnel.
       It is used to associate the tunnel up, tunnel alive, and tunnel down traps together.
       When a tunnel goes down and is then re-established it will be assigned a new
       tunnel connection ID.

       This is the same value reported by ngevTunConnectionId in traps."
    ::= { ngTunnelEntry 23 }

tunName   OBJECT-TYPE
    SYNTAX      DisplayString
    MAX-ACCESS  accessible-for-notify
    STATUS      current
    DESCRIPTION
      "The name associated with this tunnel. Note that the name will be 'settings'
       if multi-tunnel is disabled."
    ::= { ngTunnelEntry 24 }

tunDirection OBJECT-TYPE
    SYNTAX     INTEGER {
      tunnelUnknown(0),
      tunnelInbound(1),
      tunnelOutbound(2)
    }
    MAX-ACCESS read-only
    STATUS     current
    DESCRIPTION
        "Indicates whether this is an inbound or outbound tunnel."
    ::= { ngTunnelEntry 25 }

--
-- COS Info
--
ngcoEnabled OBJECT-TYPE
    SYNTAX  INTEGER {
      notActive(0),
      activeWithDscpRemarking(1),
      activeWithoutDscpRemarking(2)
    }
    MAX-ACCESS  read-only
    STATUS      current
    DESCRIPTION
      "Indicates if COS is enabled or not. As of version 6.2 bandwidth
       testing can be active without COS being enabled. When that 
       happens ngcoEnabled will return zero (notActive) but 
       ngcoNextTestTimeDAT will not return January 1 year 0 time 0 
       for the time."
    ::= { ngCosInfo 1 }

ngcoNextTestTime OBJECT-TYPE
    SYNTAX  DisplayString
    MAX-ACCESS  read-only
    STATUS      current
    DESCRIPTION
      "When the next bandwidth test is scheduled to run.
       MM/DD/YYYY HH:MM:SS. Returns '00/00/0000 00:00:00'
       when no test is scheduled.
       The time returned is the local time on the AT&T VPN Gateway.  To determine 
       how the AT&T VPN Gateway's local time relates to UTC view the following OIDs:
       nghwUtcOffset (current UTC offset), nghwDstAllowed (daylight saving time allowed),
       nghwDstActive (daylight savings time active).
       NOTE: This entry is made obsolete by ngcoNextTestTimeDAT."
    ::= { ngCosInfo 2 }

ngcoWanMtu OBJECT-TYPE
    SYNTAX      Integer32 (0..65535)
    MAX-ACCESS  read-only
    STATUS      current
    DESCRIPTION
      "Current WAN interface MTU value."
    ::= { ngCosInfo 3 }

ngcoCurUpstreamBandw OBJECT-TYPE
    SYNTAX  Unsigned32
    MAX-ACCESS  read-only
    STATUS      current
    DESCRIPTION
      "Current upstream bandwidth high water mark in use."
    ::= { ngCosInfo 4 }

ngcoCurDownstreamBandw OBJECT-TYPE
    SYNTAX  Unsigned32
    MAX-ACCESS  read-only
    STATUS      current
    DESCRIPTION
      "Current downstream bandwidth high water mark in use."
    ::= { ngCosInfo 5 }

ngcoNextTestTimeDAT OBJECT-TYPE
    SYNTAX      DateAndTime
    MAX-ACCESS  read-only
    STATUS      current
    DESCRIPTION
      "When the next bandwidth test is scheduled to run.
       Returns January 1 year 0 time 0 when no test is scheduled.
       NOTE: This entry replaces ngcoNextTestTime."
    ::= { ngCosInfo 6 }

ngcoLastTestTimeDAT OBJECT-TYPE
    SYNTAX      DateAndTime
    MAX-ACCESS  read-only
    STATUS      current
    DESCRIPTION
      "The date and time of when the last bandwidth test was performed.
       NOTE: The date and time of high water marks retained after a reboot
       will return January 1 year 0 time 0 for the time."
    ::= { ngCosInfo 7 }

ngcoLastUpstreamResult OBJECT-TYPE
    SYNTAX      Unsigned32
    MAX-ACCESS  read-only
    STATUS      current
    DESCRIPTION 
      "The upstream bandwidth measured when the last bandwidth test was performed."
    ::= { ngCosInfo 8 }

ngcoLastDownstreamResult OBJECT-TYPE
    SYNTAX      Unsigned32
    MAX-ACCESS  read-only
    STATUS      current
    DESCRIPTION
      "The downstream bandwidth measured when the last bandwidth test was performed."
    ::= { ngCosInfo 9 }

--
-- compliance statements
--
ngBasicComplianceRev MODULE-COMPLIANCE
    STATUS  current
    DESCRIPTION
            "The compliance statement for AT&T VPN Gateway entities 
             which implement this MIB module."
    MODULE  -- this module
        MANDATORY-GROUPS { nghwGroup, ngifGroup, ngvlGroup,
                           ngvrGroup, ng3gGroup, ngtuGroup,
                           ngcoGroup, ngfwGroup, ngrmGroup,
                           ngdiGroup, ngdhlGroup, ngCapPorGroup,
                           attInbTunGroup, attInbTunNetGroup
                         }
    ::= { ngMIBCompliances 1 }

--
-- Groups
--
nghwGroup   OBJECT-GROUP
    OBJECTS { nghwHardwareVersion, nghwCodeVersion, nghwAccount,
              nghwUtcOffset, nghwDstAllowed, nghwDstActive,
              nghwWanConnectionMethod, nghwHostname,
              nghwDeviceStatus, nghwLanguage,
              ngdnServer, ngcuCustComment, 
              ngpoStatus, ngdnIPv6Server,
              nghwCurrentWanConnectionMethod,
              nghwIPv6WanConnectionMethod,
              nghwIPv6CurrentWanConnectionMethod,
              nghwLastFullQueryTimeDAT,
              nghwLastAnyQueryTimeDAT,
              nghwLastUpgradeTimeDAT, hwMac, hwRollbackVersion,
              hwDualWan, hwWan2ConnectionMethod, 
              hwIPv6Wan2ConnectionMethod,
              hwWan1GwayMac, hwWan2Mac, hwWan2GwayMac
            }
    STATUS  current
    DESCRIPTION
            "The hardware group."
    ::= { ngMIBGroups 1 }

ngifGroup   OBJECT-GROUP
    OBJECTS { ngifActiveWanIface, ngifTotalBytesIn, ngifTotalBytesOut,
              ngifTimeInDial, ifTimeInBackup, ifStatsifDescr, 
              ifStatsifIndex, ifStatsRxCrcErr, ifInterfaceFormat, 
              ifCircuitSpeed }
    STATUS  current
    DESCRIPTION
            "The interface group."
    ::= { ngMIBGroups 2 }

ngvlGroup   OBJECT-GROUP
    OBJECTS { ngvlId, ngvlPorts, ngvlSpeed, ngvlIpRange,
              ngvlDhcpRelayAddr, ngvlDhcpDefRoute, ngvlLanAddr,
              ngvlLanSubAddr, ngvlIPv6IpRangeStart, ngvlIPv6IpRangeEnd,
              ngvlIPv6DhcpRelayAddrPri, ngvlIPv6DhcpRelayAddrBak,
              ngvlIPv6LanAddr, ngvlIPv6LanPrefix, ngvlSpeedCurrent
            }
    STATUS  current
    DESCRIPTION
            "The VLAN group."
    ::= { ngMIBGroups 3 }

ngvrGroup   OBJECT-GROUP
    OBJECTS { ngvrIface, ngvrId, ngvrMasterStatus,
              ngvrPriority }
    STATUS  current
    DESCRIPTION
            "The VRRP group."
    ::= { ngMIBGroups 4 }

ng3gGroup   OBJECT-GROUP
    OBJECTS { ng3gSlotNum, ng3gModemType, ng3gManufacturer,
              ng3gModel, ng3gRevision, ng3gID, ng3gSignalStrength,
              ng3gCarrier, ng3gImsiStatus, ng3gCellConnNetwork,
              ng3gPhoneNum, ng3gApn, ng3gApnUser, ng3gApnPassword,
              ng3gCellModemPresent, ng3gSIMCardNumber, ng3gDeviceType,
              cellCollectionTimeDAT, cellConnStatus, cellNetworkTech,
              cellCarrier, cellMCC, cellMNC, cellLAC, cellCID,
              cellBars, cellRSSI, cellECIO, cellRSRP, cellRSRQ,
              cellSINR, cellSNR, cellIface
            }
    STATUS  current
    DESCRIPTION
            "The 3G group."
    ::= { ngMIBGroups 5 }

ngtuGroup   OBJECT-GROUP
    OBJECTS { ngtuIpsecIface, ngtuAuthState, ngtuState,
              ngtuDuration, ngtuEndpoint, ngtuEndpointType,
              ngtuBulkEncryptMode, ngtuCurrEncryptCeIp,
              ngtuEspAlg, ngtuAuthAlg, ngtuCompressionAlg,
              ngtuAuthType, ngtuAuthProt, ngtuReasonCode,
              ngtuServerMgmt, ngtuTunInitiator, ngtuTunMode,
              ngtuIPv6Endpoint, tunCurrAutomation,
              tunInitVpnCon, tunInitVpnBkupCon,
              tunConnectionId, tunName, tunDirection
            }
    STATUS  current
    DESCRIPTION
            "The tunnel group."
    ::= { ngMIBGroups 6 }

ngcoGroup   OBJECT-GROUP
    OBJECTS { ngcoEnabled, ngcoNextTestTime, ngcoWanMtu,
              ngcoCurUpstreamBandw, ngcoCurDownstreamBandw,
	      ngcoNextTestTimeDAT, ngcoLastDownstreamResult,
              ngcoLastUpstreamResult, ngcoLastTestTimeDAT
            }
    STATUS  current
    DESCRIPTION
            "The COS group."
    ::= { ngMIBGroups 7 }

ngfwGroup   OBJECT-GROUP
    OBJECTS {
              ngfwTableName, ngfwTableNumberOfChains,
              ngfwChainTableIndex, ngfwChainName,
              ngfwChainsNumberOfRules, ngfwRuleTableIndex,
              ngfwRuleChainIndex, ngfwRulePackets, ngfwRuleBytes,
              ngfwRuleTarget, ngfwRuleProtocol, ngfwRuleInIface,
              ngfwRuleOutIface, ngfwRuleSrcIp, ngfwRuleSrcMask,
              ngfwRuleDstIp, ngfwRuleDstMask, ngfwRuleMisc,
              ngfwIpConntrackNumEntries, ngfwIpConntrackMaxNumEntries,
              ngfwIPv6RuleSrcIp, ngfwIPv6RuleSrcMask,
              ngfwIPv6RuleDstIp, ngfwIPv6RuleDstMask,
              ngfwIPv6TableName, ngfwIPv6TableNumberOfChains,
              ngfwIPv6ChainTableIndex, ngfwIPv6ChainName,
              ngfwIPv6ChainsNumberOfRules, ngfwIPv6RuleTableIndex,
              ngfwIPv6RuleChainIndex, ngfwIPv6RulePackets, ngfwIPv6RuleBytes,
              ngfwIPv6RuleTarget, ngfwIPv6RuleProtocol, ngfwIPv6RuleInIface,
              ngfwIPv6RuleOutIface, ngfwIPv6RuleMisc
            }
    STATUS  current
    DESCRIPTION
            "The firewall group."
    ::= { ngMIBGroups 8 }

ngrmGroup   OBJECT-GROUP
    OBJECTS { ngRogueMacStatus, ngrmMac, ngrmTimestamp,
              ngrmIface, ngrmTimestampDAT }
    STATUS  current
    DESCRIPTION
            "The Rogue MAC group."
    ::= { ngMIBGroups 9 }

ngdiGroup   OBJECT-GROUP
    OBJECTS { ngdiPhoneNum, ngdiLastTestResult, ngdiLastTestCompleteTime,
              ngdiDialTestFailCategory, ngdiDialTestFailReason,
	      ngdiLastTestCompleteTimeDAT, ngdiSecondaryPhoneNum }
    STATUS  current
    DESCRIPTION
            "The dial group."
    ::= { ngMIBGroups 10 }

ngdhlGroup   OBJECT-GROUP
    OBJECTS { ngdhlLeaseAddr, ngdhlMac, ngdhlHostname, ngdhlPort,
              ngdhlVlanId }
    STATUS  current
    DESCRIPTION
            "The DHCP leases group."
    ::= { ngMIBGroups 11 }

ngCapPorGroup   OBJECT-GROUP
    OBJECTS { ngcpAddr, ngcpMac, ngcpUser, ngcpDuration,
              ngcpMaxDuration, ngcpState, ngcpIdle, ngcpMaxIdle,
              ngcpPort, ngcpVlanId }
    STATUS  current
    DESCRIPTION
            "The Captive Portal group."
    ::= { ngMIBGroups 12 }

attInbTunGroup OBJECT-GROUP
    OBJECTS {
              inbTunClientTransAddr, inbTunLocalIpsecIface,
              inbTunType, inbTunUserid, inbTunSrvConfigProf,
              inbTunTimeEstablished, inbTunDuration, inbTunIdleTimeout,
              inbTunCurrIdleTimeout, inbTunNegIkePhase1Lifet,
              inbTunNatTNegotiated, inbTunActClientSaNeg
            }
    STATUS  current
    DESCRIPTION
            "The Inbound Tunnel group."
    ::= { ngMIBGroups 13 }

attInbTunNetGroup OBJECT-GROUP
    OBJECTS { 
              inbTunNetNetwork, inbTunNetTimeEstablished,
              inbTunNetNegIkePhase2Lifet, inbTunNetEspAlgorithm,
              inbTunNetCompression, inbTunNetClientTransAddr
            }
    STATUS  current
    DESCRIPTION
            "The Inbound Tunnel Network group."
    ::= { ngMIBGroups 14 }

--
-- Firewall Table Info
--
ngFirewallTable OBJECT-TYPE
    SYNTAX     SEQUENCE OF NgFirewallTableEntry
    MAX-ACCESS not-accessible
    STATUS     current
    DESCRIPTION
        "The (conceptual) table of firewall tables on the device.
        An entry shall be placed in the storage table for each
        table."
    ::= { ngFirewallInfo 1 }

ngFirewallTableEntry OBJECT-TYPE
    SYNTAX     NgFirewallTableEntry
    MAX-ACCESS not-accessible
    STATUS     current
    DESCRIPTION
        "A (conceptual) entry for one logical firewall table area on
        the host."
    INDEX { ngfwTableIndex }
    ::= { ngFirewallTable 1 }

NgFirewallTableEntry ::= SEQUENCE {
        ngfwTableIndex            Integer32,
        ngfwTableName             DisplayString,
        ngfwTableNumberOfChains   Integer32
    }

ngfwTableIndex OBJECT-TYPE
    SYNTAX     Integer32 (1..65535)
    MAX-ACCESS not-accessible
    STATUS     current
    DESCRIPTION
        "A unique value for each logical firewall table
        contained by the device."
    ::= { ngFirewallTableEntry 1 }

ngfwTableName OBJECT-TYPE
    SYNTAX  DisplayString
    MAX-ACCESS  read-only
    STATUS      current
    DESCRIPTION
      "The name of this table."
    ::= { ngFirewallTableEntry 2 }

ngfwTableNumberOfChains OBJECT-TYPE
    SYNTAX     Integer32 (1..65535)
    MAX-ACCESS read-only
    STATUS     current
    DESCRIPTION
        "The number of chains in this particular table."
    ::= { ngFirewallTableEntry 3 }

--
-- Firewall Chains Info
--
ngFirewallChainTable OBJECT-TYPE
    SYNTAX     SEQUENCE OF NgFirewallChainEntry
    MAX-ACCESS not-accessible
    STATUS     current
    DESCRIPTION
        "The (conceptual) chain of firewall chains on the device.
        An entry shall be placed in the storage chain for each
        chain."
    ::= { ngFirewallInfo 2 }

ngFirewallChainEntry OBJECT-TYPE
    SYNTAX     NgFirewallChainEntry
    MAX-ACCESS not-accessible
    STATUS     current
    DESCRIPTION
        "A (conceptual) entry for one logical firewall chain area on
        the host."
    INDEX { ngfwChainIndex }
    ::= { ngFirewallChainTable 1 }

NgFirewallChainEntry ::= SEQUENCE {
        ngfwChainIndex             Integer32,
        ngfwChainTableIndex        Integer32,
        ngfwChainName              DisplayString,
        ngfwChainsNumberOfRules    Integer32
    }

ngfwChainIndex OBJECT-TYPE
    SYNTAX     Integer32 (1..65535)
    MAX-ACCESS not-accessible
    STATUS     current
    DESCRIPTION
        "A unique value for each logical firewall chain
        contained by the device."
    ::= { ngFirewallChainEntry 1 }

ngfwChainTableIndex OBJECT-TYPE
    SYNTAX     Integer32 (1..65535)
    MAX-ACCESS read-only
    STATUS     current
    DESCRIPTION
        "Shows what table this chain belongs to.  Corresponds
         to ngfwTableIndex in ngFirewallTable."
    ::= { ngFirewallChainEntry 2 }

ngfwChainName OBJECT-TYPE
    SYNTAX  DisplayString
    MAX-ACCESS  read-only
    STATUS      current
    DESCRIPTION
      "The name of this chain."
    ::= { ngFirewallChainEntry 3 }

ngfwChainsNumberOfRules  OBJECT-TYPE
    SYNTAX     Integer32 (1..65535)
    MAX-ACCESS read-only
    STATUS     current
    DESCRIPTION
        "The number of rules in this particular chain."
    ::= { ngFirewallChainEntry 4 }

--
-- Firewall Rules Info
--
ngFirewallRuleTable OBJECT-TYPE
    SYNTAX     SEQUENCE OF NgFirewallRuleEntry
    MAX-ACCESS not-accessible
    STATUS     current
    DESCRIPTION
        "The (conceptual) table of firewall rules on the device.
        An entry shall be placed in the storage rule for each
        rule."
    ::= { ngFirewallInfo 3 }

ngFirewallRuleEntry OBJECT-TYPE
    SYNTAX     NgFirewallRuleEntry
    MAX-ACCESS not-accessible
    STATUS     current
    DESCRIPTION
        "A (conceptual) entry for one logical firewall rule area on
        the host."
    INDEX { ngfwRuleIndex }
    ::= { ngFirewallRuleTable 1 }

NgFirewallRuleEntry ::= SEQUENCE {
        ngfwRuleIndex             Integer32,
        ngfwRuleTableIndex        Integer32,
        ngfwRuleChainIndex        Integer32,
        ngfwRulePackets           Unsigned32,
        ngfwRuleBytes             Unsigned32,
        ngfwRuleTarget            DisplayString,
        ngfwRuleProtocol          DisplayString,
        ngfwRuleInIface           DisplayString,
        ngfwRuleOutIface          DisplayString,
        ngfwRuleSrcIp             IpAddress,
        ngfwRuleSrcMask           Integer32,
        ngfwRuleDstIp             IpAddress,
        ngfwRuleDstMask           Integer32,
        ngfwRuleMisc              DisplayString
    }

ngfwRuleIndex OBJECT-TYPE
    SYNTAX     Integer32 (1..65535)
    MAX-ACCESS not-accessible
    STATUS     current
    DESCRIPTION
        "A unique value for each logical firewall rule
        contained by the device."
    ::= { ngFirewallRuleEntry 1 }

ngfwRuleTableIndex OBJECT-TYPE
    SYNTAX     Integer32 (1..65535)
    MAX-ACCESS read-only
    STATUS     current
    DESCRIPTION
        "Shows what table this rule belongs to.  Corresponds
         to ngfwTableIndex in ngFirewallTable."
    ::= { ngFirewallRuleEntry 2 }

ngfwRuleChainIndex OBJECT-TYPE
    SYNTAX     Integer32 (1..65535)
    MAX-ACCESS read-only
    STATUS     current
    DESCRIPTION
        "Shows what chain this rule belongs to.  Corresponds  
         to ngfwChainIndex in ngFirewallChainTable."
    ::= { ngFirewallRuleEntry 3 }

ngfwRulePackets OBJECT-TYPE
    SYNTAX      Unsigned32
    MAX-ACCESS  read-only
    STATUS      current
    DESCRIPTION
      "Total packets for this rule."
    ::= { ngFirewallRuleEntry 4 }

ngfwRuleBytes OBJECT-TYPE
    SYNTAX      Unsigned32
    MAX-ACCESS  read-only
    STATUS      current
    DESCRIPTION
      "Total bytes for this rule."
    ::= { ngFirewallRuleEntry 5 }

ngfwRuleTarget OBJECT-TYPE
    SYNTAX      DisplayString
    MAX-ACCESS  read-only
    STATUS      current
    DESCRIPTION
      "The rule target."
    ::= { ngFirewallRuleEntry 6 }

ngfwRuleProtocol OBJECT-TYPE
    SYNTAX      DisplayString
    MAX-ACCESS  read-only
    STATUS      current
    DESCRIPTION
      "The rule protocol."
    ::= { ngFirewallRuleEntry 7 }

ngfwRuleInIface OBJECT-TYPE
    SYNTAX      DisplayString
    MAX-ACCESS  read-only
    STATUS      current
    DESCRIPTION
      "The rule input interface."
    ::= { ngFirewallRuleEntry 8 }

ngfwRuleOutIface OBJECT-TYPE
    SYNTAX      DisplayString
    MAX-ACCESS  read-only
    STATUS      current
    DESCRIPTION
      "The rule output interface."
    ::= { ngFirewallRuleEntry 9 }

ngfwRuleSrcIp OBJECT-TYPE
    SYNTAX     IpAddress
    MAX-ACCESS read-only
    STATUS     current
    DESCRIPTION
        "The rule source IP."
    ::= { ngFirewallRuleEntry 10 }

ngfwRuleSrcMask OBJECT-TYPE
    SYNTAX     Integer32 (0..65535)
    MAX-ACCESS read-only
    STATUS     current
    DESCRIPTION
        "The rule source mask in CIDR-compliant format."
    ::= { ngFirewallRuleEntry 11 }

ngfwRuleDstIp OBJECT-TYPE
    SYNTAX     IpAddress
    MAX-ACCESS read-only
    STATUS     current
    DESCRIPTION
        "The rule destination IP."
    ::= { ngFirewallRuleEntry 12 }

ngfwRuleDstMask OBJECT-TYPE
    SYNTAX     Integer32 (0..65535)
    MAX-ACCESS read-only
    STATUS     current
    DESCRIPTION
        "The rule destination mask in CIDR-compliant format."
    ::= { ngFirewallRuleEntry 13 }

ngfwRuleMisc OBJECT-TYPE
    SYNTAX      DisplayString
    MAX-ACCESS  read-only
    STATUS      current
    DESCRIPTION
      "The rule MISC section."
    ::= { ngFirewallRuleEntry 14 }

--
-- 
--

ngfwIpConntrackNumEntries  OBJECT-TYPE
    SYNTAX     Integer32 (0..65535)
    MAX-ACCESS read-only
    STATUS     current
    DESCRIPTION
        "The number entries in the ip_conntrack file."
    ::= { ngFirewallInfo 4 }

ngfwIpConntrackMaxNumEntries  OBJECT-TYPE
    SYNTAX     Integer32 (0..65535)
    MAX-ACCESS read-only
    STATUS     current
    DESCRIPTION
        "The maximum number of entries in the ip_conntrack file."
    ::= { ngFirewallInfo 5 }

--
-- Start IPv6 Firewall Info
--
ngIPv6FirewallTable OBJECT-TYPE
    SYNTAX     SEQUENCE OF NgIPv6FirewallTableEntry
    MAX-ACCESS not-accessible
    STATUS     current
    DESCRIPTION
        "The (conceptual) table of IPv6 firewall tables on the device.
        An entry shall be placed in the storage table for each
        table."
    ::= { ngFirewallInfo 6 }

ngIPv6FirewallTableEntry OBJECT-TYPE
    SYNTAX     NgIPv6FirewallTableEntry
    MAX-ACCESS not-accessible
    STATUS     current
    DESCRIPTION
        "A (conceptual) entry for one logical IPv6 firewall table area on
        the host."
    INDEX { ngfwIPv6TableIndex }
    ::= { ngIPv6FirewallTable 1 }

NgIPv6FirewallTableEntry ::= SEQUENCE {
        ngfwIPv6TableIndex            Integer32,
        ngfwIPv6TableName             DisplayString,
        ngfwIPv6TableNumberOfChains   Integer32
    }

ngfwIPv6TableIndex OBJECT-TYPE
    SYNTAX     Integer32 (1..65535)
    MAX-ACCESS not-accessible
    STATUS     current
    DESCRIPTION
        "A unique value for each logical IPv6 firewall table
        contained by the device."
    ::= { ngIPv6FirewallTableEntry 1 }

ngfwIPv6TableName OBJECT-TYPE
    SYNTAX  DisplayString
    MAX-ACCESS  read-only
    STATUS      current
    DESCRIPTION
      "The name of this table."
    ::= { ngIPv6FirewallTableEntry 2 }

ngfwIPv6TableNumberOfChains OBJECT-TYPE
    SYNTAX     Integer32 (1..65535)
    MAX-ACCESS read-only
    STATUS     current
    DESCRIPTION
        "The number of chains in this particular table."
    ::= { ngIPv6FirewallTableEntry 3 }

--
-- IPv6 Firewall Chains Info
--
ngIPv6FirewallChainTable OBJECT-TYPE
    SYNTAX     SEQUENCE OF NgIPv6FirewallChainEntry
    MAX-ACCESS not-accessible
    STATUS     current
    DESCRIPTION
        "The (conceptual) chain of IPv6 firewall chains on the device.
        An entry shall be placed in the storage chain for each
        chain."
    ::= { ngFirewallInfo 7 }

ngIPv6FirewallChainEntry OBJECT-TYPE
    SYNTAX     NgIPv6FirewallChainEntry
    MAX-ACCESS not-accessible
    STATUS     current
    DESCRIPTION
        "A (conceptual) entry for one logical IPv6 firewall chain area on
        the host."
    INDEX { ngfwIPv6ChainIndex }
    ::= { ngIPv6FirewallChainTable 1 }

NgIPv6FirewallChainEntry ::= SEQUENCE {
        ngfwIPv6ChainIndex             Integer32,
        ngfwIPv6ChainTableIndex        Integer32,
        ngfwIPv6ChainName              DisplayString,
        ngfwIPv6ChainsNumberOfRules    Integer32
    }

ngfwIPv6ChainIndex OBJECT-TYPE
    SYNTAX     Integer32 (1..65535)
    MAX-ACCESS not-accessible
    STATUS     current
    DESCRIPTION
        "A unique value for each logical IPv6 firewall chain
        contained by the device."
    ::= { ngIPv6FirewallChainEntry 1 }

ngfwIPv6ChainTableIndex OBJECT-TYPE
    SYNTAX     Integer32 (1..65535)
    MAX-ACCESS read-only
    STATUS     current
    DESCRIPTION
        "Shows what table this chain belongs to.  Corresponds
         to ngfwIPv6TableIndex in ngIPv6FirewallTable."
    ::= { ngIPv6FirewallChainEntry 2 }

ngfwIPv6ChainName OBJECT-TYPE
    SYNTAX  DisplayString
    MAX-ACCESS  read-only
    STATUS      current
    DESCRIPTION
      "The name of this chain."
    ::= { ngIPv6FirewallChainEntry 3 }

ngfwIPv6ChainsNumberOfRules  OBJECT-TYPE
    SYNTAX     Integer32 (1..65535)
    MAX-ACCESS read-only
    STATUS     current
    DESCRIPTION
        "The number of rules in this particular chain."
    ::= { ngIPv6FirewallChainEntry 4 }

--
-- IPv6 Firewall Rules Info
--
ngIPv6FirewallRuleTable OBJECT-TYPE
    SYNTAX     SEQUENCE OF NgIPv6FirewallRuleEntry
    MAX-ACCESS not-accessible
    STATUS     current
    DESCRIPTION
        "The (conceptual) table of IPv6 firewall rules on the device.
        An entry shall be placed in the storage rule for each
        rule."
    ::= { ngFirewallInfo 8 }

ngIPv6FirewallRuleEntry OBJECT-TYPE
    SYNTAX     NgIPv6FirewallRuleEntry
    MAX-ACCESS not-accessible
    STATUS     current
    DESCRIPTION
        "A (conceptual) entry for one logical IPv6 firewall rule area on
        the host."
    INDEX { ngfwIPv6RuleIndex }
    ::= { ngIPv6FirewallRuleTable 1 }

NgIPv6FirewallRuleEntry ::= SEQUENCE {
        ngfwIPv6RuleIndex             Integer32,
        ngfwIPv6RuleTableIndex        Integer32,
        ngfwIPv6RuleChainIndex        Integer32,
        ngfwIPv6RulePackets           Unsigned32,
        ngfwIPv6RuleBytes             Unsigned32,
        ngfwIPv6RuleTarget            DisplayString,
        ngfwIPv6RuleProtocol          DisplayString,
        ngfwIPv6RuleInIface           DisplayString,
        ngfwIPv6RuleOutIface          DisplayString,
        ngfwIPv6RuleSrcIp             InetAddressIPv6,
        ngfwIPv6RuleSrcMask           Integer32,
        ngfwIPv6RuleDstIp             InetAddressIPv6,
        ngfwIPv6RuleDstMask           Integer32,
        ngfwIPv6RuleMisc              DisplayString
    }

ngfwIPv6RuleIndex OBJECT-TYPE
    SYNTAX     Integer32 (1..65535)
    MAX-ACCESS not-accessible
    STATUS     current
    DESCRIPTION
        "A unique value for each logical IPv6 firewall rule
        contained by the device."
    ::= { ngIPv6FirewallRuleEntry 1 }

ngfwIPv6RuleTableIndex OBJECT-TYPE
    SYNTAX     Integer32 (1..65535)
    MAX-ACCESS read-only
    STATUS     current
    DESCRIPTION
        "Shows what table this rule belongs to.  Corresponds
         to ngfwIPv6TableIndex in ngIPv6FirewallTable."
    ::= { ngIPv6FirewallRuleEntry 2 }

ngfwIPv6RuleChainIndex OBJECT-TYPE
    SYNTAX     Integer32 (1..65535)
    MAX-ACCESS read-only
    STATUS     current
    DESCRIPTION
        "Shows what chain this rule belongs to.  Corresponds  
         to ngfwIPv6ChainIndex in ngIPv6FirewallChainTable."
    ::= { ngIPv6FirewallRuleEntry 3 }

ngfwIPv6RulePackets OBJECT-TYPE
    SYNTAX      Unsigned32
    MAX-ACCESS  read-only
    STATUS      current
    DESCRIPTION
      "Total packets for this rule."
    ::= { ngIPv6FirewallRuleEntry 4 }

ngfwIPv6RuleBytes OBJECT-TYPE
    SYNTAX      Unsigned32
    MAX-ACCESS  read-only
    STATUS      current
    DESCRIPTION
      "Total bytes for this rule."
    ::= { ngIPv6FirewallRuleEntry 5 }

ngfwIPv6RuleTarget OBJECT-TYPE
    SYNTAX      DisplayString
    MAX-ACCESS  read-only
    STATUS      current
    DESCRIPTION
      "The rule target."
    ::= { ngIPv6FirewallRuleEntry 6 }

ngfwIPv6RuleProtocol OBJECT-TYPE
    SYNTAX      DisplayString
    MAX-ACCESS  read-only
    STATUS      current
    DESCRIPTION
      "The rule protocol."
    ::= { ngIPv6FirewallRuleEntry 7 }

ngfwIPv6RuleInIface OBJECT-TYPE
    SYNTAX      DisplayString
    MAX-ACCESS  read-only
    STATUS      current
    DESCRIPTION
      "The rule input interface."
    ::= { ngIPv6FirewallRuleEntry 8 }

ngfwIPv6RuleOutIface OBJECT-TYPE
    SYNTAX      DisplayString
    MAX-ACCESS  read-only
    STATUS      current
    DESCRIPTION
      "The rule output interface."
    ::= { ngIPv6FirewallRuleEntry 9 }

ngfwIPv6RuleSrcIp OBJECT-TYPE
    SYNTAX      InetAddressIPv6
    MAX-ACCESS  accessible-for-notify
    STATUS      current
    DESCRIPTION
        "The rule source IP. Not used and set to all zeroes for IPv4 firewall output."
    ::= { ngIPv6FirewallRuleEntry 10 }

ngfwIPv6RuleSrcMask OBJECT-TYPE
    SYNTAX     Integer32 (0..65535)
    MAX-ACCESS read-only
    STATUS     current
    DESCRIPTION
        "The rule source mask in CIDR-compliant format. 
         Not used and set to all zeroes for IPv4 firewall output."
    ::= { ngIPv6FirewallRuleEntry 11 }

ngfwIPv6RuleDstIp OBJECT-TYPE
    SYNTAX      InetAddressIPv6
    MAX-ACCESS  accessible-for-notify
    STATUS      current
    DESCRIPTION
        "The rule source IP. Not used and set to all zeroes for IPv4 firewall output."
    ::= { ngIPv6FirewallRuleEntry 12 }

ngfwIPv6RuleDstMask OBJECT-TYPE
    SYNTAX     Integer32 (0..65535)
    MAX-ACCESS read-only
    STATUS     current
    DESCRIPTION
        "The rule source mask in CIDR-compliant format. 
         Not used and set to all zeroes for IPv4 firewall output."
    ::= { ngIPv6FirewallRuleEntry 13 }

ngfwIPv6RuleMisc OBJECT-TYPE
    SYNTAX      DisplayString
    MAX-ACCESS  read-only
    STATUS      current
    DESCRIPTION
      "The rule MISC section."
    ::= { ngIPv6FirewallRuleEntry 14 }
--
-- End IPv6 Firewall Info
--

--
-- Rogue MAC Info
--
ngRogueMacStatus OBJECT-TYPE
    SYNTAX     INTEGER {
      disabled(0),
      enabled(1)
    }
    MAX-ACCESS read-only
    STATUS     current
    DESCRIPTION
        "Inidicates whether or not Rogue MAC detection has been enabled
         in Service Manager."
    ::= { ngRogueMacInfo 1 }

ngRogueMacTable OBJECT-TYPE
    SYNTAX     SEQUENCE OF NgRogueMacEntry
    MAX-ACCESS not-accessible
    STATUS     current
    DESCRIPTION
        "The (conceptual) table of rogue MACs detected by the device.
        An entry shall be placed in the storage table for each
        rogue MAC."
    ::= { ngRogueMacInfo 2 }

ngRogueMacEntry OBJECT-TYPE
    SYNTAX     NgRogueMacEntry
    MAX-ACCESS not-accessible
    STATUS     current
    DESCRIPTION
        "A (conceptual) entry for one logical rogue MAC area on
        the host."
    INDEX { ngrmIndex }
    ::= { ngRogueMacTable 1 }

NgRogueMacEntry ::= SEQUENCE {
        ngrmIndex            Integer32,
        ngrmMac              DisplayString,
        ngrmTimestamp        DisplayString,
        ngrmIface            DisplayString,
	ngrmTimestampDAT     DateAndTime
    }

ngrmIndex OBJECT-TYPE
    SYNTAX     Integer32 (1..65535)
    MAX-ACCESS not-accessible
    STATUS     current
    DESCRIPTION
        "A unique value for each logical rogue MAC
         detected by the device."
    ::= { ngRogueMacEntry 1 }

ngrmMac OBJECT-TYPE
    SYNTAX     DisplayString
    MAX-ACCESS read-only
    STATUS     current
    DESCRIPTION
        "The MAC address of this detected rogue MAC. One
         entry that is zeroed out is returned when there
         are no rogue MACs detected."
    ::= { ngRogueMacEntry 2 }

ngrmTimestamp OBJECT-TYPE
    SYNTAX     DisplayString
    MAX-ACCESS read-only
    STATUS     current
    DESCRIPTION
        "The date and time of when this rogue MAC was detected.
         Returned as a regular string in the format MM/DD/YYYY HH:MM:SS. 
         Returns '00/00/0000 00:00:00' when there are no rogue MACs detected.
         The time returned is the local time on the AT&T VPN Gateway.  To determine 
         how the AT&T VPN Gateway's local time relates to UTC view the following OIDs:
         nghwUtcOffset (current UTC offset), nghwDstAllowed (daylight saving time allowed),
         nghwDstActive (daylight savings time active).
         NOTE: This entry is made obsolete by ngrmTimestampDAT."
    ::= { ngRogueMacEntry 3 }

ngrmIface OBJECT-TYPE
    SYNTAX     DisplayString
    MAX-ACCESS read-only
    STATUS     current
    DESCRIPTION
        "The interface this rogue MAC was
         detected on.  One entry that with a value of 
         'NONE' and a msg is returned when there are 
         no rogue MACs detected."
    ::= { ngRogueMacEntry 4 }

ngrmTimestampDAT OBJECT-TYPE
    SYNTAX      DateAndTime
    MAX-ACCESS  read-only
    STATUS      current
    DESCRIPTION
      "The date and time of when this rogue MAC was detected.
       Returns January 1 year 0 time 0 when there are no rogue MACs detected or
       the time is unknown.
       NOTE: This entry replaces ngrmTimestamp."
    ::= { ngRogueMacEntry 5 }

--
-- Dial Info
--
ngdiPhoneNum OBJECT-TYPE
    SYNTAX     DisplayString
    MAX-ACCESS read-only
    STATUS     current
    DESCRIPTION
        "The full phone number that will be dialed by the AT&T VPN Gateway.  This
         also includes dial prefix information.  For example, the AT&T VPN Gateway
         might have to dial the number nine and then a comma to access an outside
         line.  The nine and the comma will be included in this entry."
    ::= { ngDialInfo 1 }

ngdiLastTestResult OBJECT-TYPE
    SYNTAX  INTEGER {
      failure(0),
      success(1)
    }
    MAX-ACCESS  read-only
    STATUS      current
    DESCRIPTION
      "The result of the last dial test.  If no dial test has been performed yet
       then 'failure' is returned.  If a dial test is not needed because dial is
       currently up then 'success' is returned."
    ::= { ngDialInfo 2 }

ngdiLastTestCompleteTime OBJECT-TYPE
    SYNTAX  DisplayString
    MAX-ACCESS  read-only
    STATUS      current
    DESCRIPTION
      "The approximate time the last dial test completed given in the format
       MM/DD/YYYY HH:MM:SS. Returns '00/00/0000 00:00:00' when no test is scheduled.
       or when no test has run yet.  
       If the dial connection is currently in use then the dial test is not needed
       (since dial is obviously already working). ngdiLastTestCompleteTime is simply
       updated to the recent time whent the AT&T VPN Gateway last verified that the dial
       connection was still up.
       The time returned is the local time on the AT&T VPN Gateway.  To determine 
       how the AT&T VPN Gateway's local time relates to UTC view the following OIDs:
       nghwUtcOffset (current UTC offset), nghwDstAllowed (daylight saving time allowed),
       nghwDstActive (daylight savings time active).
       NOTE: This entry is made obsolete by ngdiLastTestCompleteTimeDAT."
    ::= { ngDialInfo 3 }

ngdiDialTestFailCategory  OBJECT-TYPE
    SYNTAX      INTEGER {
                  dialProblemError(0),
                  dialProblemWarning(1),
                  dialProblemMessage(2),
                  dialProblemNoCategory(3)
                }
    MAX-ACCESS  accessible-for-notify
    STATUS      current
    DESCRIPTION
      "Shows what type of category the dial test failure would be put in.
       For example, a busy signal would return dialProblemWarning but a bad password 
       would return dialProblemError.
       If a dial test is not needed because dial is currently up then dialProblemMessage
       is returned."
    ::= { ngDialInfo 4 }

ngdiDialTestFailReason OBJECT-TYPE
    SYNTAX      DisplayString
    MAX-ACCESS  accessible-for-notify
    STATUS      current
    DESCRIPTION
      "String that shows why the dial test failed.  If the test was successful or the dial
       connection is currently up then 'success' is returned."
    ::= { ngDialInfo 5 }

ngdiLastTestCompleteTimeDAT OBJECT-TYPE
    SYNTAX      DateAndTime
    MAX-ACCESS  read-only
    STATUS      current
    DESCRIPTION
      "If the dial connection is currently in use then the dial test is not needed
       (since dial is obviously already working). ngdiLastTestCompleteTimeDAT is simply
       updated to the recent time whent the AT&T VPN Gateway last verified that the dial
       connection was still up.
       Returns January 1 year 0 time 0 when no test is scheduled or when no test has run yet.  
       The time returned is the local time on the AT&T VPN Gateway.  To determine 
       how the AT&T VPN Gateway's local time relates to UTC view the following OIDs:
       nghwUtcOffset (current UTC offset), nghwDstAllowed (daylight saving time allowed),
       nghwDstActive (daylight savings time active).
       NOTE: This entry replaces ngdiLastTestCompleteTime."
    ::= { ngDialInfo 6 }

ngdiSecondaryPhoneNum OBJECT-TYPE
    SYNTAX     DisplayString
    MAX-ACCESS read-only
    STATUS     current
    DESCRIPTION
        "Specifies the secondary phone number to be tried for Dial Backup in case the 
         primary Dial Backup phone number is not available."
    ::= { ngDialInfo 7 }

--
-- DHCP Lease Info
--

ngDhcpLeaseTable OBJECT-TYPE
    SYNTAX     SEQUENCE OF NgDhcpLeaseEntry
    MAX-ACCESS not-accessible
    STATUS     current
    DESCRIPTION
        "The (conceptual) table of all current, active DHCP leases
	on the device. An entry shall be placed in the storage table 
	for each DHCP lease."
    ::= { ngDhcpLeaseInfo 1 }

ngDhcpLeaseEntry OBJECT-TYPE
    SYNTAX     NgDhcpLeaseEntry
    MAX-ACCESS not-accessible
    STATUS     current
    DESCRIPTION
        "A (conceptual) entry for one logical DHCP lease on
        the host."
    INDEX { ngdhlIndex }
    ::= { ngDhcpLeaseTable 1 }

NgDhcpLeaseEntry ::= SEQUENCE {
        ngdhlIndex            Integer32,
        ngdhlLeaseAddr        IpAddress,
        ngdhlMac              DisplayString,
        ngdhlHostname         DisplayString,
        ngdhlPort             Integer32,
        ngdhlVlanId           Integer32
    }

ngdhlIndex OBJECT-TYPE
    SYNTAX     Integer32 (1..65535)
    MAX-ACCESS not-accessible
    STATUS     current
    DESCRIPTION
        "A unique value for each logical DHCP lease
        contained by the device."
    ::= { ngDhcpLeaseEntry 1 }

ngdhlLeaseAddr OBJECT-TYPE
    SYNTAX      IpAddress
    MAX-ACCESS  read-only
    STATUS      current
    DESCRIPTION
      "The IP address associated with an indivdual DHCP lease."
    ::= { ngDhcpLeaseEntry 2 }

ngdhlMac OBJECT-TYPE
    SYNTAX  DisplayString
    MAX-ACCESS  read-only
    STATUS      current
    DESCRIPTION
      "The MAC address associated with an indivdual DHCP lease."
    ::= { ngDhcpLeaseEntry 3 }

ngdhlHostname OBJECT-TYPE
    SYNTAX  DisplayString
    MAX-ACCESS  read-only
    STATUS      current
    DESCRIPTION
      "The hostname associated with an indivdual DHCP lease."
    ::= { ngDhcpLeaseEntry 4 }

ngdhlPort OBJECT-TYPE
    SYNTAX     Integer32 (0..65535)
    MAX-ACCESS  read-only
    STATUS      current
    DESCRIPTION
      "The physical port (if valid) on the device associated
      with an indivdual DHCP lease."
    ::= { ngDhcpLeaseEntry 5 }

ngdhlVlanId OBJECT-TYPE
    SYNTAX     Integer32 (0..65535)
    MAX-ACCESS  read-only
    STATUS      current
    DESCRIPTION
      "The VLAN ID on the device associated
      with an indivdual DHCP lease."
    ::= { ngDhcpLeaseEntry 6 }

--
-- Captive Portal Info
--
ngCapPorTable OBJECT-TYPE
    SYNTAX     SEQUENCE OF NgCapPorEntry
    MAX-ACCESS not-accessible
    STATUS     current
    DESCRIPTION
        "The (conceptual) table of all current, active DHCP leases
	on the device. An entry shall be placed in the storage table 
	for each DHCP lease."
    ::= { ngCaptPortalInfo 1 }

ngCapPorEntry OBJECT-TYPE
    SYNTAX     NgCapPorEntry
    MAX-ACCESS not-accessible
    STATUS     current
    DESCRIPTION
        "A (conceptual) entry for one logical DHCP lease on
        the host."
    INDEX { ngcpIndex }
    ::= { ngCapPorTable 1 }

NgCapPorEntry ::= SEQUENCE {
        ngcpIndex            Integer32,
        ngcpAddr             IpAddress,
        ngcpMac              DisplayString,
        ngcpUser             DisplayString,
        ngcpDuration         Integer32,
        ngcpMaxDuration      Integer32,
        ngcpState            Integer32,
        ngcpIdle             Integer32,
        ngcpMaxIdle          Integer32,
        ngcpPort             Integer32,
        ngcpVlanId           Integer32
    }

ngcpIndex OBJECT-TYPE
    SYNTAX     Integer32 (1..65535)
    MAX-ACCESS not-accessible
    STATUS     current
    DESCRIPTION
        "A unique value for each logical DHCP lease
        contained by the device."
    ::= { ngCapPorEntry 1 }

ngcpAddr OBJECT-TYPE
    SYNTAX      IpAddress
    MAX-ACCESS  read-only
    STATUS      current
    DESCRIPTION
      "The IP address associated with an indivdual DHCP lease."
    ::= { ngCapPorEntry 2 }

ngcpMac OBJECT-TYPE
    SYNTAX  DisplayString
    MAX-ACCESS  read-only
    STATUS      current
    DESCRIPTION
      "The MAC address associated with an indivdual DHCP lease."
    ::= { ngCapPorEntry 3 }

ngcpUser OBJECT-TYPE
    SYNTAX  DisplayString
    MAX-ACCESS  read-only
    STATUS      current
    DESCRIPTION
      "The hostname associated with an indivdual DHCP lease."
    ::= { ngCapPorEntry 4 }

ngcpDuration OBJECT-TYPE
    SYNTAX     Integer32
    MAX-ACCESS  read-only
    STATUS      current
    DESCRIPTION
      "The physical port (if valid) on the device associated
      with an indivdual DHCP lease."
    ::= { ngCapPorEntry 5 }

ngcpMaxDuration OBJECT-TYPE
    SYNTAX     Integer32
    MAX-ACCESS  read-only
    STATUS      current
    DESCRIPTION
      "The physical port (if valid) on the device associated
      with an indivdual DHCP lease."
    ::= { ngCapPorEntry 6 }

ngcpState OBJECT-TYPE
    SYNTAX     Integer32 (0..65535)
    MAX-ACCESS  read-only
    STATUS      current
    DESCRIPTION
      "The physical port (if valid) on the device associated
      with an indivdual DHCP lease."
    ::= { ngCapPorEntry 7 }

ngcpIdle OBJECT-TYPE
    SYNTAX     Integer32
    MAX-ACCESS  read-only
    STATUS      current
    DESCRIPTION
      "The physical port (if valid) on the device associated
      with an indivdual DHCP lease."
    ::= { ngCapPorEntry 8 }

ngcpMaxIdle OBJECT-TYPE
    SYNTAX     Integer32
    MAX-ACCESS  read-only
    STATUS      current
    DESCRIPTION
      "The physical port (if valid) on the device associated
      with an indivdual DHCP lease."
    ::= { ngCapPorEntry 9 }

ngcpPort OBJECT-TYPE
    SYNTAX     Integer32 (0..65535)
    MAX-ACCESS  read-only
    STATUS      current
    DESCRIPTION
      "The physical port (if valid) on the device associated
      with an indivdual DHCP lease."
    ::= { ngCapPorEntry 10 }

ngcpVlanId OBJECT-TYPE
    SYNTAX     Integer32 (0..65535)
    MAX-ACCESS  read-only
    STATUS      current
    DESCRIPTION
      "The VLAN ID on the device associated
      with an indivdual DHCP lease."
    ::= { ngCapPorEntry 11 }

--
-- Inbound Tunnel Info
--
attInbTunTable OBJECT-TYPE
    SYNTAX     SEQUENCE OF AttInbTunEntry
    MAX-ACCESS not-accessible
    STATUS     current
    DESCRIPTION
        "The (conceptual) table of inbound tunnels on the device.
        An entry shall be placed in the storage table for each
        inbound tunnel."
    ::= { attInbTunInfo 1 }

attInbTunEntry OBJECT-TYPE
    SYNTAX     AttInbTunEntry
    MAX-ACCESS not-accessible
    STATUS     current
    DESCRIPTION
        "A (conceptual) entry for one logical inbound tunnel area on
        the host."
    INDEX { inbTunIndex }
    ::= { attInbTunTable 1 }

AttInbTunEntry ::= SEQUENCE {
        inbTunIndex             Integer32,
        inbTunClientTransAddr   DisplayString,
        inbTunLocalIpsecIface   DisplayString,
        inbTunType              DisplayString,
        inbTunUserid            DisplayString,
        inbTunSrvConfigProf     DisplayString,
        inbTunTimeEstablished    DateAndTime,
        inbTunDuration          TimeTicks,
        inbTunIdleTimeout       TimeTicks,
        inbTunCurrIdleTimeout   TimeTicks,
        inbTunNegIkePhase1Lifet TimeTicks,
        inbTunNatTNegotiated    INTEGER,
        inbTunActClientSaNeg    Integer32
    }

inbTunIndex OBJECT-TYPE
    SYNTAX     Integer32 (1..65535)
    MAX-ACCESS not-accessible
    STATUS     current
    DESCRIPTION
        "A unique value for each logical inbound tunnel
        contained by the device."
    ::= { attInbTunEntry 1 }

inbTunClientTransAddr OBJECT-TYPE
    SYNTAX     DisplayString
    MAX-ACCESS read-only
    STATUS     current
    DESCRIPTION
        "The client transport address of this inbound tunnel."
    ::= { attInbTunEntry 2 }

inbTunLocalIpsecIface OBJECT-TYPE
    SYNTAX     DisplayString
    MAX-ACCESS read-only
    STATUS     current
    DESCRIPTION
        "The IPsec interface associated with this inbound tunnel."
    ::= { attInbTunEntry 3 }

inbTunType OBJECT-TYPE
    SYNTAX     DisplayString
    MAX-ACCESS read-only
    STATUS     current
    DESCRIPTION
        "The tunnel type of this inbound tunnel."
    ::= { attInbTunEntry 4 }

inbTunUserid OBJECT-TYPE
    SYNTAX     DisplayString
    MAX-ACCESS read-only
    STATUS     current
    DESCRIPTION
        "The userid associated with this inbound tunnel."
    ::= { attInbTunEntry 5 }

inbTunSrvConfigProf OBJECT-TYPE
    SYNTAX     DisplayString
    MAX-ACCESS read-only
    STATUS     current
    DESCRIPTION
        "The Service Manager profile associated with this inbound tunnel."
    ::= { attInbTunEntry 6 }

inbTunTimeEstablished OBJECT-TYPE
    SYNTAX      DateAndTime
    MAX-ACCESS  read-only
    STATUS      current
    DESCRIPTION
      "Time this inbound tunnel was established."
    ::= { attInbTunEntry 7 }

inbTunDuration OBJECT-TYPE
    SYNTAX     TimeTicks
    MAX-ACCESS read-only
    STATUS     current
    DESCRIPTION
        "How long this inbound tunnel has been up."
    ::= { attInbTunEntry 8 }

inbTunIdleTimeout OBJECT-TYPE
    SYNTAX     TimeTicks
    MAX-ACCESS read-only
    STATUS     current
    DESCRIPTION
        "This inbound tunnel's idle timeout setting."
    ::= { attInbTunEntry 9 }

inbTunCurrIdleTimeout OBJECT-TYPE
    SYNTAX     TimeTicks
    MAX-ACCESS read-only
    STATUS     current
    DESCRIPTION
        "How long this inbound tunnel has been idle."
    ::= { attInbTunEntry 10 }

inbTunNegIkePhase1Lifet OBJECT-TYPE
    SYNTAX     TimeTicks
    MAX-ACCESS read-only
    STATUS     current
    DESCRIPTION
        "This inbound tunnel's negotiated IKE Phase 1
         lifetime."
    ::= { attInbTunEntry 11 }

inbTunNatTNegotiated OBJECT-TYPE
    SYNTAX  INTEGER {
     no(0),
     yes(1)
    }
    MAX-ACCESS  read-only
    STATUS      current
    DESCRIPTION
      "Is NAT-T negotiated for this inbound tunnel?"
    ::= { attInbTunEntry 12 }

inbTunActClientSaNeg OBJECT-TYPE
    SYNTAX     Integer32 (1..65535)
    MAX-ACCESS  read-only
    STATUS     current
    DESCRIPTION
        "Active client SA's negotiated for this inbound tunnel."
    ::= { attInbTunEntry 13 }

--
-- Inbound Tunnel Network Info
--
attInbTunNetTable OBJECT-TYPE
    SYNTAX     SEQUENCE OF AttInbTunNetEntry
    MAX-ACCESS not-accessible
    STATUS     current
    DESCRIPTION
        "The (conceptual) table of inbound tunnel networks on the device.
        An entry shall be placed in the storage table for each
        inbound tunnel network."
    ::= { attInbTunInfo 2 }

attInbTunNetEntry OBJECT-TYPE
    SYNTAX     AttInbTunNetEntry
    MAX-ACCESS not-accessible
    STATUS     current
    DESCRIPTION
        "A (conceptual) entry for one logical inbound tunnel network area on
        the host."
    INDEX { inbTunNetIndex }
    ::= { attInbTunNetTable 1 }

AttInbTunNetEntry ::= SEQUENCE {
        inbTunNetIndex             Integer32,
        inbTunNetNetwork           DisplayString,
        inbTunNetTimeEstablished   DateAndTime,
        inbTunNetNegIkePhase2Lifet TimeTicks,
        inbTunNetEspAlgorithm      DisplayString,
        inbTunNetCompression       INTEGER,
        inbTunNetClientTransAddr   DisplayString
    }

inbTunNetIndex OBJECT-TYPE
    SYNTAX     Integer32 (1..65535)
    MAX-ACCESS not-accessible
    STATUS     current
    DESCRIPTION
        "A unique value for each logical inbound tunnel's
        network contained by the device."
    ::= { attInbTunNetEntry 1 }

inbTunNetNetwork OBJECT-TYPE
    SYNTAX     DisplayString
    MAX-ACCESS read-only
    STATUS     current
    DESCRIPTION
        "This inbound tunnel network."
    ::= { attInbTunNetEntry 2 }

inbTunNetTimeEstablished OBJECT-TYPE
    SYNTAX      DateAndTime
    MAX-ACCESS  read-only
    STATUS      current
    DESCRIPTION
      "Time this inbound tunnel network was established."
    ::= { attInbTunNetEntry 3 }

inbTunNetNegIkePhase2Lifet OBJECT-TYPE
    SYNTAX     TimeTicks
    MAX-ACCESS read-only
    STATUS     current
    DESCRIPTION
        "This inbound tunnel network's negotiated IKE Phase 2
         lifetime."
    ::= { attInbTunNetEntry 4 }

inbTunNetEspAlgorithm OBJECT-TYPE
    SYNTAX     DisplayString
    MAX-ACCESS read-only
    STATUS     current
    DESCRIPTION
        "This inbound tunnel network's ESP algorithm."
    ::= { attInbTunNetEntry 5 }

inbTunNetCompression OBJECT-TYPE
    SYNTAX  INTEGER {
     no(0),
     yes(1)
    }
    MAX-ACCESS  read-only
    STATUS      current
    DESCRIPTION
      "Is compression negotiated for this inbound tunnel?"
    ::= { attInbTunNetEntry 6 }

inbTunNetClientTransAddr OBJECT-TYPE
    SYNTAX     DisplayString
    MAX-ACCESS read-only
    STATUS     current
    DESCRIPTION
        "Shows what inbound tunnel this network belongs to.  Corresponds
         to inbTunClientTransAddr in attInbTunEntry."
    ::= { attInbTunNetEntry 7 }

--
-- AT&T VPN Gateway Traps/Informs
--

--
-- Objects in the individual events.
--
ngevMac OBJECT-TYPE
    SYNTAX      DisplayString
    MAX-ACCESS  accessible-for-notify
    STATUS      current
    DESCRIPTION
      "The MAC address in Service Manager this device
       is registered under."
    ::= { ngEventObjects 1 }

ngevRogueMac    OBJECT-TYPE
    SYNTAX      DisplayString
    MAX-ACCESS  accessible-for-notify
    STATUS      current
    DESCRIPTION
      "The MAC address of the unauthorized machine detected when
       MAC monitoring is enabled."
    ::= { ngEventObjects 2 }

ngevActiveWanIp OBJECT-TYPE
    SYNTAX      IpAddress
    MAX-ACCESS  accessible-for-notify
    STATUS      current
    DESCRIPTION
      "The IP address of the active WAN interface.  When viewing
       the output of the SNMP tree this can be determined from the
       interface statistics.  However, for traps the active WAN
       interface might not be used to send the trap (i.e. it could
       be down the tunnel. Set to zero if not used."
    ::= { ngEventObjects 3 }

ngevIpConntrackMaxPercentage OBJECT-TYPE
    SYNTAX      Integer32 (1..65535)
    MAX-ACCESS  accessible-for-notify
    STATUS      current
    DESCRIPTION
      "An alert will be sent when the ip_conntrack table is within
       this percentage of the maximum."
    ::= { ngEventObjects 4 }

ngevIpConntrackCurrentPercentage OBJECT-TYPE
    SYNTAX      Integer32 (0..65535)
    MAX-ACCESS  accessible-for-notify
    STATUS      current
    DESCRIPTION
      "The ip_conntrack table is currently at this percentage
       of the maximum."
    ::= { ngEventObjects 5 }

ngevTimeInDial  OBJECT-TYPE
    SYNTAX      Integer32 (1..65535)
    MAX-ACCESS  accessible-for-notify
    STATUS      current
    DESCRIPTION
      "The number of minutes the device has been connected
       via dial."
    ::= { ngEventObjects 6 }

ngevQueryProblem  OBJECT-TYPE
    SYNTAX      INTEGER {
                  profileNotFound(0),
                  discontinuingTheDevice(1),
		  bandwNoResults(2)
                }
    MAX-ACCESS  accessible-for-notify
    STATUS      current
    DESCRIPTION
      "Used to indicate what type of problem is happening with the device's status.
       profileNotFound means that a profile for the device was not found on an AT&T
       Administration Server in any region. discontinuingTheDevice means that the
       device has gone too long without having a valid profile in any region.  
       bandwNoResults means that a bandwidth test failed and no previous bandwidth 
       test results have been found, which results in the device being marked as 
       discontinued until a bandwidth test works."
    ::= { ngEventObjects 7 }

ngevTunConnectionId   OBJECT-TYPE
    SYNTAX      DisplayString
    MAX-ACCESS  accessible-for-notify
    STATUS      current
    DESCRIPTION
      "The tunnel connection ID is a unique value assigned to each instance of a tunnel. 
       It is used to associate the tunnel up, tunnel alive, and tunnel down traps together.
       When a tunnel goes down and is then re-established it will be assigned a new
       tunnel connection ID."
    ::= { ngEventObjects 8 }

ngevTunnelDateAndTime   OBJECT-TYPE
    SYNTAX      DateAndTime
    MAX-ACCESS  accessible-for-notify
    STATUS      current
    DESCRIPTION
      "The timestamp from when the tunnel came up, tried to come up,
       or came down."
    ::= { ngEventObjects 9 }

ngevConnectionType  OBJECT-TYPE
    SYNTAX      INTEGER {
                  connTypeBroadband(0),
                  connTypeAgnsDial(1),
                  connTypeOtherIspDial(2)
                }
    MAX-ACCESS  accessible-for-notify
    STATUS      current
    DESCRIPTION
      "Indicates whether the tunnel is via broadband or dial."
    ::= { ngEventObjects 10 }

ngevAccount OBJECT-TYPE
    SYNTAX      DisplayString (SIZE (1..8))
    MAX-ACCESS  accessible-for-notify
    STATUS      current
    DESCRIPTION
      "In the tunnel up/down trap it is the customer account
       used to start the tunnel. 
       In the secondary auth attempt trap it is the account
       used for the login attempt."
    ::= { ngEventObjects 11 }

ngevUserid OBJECT-TYPE
    SYNTAX      DisplayString
    MAX-ACCESS  accessible-for-notify
    STATUS      current
    DESCRIPTION
      "In the tunnel up/down trap it is the customer userid
       used to start the tunnel. 
       In the secondary auth attempt trap it is the userid
       used for the login attempt."
    ::= { ngEventObjects 12 }

ngevTunConReason OBJECT-TYPE
    SYNTAX      DisplayString
    MAX-ACCESS  accessible-for-notify
    STATUS      current
    DESCRIPTION
      "String that shows a message that explains the
       results of a tunnel connection attempt."
    ::= { ngEventObjects 13 }

ngevDialTestFailReason OBJECT-TYPE
    SYNTAX      DisplayString
    MAX-ACCESS  accessible-for-notify
    STATUS      current
    DESCRIPTION
      "String that shows why the dial test failed."
    ::= { ngEventObjects 14 }

ngevSshSourceIp OBJECT-TYPE
    SYNTAX      IpAddress
    MAX-ACCESS  accessible-for-notify
    STATUS      current
    DESCRIPTION
      "The IP address of the client that ssh'ed into the device."
    ::= { ngEventObjects 15 }

ngevRequestorIp OBJECT-TYPE
    SYNTAX      IpAddress
    MAX-ACCESS  accessible-for-notify
    STATUS      current
    DESCRIPTION
      "The IP address of the machine that initiated a particular
       request (reboot, shutdown, secondary auth attempt, etc.).
       Will be set to loopback if an automated process caused
       the reboot."
    ::= { ngEventObjects 16 }

ngevDialTestFailCategory  OBJECT-TYPE
    SYNTAX      INTEGER {
                  dialProblemError(0),
                  dialProblemWarning(1),
                  dialProblemMessage(2),
                  dialProblemNoCategory(3)
                }
    MAX-ACCESS  accessible-for-notify
    STATUS      current
    DESCRIPTION
      "Shows what type of category the dial test failure would
       be put in.  For example, a busy signal would be a warning
       but a bad password would be an error."
    ::= { ngEventObjects 17 }

ngevRogueIp    OBJECT-TYPE
    SYNTAX     IpAddress
    MAX-ACCESS accessible-for-notify
    STATUS     current
    DESCRIPTION
      "The IP address of the unauthorized machine detected when
       MAC monitoring is enabled. Set to zero if not used."
    ::= { ngEventObjects 18 }

ngevRogueInterface OBJECT-TYPE
    SYNTAX      DisplayString
    MAX-ACCESS  accessible-for-notify
    STATUS      current
    DESCRIPTION
      "The interface of the unauthorized machine detected when
       MAC monitoring is enabled."
    ::= { ngEventObjects 19 }

ngevTrapDescription OBJECT-TYPE
    SYNTAX      DisplayString
    MAX-ACCESS  accessible-for-notify
    STATUS      current
    DESCRIPTION
      "For MAC monitoring this is the Service Manager 
       description field.  Other traps may use this field
       for other purposes."
    ::= { ngEventObjects 20 }

ngevLoginResult  OBJECT-TYPE
    SYNTAX      INTEGER {
                  failure(0),
                  success(1)
                }
    MAX-ACCESS  accessible-for-notify
    STATUS      current
    DESCRIPTION
      "Specifies the result of the secondary login attempt when
       someone tries to ssh into the AT&T VPN Gateway."
    ::= { ngEventObjects 21 }

ngevNewLocalID OBJECT-TYPE
    SYNTAX      DisplayString
    MAX-ACCESS  accessible-for-notify
    STATUS      current
    DESCRIPTION
      "The userid that the user became after their secondary 
       login attempt was successful. Secondary logins are 
       performed when someone tries to ssh into the AT&T VPN Gateway.

       The userid that the user became (or tried to become)
       for their switch user attempt."
    ::= { ngEventObjects 22 }

ngevOldLocalID OBJECT-TYPE
    SYNTAX      DisplayString
    MAX-ACCESS  accessible-for-notify
    STATUS      current
    DESCRIPTION
      "The userid that was in use when the user made their
       switch user attempt."
    ::= { ngEventObjects 23 }

ngevMaxTimeInDialUntilAlert  OBJECT-TYPE
    SYNTAX      TimeTicks
    MAX-ACCESS  accessible-for-notify
    STATUS      current
    DESCRIPTION
      "The max number of minutes the device can be connected
       via dial without a trap being sent for excessive dial.
       Once this maximum is reached a trap will be sent."
    ::= { ngEventObjects 24 }

ngevPortDown OBJECT-TYPE
    SYNTAX      Integer32 (0..65535)
    MAX-ACCESS  accessible-for-notify
    STATUS      current
    DESCRIPTION
      "An individual port that is currently not active.  Only
       used by the AT&T VPN Gateway 8200V."
    ::= { ngEventObjects 25 }

ngevIPv6ActiveWanIp OBJECT-TYPE
    SYNTAX      InetAddressIPv6
    MAX-ACCESS  accessible-for-notify
    STATUS      current
    DESCRIPTION
      "The IP address of the active IPv6 WAN interface.  When viewing
       the output of the SNMP tree this can be determined from the
       interface statistics.  However, for traps the active WAN
       interface might not be used to send the trap (i.e. it could
       be down the tunnel. Set to zero if not used."
    ::= { ngEventObjects 26 }

ngevIPv6RogueIp OBJECT-TYPE
    SYNTAX     InetAddressIPv6
    MAX-ACCESS accessible-for-notify
    STATUS     current
    DESCRIPTION
      "The IPv6 IP address of the unauthorized machine detected when
       MAC monitoring is enabled. Set to zero if not used."
    ::= { ngEventObjects 27 }

ngevIPv6RequestorIp OBJECT-TYPE
    SYNTAX      InetAddressIPv6
    MAX-ACCESS  accessible-for-notify
    STATUS      current
    DESCRIPTION
      "The IPv6 IP address of the machine that initiated a particular
       request (reboot, shutdown, secondary auth attempt, etc.).
       Will be set to loopback if an automated process caused
       the reboot."
    ::= { ngEventObjects 28 }

ngevCardNotFoundTime   OBJECT-TYPE
    SYNTAX      DateAndTime
    MAX-ACCESS  accessible-for-notify
    STATUS      current
    DESCRIPTION
      "The timestamp that indicates when the AT&T VPN Gateway noted that
       the required cellular card was missing."
    ::= { ngEventObjects 29 }

ngevVPNServiceIPv4Address    OBJECT-TYPE
    SYNTAX     IpAddress
    MAX-ACCESS accessible-for-notify
    STATUS     current
    DESCRIPTION
      "The VPN Service Address assigned for this tunnel connetion. 
       Will be not set if this is an IPv6 tunnel or the tunnel did
       not come up."
    ::= { ngEventObjects 30 }

ngevVPNServiceIPv6Address    OBJECT-TYPE
    SYNTAX      InetAddressIPv6
    MAX-ACCESS accessible-for-notify
    STATUS     current
    DESCRIPTION
      "The VPN Service Address assigned for this tunnel connetion.  
       Will be not set if this is an IPv4 tunnel or the tunnel did
       not come up."
    ::= { ngEventObjects 31 }

ngevTunConReasonNUM OBJECT-TYPE
    SYNTAX     INTEGER {
      success(0),
      gigCantAuthAtThisTime(40),
      alreadyLoggedOntoGIG(73),
      ikePhase1Failed(211),
      ikePhase2Failed(212),
      attEntrustLoginErr(215),
      attEntrustErr(216),
      ikeMemoryAlloc(218),
      ikeInitFailed(220),
      ikeUnableToAccessCertSvcs(221),
      attCertificateErr(222),
      internalErrMsg(224),
      tunSrvAuthFailed(228),
      ikeProtoclNegFailed(250),
      ikeProtocolNotChosen(251),
      ikeGenericErrMsg(252),
      ikeConnectionRefused(253),
      ikeSocketsErr(254),
      ikeTunnelSvrNotResp(255),
      iuthTunnelSvrNotResp(256),
      ikeIsakmpSaMissing(257),
      rigCommunicationErr(260),
      deviceStatusInactive(261),
      isakmpNegTimeout(262),
      protocolNegTimeout(263),
      errSettingUpSa(264),
      errCreateEspAuthData(265),
      errAttemptToSendXauthChal(266),
      errXauthTimeout(267),
      errSendingModeConfigReq(268),
      errUnexpectedXauthMessage(269),
      errExpectedXauthMethod(270),
      errMissingGroupIdOrPwd(271),
      errAssigningPrivateIPonSIG(302),
      alreadyLoggedOntoSIG(303),
      vigInternalError(311),
      enterValidAcctAndUser(314),
      userIdNotAuthorized(316),
      sigCantAuthAtThisTime(318),
      timeoutWaitingForServerRespond(402),
      inetNoTunnelHosts(466),
      userHitCancelButton(502),
      wanConnectionLost(505),
      dialAttemptFailed(540),
      dialSetupFailed(541),
      errParsingAuthResp(542),
      excNotReset(545),
      errGettingRigAddr(546),
      errRigAuth(547),
      errTunSrvNotReachable(548),
      errMissingLoginInfo(549),
      errSvcMgrProfileChanged(550),
      errTunNotAllowedViaDial(552),
      inbSAFromOldConWithSameClientAddr(556),
      inbLocalAuthFailed(557),
      inbAuthErr(558),
      inbOverlappingNetw(559),
      inbGroupIdNotFound(560),
      inbIkePhase1NegTimeout(561),
      errUnknown(599)
    }
    MAX-ACCESS  read-only
    STATUS      current
    DESCRIPTION
        "A numeric value that indicates the results of an
         inbound or outbound tunnel connection attempt."
    ::= { ngEventObjects 32 }

evIface OBJECT-TYPE
    SYNTAX      DisplayString
    MAX-ACCESS  accessible-for-notify
    STATUS      current
    DESCRIPTION
      "The interface in question for this event."
    ::= { ngEventObjects 33 }

evNotFoundTime   OBJECT-TYPE
    SYNTAX      DateAndTime
    MAX-ACCESS  accessible-for-notify
    STATUS      current
    DESCRIPTION
      "The timestamp that indicates when the AT&T VPN Gateway noted
       that the item in question was missing."
    ::= { ngEventObjects 34 }

evTrapCreatedTime   OBJECT-TYPE
    SYNTAX      DateAndTime
    MAX-ACCESS  accessible-for-notify
    STATUS      current
    DESCRIPTION
      "The timestamp that indicates when the trap was actually generated.
       If informs are in use and the server is temporarily not 
       reachable it could be a long time before the inform is actually
       received."
    ::= { ngEventObjects 35 }

evDualWanProb  OBJECT-TYPE
    SYNTAX      INTEGER {
                  dwTrapNone(0),
                  dwTrapGeneralErr(1),
                  dwTrapConTypeNotFound(2),
                  dwTrapUnsuppConType(3),
                  dwTrapMissingStaticIP(4),
                  dwTrapMissingStaticIPMask(5),
                  dwTrapMissingStaticIPGway(6),
                  dwTrapMissingPPPoEUser(7),
                  dwTrapMissingPPPoEPass(8),
                  dwTrapWAN2TestFailed(9)
                }
    MAX-ACCESS  accessible-for-notify
    STATUS      current
    DESCRIPTION
      "Used to help indicate why IPv4 WAN2 could not be brought up when configured
       for Dual WAN. The generic 'dwTrapGeneralErr' is used when a specific
       reason isn't available. 'dwTrapNone' means that there was no error."
    ::= { ngEventObjects 36 }

evDualWanV6Prob  OBJECT-TYPE
    SYNTAX      INTEGER {
                  dwTrapNone(0),
                  dwTrapGeneralErr(1),
                  dwTrapConTypeNotFound(2),
                  dwTrapUnsuppConType(3),
                  dwTrapMissingStaticIP(4),
                  dwTrapMissingStaticIPMask(5),
                  dwTrapMissingStaticIPGway(6),
                  dwTrapWAN2TestFailed(9)
                }
    MAX-ACCESS  accessible-for-notify
    STATUS      current
    DESCRIPTION
      "Used to help indicate why IPv6 WAN2 could not be brought up when configured
       for Dual WAN. The generic 'dwTrapGeneralErr' is used when a specific
       reason isn't available. 'dwTrapNone' means that there was no error."
    ::= { ngEventObjects 37 }

evFoundOOB OBJECT-TYPE
    SYNTAX      Integer32 (0..65535)
    MAX-ACCESS  accessible-for-notify
    STATUS      current
    DESCRIPTION
      "How many OOB cables were detected when at least one was
       found to be missing."
    ::= { ngEventObjects 38 }

evExpectedOOB OBJECT-TYPE
    SYNTAX      Integer32 (0..65535)
    MAX-ACCESS  accessible-for-notify
    STATUS      current
    DESCRIPTION
      "How many OOB cables were expected when at least one was 
       found to be missing."
    ::= { ngEventObjects 39 }

evResult  OBJECT-TYPE
    SYNTAX      INTEGER {
                  failure(0),
                  success(1)
                }
    MAX-ACCESS  accessible-for-notify
    STATUS      current
    DESCRIPTION
      "Generic field to indicate a result."
    ::= { ngEventObjects 40 }

evSrcV4    OBJECT-TYPE
    SYNTAX     IpAddress
    MAX-ACCESS accessible-for-notify
    STATUS     current
    DESCRIPTION
      "Generic source IPv4 address."
    ::= { ngEventObjects 41 }

evDestV4    OBJECT-TYPE
    SYNTAX     IpAddress
    MAX-ACCESS accessible-for-notify
    STATUS     current
    DESCRIPTION
      "Generic destination IPv4 address."
    ::= { ngEventObjects 42 }

evSrcV6    OBJECT-TYPE
    SYNTAX      InetAddressIPv6
    MAX-ACCESS accessible-for-notify
    STATUS     current
    DESCRIPTION
      "Generic source IPv6 address."
    ::= { ngEventObjects 43 }

evDestV6    OBJECT-TYPE
    SYNTAX      InetAddressIPv6
    MAX-ACCESS accessible-for-notify
    STATUS     current
    DESCRIPTION
      "Generic destination IPv6 address."
    ::= { ngEventObjects 44 }

evResponseMax OBJECT-TYPE
    SYNTAX      Integer32 (0..65535)
    MAX-ACCESS  accessible-for-notify
    STATUS      current
    DESCRIPTION
      "Generic field to indicate how long a test waited for a response."
    ::= { ngEventObjects 45 }

evFailureCount OBJECT-TYPE
    SYNTAX      Integer32 (0..65535)
    MAX-ACCESS  accessible-for-notify
    STATUS      current
    DESCRIPTION
      "Generic field to indicate how many failures occurred before
       this event was generated."
    ::= { ngEventObjects 46 }

evDescription OBJECT-TYPE
    SYNTAX      DisplayString
    MAX-ACCESS  accessible-for-notify
    STATUS      current
    DESCRIPTION
      "Generic field for description."
    ::= { ngEventObjects 47 }

evSendTrapWhen  OBJECT-TYPE
    SYNTAX      INTEGER {
                  failure(0),
                  success(1),
                  always(2),
                  unknown(3)
                }
    MAX-ACCESS  accessible-for-notify
    STATUS      current
    DESCRIPTION
      "Generic field used to indicate when to send a trap after a test
       is performed."
    ::= { ngEventObjects 48 }

evWan1IPv4IP OBJECT-TYPE
    SYNTAX      IpAddress
    MAX-ACCESS  accessible-for-notify
    STATUS      current
    DESCRIPTION
      "Field used to report on the IP of the first interface if it is
       using IPv4."
    ::= { ngEventObjects 49 }

evWan1IPv4Name OBJECT-TYPE
    SYNTAX      DisplayString
    MAX-ACCESS  accessible-for-notify
    STATUS      current
    DESCRIPTION
      "Field used to report on the name of the first interface if it is
       using IPv4."
    ::= { ngEventObjects 50 }

evWan1IPv6IP    OBJECT-TYPE
    SYNTAX      InetAddressIPv6
    MAX-ACCESS accessible-for-notify
    STATUS     current
    DESCRIPTION
      "Generic field used to report on the IP of the first interface if it is
       using IPv6."
    ::= { ngEventObjects 51 }

evWan1IPv6Name OBJECT-TYPE
    SYNTAX      DisplayString
    MAX-ACCESS  accessible-for-notify
    STATUS      current
    DESCRIPTION
      "Field used to report on the name of the first interface if it is
       using IPv6."
    ::= { ngEventObjects 52 }

evWan2IPv4IP OBJECT-TYPE
    SYNTAX      IpAddress
    MAX-ACCESS  accessible-for-notify
    STATUS      current
    DESCRIPTION
      "Generic field used to report on the IP of the second interface if it is
       using IPv4."
    ::= { ngEventObjects 53 }

evWan2IPv4Name OBJECT-TYPE
    SYNTAX      DisplayString
    MAX-ACCESS  accessible-for-notify
    STATUS      current
    DESCRIPTION
      "Field used to report on the name of the second interface if it is
       using IPv4."
    ::= { ngEventObjects 54 }

evWan2IPv6IP    OBJECT-TYPE
    SYNTAX      InetAddressIPv6
    MAX-ACCESS accessible-for-notify
    STATUS     current
    DESCRIPTION
      "Generic field used to report on the IP of the second interface if it is
       using IPv6."
    ::= { ngEventObjects 55 }

evWan2IPv6Name OBJECT-TYPE
    SYNTAX      DisplayString
    MAX-ACCESS  accessible-for-notify
    STATUS      current
    DESCRIPTION 
      "Field used to report on the name of the second interface if it is
       using IPv6."
    ::= { ngEventObjects 56 }

evNatTEnabled  OBJECT-TYPE
    SYNTAX      INTEGER {
                  disabled(0),
                  enabled(1)
                }
    MAX-ACCESS  accessible-for-notify
    STATUS      current
    DESCRIPTION
      "Tunnel field that indicates whether or not Nat-T is in use."
    ::= { ngEventObjects 57 }

evESPAlgorithm  OBJECT-TYPE
    SYNTAX      DisplayString
    MAX-ACCESS  accessible-for-notify
    STATUS      current
    DESCRIPTION
      "Tunnel field that indicates the ESP Algorithm."
    ::= { ngEventObjects 58 }

evAuthAlgorithm  OBJECT-TYPE
    SYNTAX      DisplayString
    MAX-ACCESS  accessible-for-notify
    STATUS      current
    DESCRIPTION
      "Tunnel field that indicates the Auth Algorithm."
    ::= { ngEventObjects 59 }

evCompressionAlgorithm  OBJECT-TYPE
    SYNTAX      DisplayString
    MAX-ACCESS  accessible-for-notify
    STATUS      current
    DESCRIPTION
      "Tunnel field that indicates the (optional) Compression Algorithm."
    ::= { ngEventObjects 60 }

--
-- Objects in the individual events used only for data usage statistics.
--

evDataUpHwm OBJECT-TYPE
    SYNTAX  Unsigned32
    MAX-ACCESS  read-only
    STATUS      current
    DESCRIPTION
      "The upstream high water mark to be used for the calculations."
    ::= { ngEventDataUsageObjects 1 }


evDataDownHwm OBJECT-TYPE
    SYNTAX  Unsigned32
    MAX-ACCESS  read-only
    STATUS      current
    DESCRIPTION
      "The downstream high water mark to be used for the calculations."
    ::= { ngEventDataUsageObjects 2 }

evDataUp1 OBJECT-TYPE
    SYNTAX      Unsigned32
    MAX-ACCESS  read-only
    STATUS      current
    DESCRIPTION
      "Average upstream bandwidth measured over a certain time period."
    ::= { ngEventDataUsageObjects 3 }

evDataDown1 OBJECT-TYPE
    SYNTAX  Unsigned32
    MAX-ACCESS  read-only
    STATUS      current
    DESCRIPTION
      "Average downstream bandwidth measured over a certain time period."
    ::= { ngEventDataUsageObjects 4 }

evDataUp2 OBJECT-TYPE
    SYNTAX      Unsigned32
    MAX-ACCESS  read-only
    STATUS      current
    DESCRIPTION
      "Average upstream bandwidth measured over a certain time period."
    ::= { ngEventDataUsageObjects 5 }

evDataDown2 OBJECT-TYPE
    SYNTAX  Unsigned32
    MAX-ACCESS  read-only
    STATUS      current
    DESCRIPTION
      "Average downstream bandwidth measured over a certain time period."
    ::= { ngEventDataUsageObjects 6 }

evDataUp3 OBJECT-TYPE
    SYNTAX      Unsigned32
    MAX-ACCESS  read-only
    STATUS      current
    DESCRIPTION
      "Average upstream bandwidth measured over a certain time period."
    ::= { ngEventDataUsageObjects 7 }

evDataDown3 OBJECT-TYPE
    SYNTAX  Unsigned32
    MAX-ACCESS  read-only
    STATUS      current
    DESCRIPTION
      "Average downstream bandwidth measured over a certain time period."
    ::= { ngEventDataUsageObjects 8 }

evDataUp4 OBJECT-TYPE
    SYNTAX      Unsigned32
    MAX-ACCESS  read-only
    STATUS      current
    DESCRIPTION
      "Average upstream bandwidth measured over a certain time period."
    ::= { ngEventDataUsageObjects 9 }

evDataDown4 OBJECT-TYPE
    SYNTAX  Unsigned32
    MAX-ACCESS  read-only
    STATUS      current
    DESCRIPTION
      "Average downstream bandwidth measured over a certain time period."
    ::= { ngEventDataUsageObjects 10 }

evDataUp5 OBJECT-TYPE
    SYNTAX      Unsigned32
    MAX-ACCESS  read-only
    STATUS      current
    DESCRIPTION
      "Average upstream bandwidth measured over a certain time period."
    ::= { ngEventDataUsageObjects 11 }

evDataDown5 OBJECT-TYPE
    SYNTAX  Unsigned32
    MAX-ACCESS  read-only
    STATUS      current
    DESCRIPTION
      "Average downstream bandwidth measured over a certain time period."
    ::= { ngEventDataUsageObjects 12 }

evDataUp6 OBJECT-TYPE
    SYNTAX      Unsigned32
    MAX-ACCESS  read-only
    STATUS      current
    DESCRIPTION
      "Average upstream bandwidth measured over a certain time period."
    ::= { ngEventDataUsageObjects 13 }

evDataDown6 OBJECT-TYPE
    SYNTAX  Unsigned32
    MAX-ACCESS  read-only
    STATUS      current
    DESCRIPTION
      "Average downstream bandwidth measured over a certain time period."
    ::= { ngEventDataUsageObjects 14 }

evDataUp7 OBJECT-TYPE
    SYNTAX      Unsigned32
    MAX-ACCESS  read-only
    STATUS      current
    DESCRIPTION
      "Average upstream bandwidth measured over a certain time period."
    ::= { ngEventDataUsageObjects 15 }

evDataDown7 OBJECT-TYPE
    SYNTAX  Unsigned32
    MAX-ACCESS  read-only
    STATUS      current
    DESCRIPTION
      "Average downstream bandwidth measured over a certain time period."
    ::= { ngEventDataUsageObjects 16 }

evDataUp8 OBJECT-TYPE
    SYNTAX      Unsigned32
    MAX-ACCESS  read-only
    STATUS      current
    DESCRIPTION
      "Average upstream bandwidth measured over a certain time period."
    ::= { ngEventDataUsageObjects 17 }

evDataDown8 OBJECT-TYPE
    SYNTAX  Unsigned32
    MAX-ACCESS  read-only
    STATUS      current
    DESCRIPTION
      "Average downstream bandwidth measured over a certain time period."
    ::= { ngEventDataUsageObjects 18 }

evDataUp9 OBJECT-TYPE
    SYNTAX      Unsigned32
    MAX-ACCESS  read-only
    STATUS      current
    DESCRIPTION
      "Average upstream bandwidth measured over a certain time period."
    ::= { ngEventDataUsageObjects 19 }

evDataDown9 OBJECT-TYPE
    SYNTAX  Unsigned32
    MAX-ACCESS  read-only
    STATUS      current
    DESCRIPTION
      "Average downstream bandwidth measured over a certain time period."
    ::= { ngEventDataUsageObjects 20 }

evDataUp10 OBJECT-TYPE
    SYNTAX      Unsigned32
    MAX-ACCESS  read-only
    STATUS      current
    DESCRIPTION
      "Average upstream bandwidth measured over a certain time period."
    ::= { ngEventDataUsageObjects 21 }

evDataDown10 OBJECT-TYPE
    SYNTAX  Unsigned32
    MAX-ACCESS  read-only
    STATUS      current
    DESCRIPTION
      "Average downstream bandwidth measured over a certain time period."
    ::= { ngEventDataUsageObjects 22 }

evDataUp11 OBJECT-TYPE
    SYNTAX      Unsigned32
    MAX-ACCESS  read-only
    STATUS      current
    DESCRIPTION
      "Average upstream bandwidth measured over a certain time period."
    ::= { ngEventDataUsageObjects 23 }

evDataDown11 OBJECT-TYPE
    SYNTAX  Unsigned32
    MAX-ACCESS  read-only
    STATUS      current
    DESCRIPTION
      "Average downstream bandwidth measured over a certain time period."
    ::= { ngEventDataUsageObjects 24 }

evDataUp12 OBJECT-TYPE
    SYNTAX      Unsigned32
    MAX-ACCESS  read-only
    STATUS      current
    DESCRIPTION
      "Average upstream bandwidth measured over a certain time period."
    ::= { ngEventDataUsageObjects 25 }

evDataDown12 OBJECT-TYPE
    SYNTAX  Unsigned32
    MAX-ACCESS  read-only
    STATUS      current
    DESCRIPTION
      "Average downstream bandwidth measured over a certain time period."
    ::= { ngEventDataUsageObjects 26 }

--
-- Individual events (traps/informs).
--
ngevIpConntrackTable NOTIFICATION-TYPE
    OBJECTS { ngevMac, ngevIpConntrackCurrentPercentage,
              ngevIpConntrackMaxPercentage, evTrapCreatedTime }
    STATUS  current
    DESCRIPTION
             "Sent if the Firewall Connection table reaches
              the specified threshold."
    ::= { ngEventNotification 1 }

ngevIpConntrackTableFull NOTIFICATION-TYPE
    OBJECTS { ngevMac, evTrapCreatedTime }
    STATUS  current
    DESCRIPTION
            "Indicates the firewall Connection table has reached
             capacity."
    ::= { ngEventNotification 2 }

ngevExcessiveDial NOTIFICATION-TYPE
    OBJECTS { ngevMac, ngevTimeInDial, 
              ngifTimeInDial, ngevMaxTimeInDialUntilAlert,
              ngifActiveWanIface, evTrapCreatedTime
            }
    STATUS  current
    DESCRIPTION
            "The device has been in dial backup longer than
             the allowed threshold."
    ::= { ngEventNotification 3 }

ngevActiveWanIpChanged NOTIFICATION-TYPE
    OBJECTS { ngevMac, ngifActiveWanIface, ngevActiveWanIp, 
              ngevIPv6ActiveWanIp, nghwCodeVersion, evTrapCreatedTime
            }
    STATUS  current
    DESCRIPTION
            "The IP address associated with the active WAN interface
             has changed.  For example, dial backup was initiated
             because WAN connectivity was lost.  Another example
             is that a PPPoE connection changed its IP address."
    ::= { ngEventNotification 4 }

ngevRogueMacDetected NOTIFICATION-TYPE
    OBJECTS { ngevMac, ngevRogueMac, ngevRogueIp, 
              ngevRogueInterface, ngevTrapDescription,
              ngevIPv6RogueIp, evTrapCreatedTime }
    STATUS  current
    DESCRIPTION
            "The unauthorized MAC detection feature is enabled and 
             an unauthorized MAC address was detected."
    ::= { ngEventNotification 5 }

ngevRogueMacNoFile NOTIFICATION-TYPE
    OBJECTS { ngevMac, evTrapCreatedTime }
    STATUS  current
    DESCRIPTION
            "The unauthorized MAC detection feature is enabled and 
             the authorized MAC file doesn't exist."
    ::= { ngEventNotification 6 }

ngevNoTeps NOTIFICATION-TYPE
    OBJECTS { ngevMac, ngtuIpsecIface, evTrapCreatedTime }
    STATUS  current
    DESCRIPTION
            "The AT&T VPN Gateway cannot bring up a tunnel to any of the 
             tunnel endpoints."
    ::= { ngEventNotification 7 }

ngevDeviceDiscoOrNotFound NOTIFICATION-TYPE
    OBJECTS { ngevMac, ngevQueryProblem, evTrapCreatedTime }
    STATUS  current
    DESCRIPTION
            "Sent if the AT&T VPN Gateway profile is not found.
             If the AT&T VPN Gateway goes too long without 
             finding its device profile then the device will 
             switch its status to discontinued, which will
             also trigger a trap/inform."
    ::= { ngEventNotification 8 }

ngevTunnelUp NOTIFICATION-TYPE
    OBJECTS { ngevMac, ngevTunConnectionId, 
              ngevTunnelDateAndTime, ngtuTunMode,
              ngevConnectionType, ngevAccount, ngevUserid,
              ngtuEndpoint, ngtuAuthType, ngtuAuthProt,
              ngtuEndpointType, ngevTunConReason, 
              nghwWanConnectionMethod, ngtuTunInitiator,
              ngtuIpsecIface, ngtuIPv6Endpoint,
              ngevVPNServiceIPv4Address, ngevVPNServiceIPv6Address,
              ngevTunConReasonNUM, tunName, tunDirection,
              evNatTEnabled, evESPAlgorithm, evAuthAlgorithm, 
              evCompressionAlgorithm
            }
    STATUS  current
    DESCRIPTION
            "Information about the results of a tunnel connection attempt."
    ::= { ngEventNotification 9 }

ngevTunnelDown NOTIFICATION-TYPE
    OBJECTS { ngevMac, ngevTunConnectionId, 
              ngevTunnelDateAndTime, ngtuReasonCode, ngtuEndpoint,
              ngtuIPv6Endpoint, ngevVPNServiceIPv4Address,
              ngevVPNServiceIPv6Address, tunName, ngtuTunMode,
              tunDirection
            }
    STATUS  current
    DESCRIPTION
            "Information about a tunnel disconnect.
             The one exception is a tunnel 'alive' message,
             which is sent for a tunnel that is still up.
             Tunnel 'alive' messages have a ngtuReasonCode
             of tnlAlive."
    ::= { ngEventNotification 10 }

ngevDialAutotestFailure NOTIFICATION-TYPE
    OBJECTS { ngevMac, ngevDialTestFailReason,
              ngevDialTestFailCategory, evTrapCreatedTime, ng3gModemType }
    STATUS  current
    DESCRIPTION
            "The Dial Autotest (and all specified retries) failed."
    ::= { ngEventNotification 11 }

ngevDeviceReboot NOTIFICATION-TYPE
    OBJECTS { ngevMac, ngevRequestorIp, ngevIPv6RequestorIp,
              evTrapCreatedTime }
    STATUS  current
    DESCRIPTION
            "Sent when the device reboots. Requestor IP
             will be set to loopback if an automated process 
             caused the reboot."
    ::= { ngEventNotification 12 }

ngevDeviceShutdown NOTIFICATION-TYPE
    OBJECTS { ngevMac, ngevRequestorIp, ngevIPv6RequestorIp,
              evTrapCreatedTime }
    STATUS  current
    DESCRIPTION
            "Sent when the device shuts down."
    ::= { ngEventNotification 13 }

ngevSshLogin NOTIFICATION-TYPE
    OBJECTS { ngevMac, ngevSshSourceIp, ngevIPv6RequestorIp, 
              evTrapCreatedTime, ngevLoginResult }
    STATUS  current
    DESCRIPTION
            "Sent when a user accesses the device via SSH."
    ::= { ngEventNotification 14 }

ngevDhcpPoolExhausted NOTIFICATION-TYPE
    OBJECTS { ngevMac, ngvlId, evTrapCreatedTime }
    STATUS  current
    DESCRIPTION
            "Sent when a VLAN's DHCP pool is full."
    ::= { ngEventNotification 15 }

ngevForTestingOnly NOTIFICATION-TYPE
    OBJECTS { ngevMac, ngevTunConReason,
              ngevTunnelDateAndTime
            }
    STATUS  current
    DESCRIPTION
            "Only for use by QA and development for testing."
    ::= { ngEventNotification 16 }

ngevSecondaryAuthAttempt NOTIFICATION-TYPE
    OBJECTS { ngevMac, ngevRequestorIp, ngevAccount, ngevUserid,
              ngevLoginResult, ngevNewLocalID, ngevIPv6RequestorIp,
              evTrapCreatedTime
            }
    STATUS  current
    DESCRIPTION
            "Sent when a secondary login attempt occurs. Secondary logins are 
             performed when someone tries to ssh into the AT&T VPN Gateway."
    ::= { ngEventNotification 17 }

ngevSwitchUseridAttempt NOTIFICATION-TYPE
    OBJECTS { ngevMac, ngevRequestorIp, ngevAccount, ngevUserid,
              ngevLoginResult, ngevNewLocalID, ngevOldLocalID, ngevIPv6RequestorIp,
              evTrapCreatedTime
            }
    STATUS  current
    DESCRIPTION
            "Sent when a user who is ssh'ed into the AT&T VPN Gateway tries to
             switch to another userid."
    ::= { ngEventNotification 18 }

ngev8200VPortDown NOTIFICATION-TYPE
    OBJECTS { ngevMac, ngevPortDown, evTrapCreatedTime
            }
    STATUS  current
    DESCRIPTION
            "Sent when either port 7 or 8 is determined to be not active.
             Only used by the AT&T VPN Gateway 8200V."
    ::= { ngEventNotification 19 }

ngevCellModemRequired NOTIFICATION-TYPE
    OBJECTS { ngevMac, ng3gModel, ng3gManufacturer, ng3gID,
              ng3gRevision, ng3gSIMCardNumber, ng3gPhoneNum,
              ngevCardNotFoundTime
            }
    STATUS  current
    DESCRIPTION
            "Sent when either the AT&T VPN Gateway boots without a cell modem
             present or when the AT&T VPN Gateway detects that the cell modem
             has been removed. The cellular modem must be a supported unit
             that allows the AT&T VPN Gateway to query its current status."
    ::= { ngEventNotification 20 }

evVrrpStateChange NOTIFICATION-TYPE
    OBJECTS { ngevMac, ngvlId, ngvrId, ngvrMasterStatus, evTrapCreatedTime
            }
    STATUS  current
    DESCRIPTION
            "Sent when there is a VRRP state change."
    ::= { ngEventNotification 21 }

evDualWanIfaceProblem NOTIFICATION-TYPE
    OBJECTS { ngevMac, evDualWanProb, evDualWanV6Prob, evTrapCreatedTime
            }
    STATUS  current
    DESCRIPTION
            "Sent when the AT&T VPN Gateway is configured to also use the second
             WAN port as Internet Primary and one of the interfaces could not 
             be brought up." 
    ::= { ngEventNotification 22 }

evOOBCableRequired NOTIFICATION-TYPE
    OBJECTS { ngevMac, evNotFoundTime, evFoundOOB, evExpectedOOB
            }
    STATUS  current
    DESCRIPTION
            "Optional USB cables allow out of bound (OOB) access to the 
             AT&T VPN Gateway. The number of OOB cables expected to be 
             plugged into the AT&T VPN Gateway is controlled by a setting 
             in Service Manager. This event is sent when either the 
             AT&T VPN Gateway boots without the expected number of cables 
             present, when the AT&T VPN Gateway detects that a cable was 
             present but has been removed, or when all missing cables are 
             returned."
    ::= { ngEventNotification 23 }

evTunConfigChanged NOTIFICATION-TYPE
    OBJECTS { ngevMac, evTrapCreatedTime
            }
    STATUS  current
    DESCRIPTION
            "Sent when the tunnel configuration has changed. All tunnels (if
             any) are restarted when this occurs."
    ::= { ngEventNotification 24 }

evDataUsageReport NOTIFICATION-TYPE
    OBJECTS { ngevMac, evTrapCreatedTime, 
              evDataUpHwm, evDataDownHwm,
              evDataUp1, evDataUp2, evDataUp3, evDataUp4, evDataUp5, evDataUp6,
              evDataUp7, evDataUp8, evDataUp9, evDataUp10, evDataUp11, evDataUp12,
              evDataDown1, evDataDown2, evDataDown3, evDataDown4, evDataDown5, evDataDown6,
              evDataDown7, evDataDown8, evDataDown9, evDataDown10, evDataDown11, evDataDown12
            }
    STATUS  current
    DESCRIPTION
            "Reporting of average bandwidth along with high water mark calculations."
    ::= { ngEventNotification 25 }

evPingTestResult NOTIFICATION-TYPE
    OBJECTS { ngevMac, evTrapCreatedTime, evResult, evSrcV4, evDestV4,
              evSrcV6, evDestV6, evResponseMax, evFailureCount,
              evDescription, evSendTrapWhen
            }
    STATUS  current
    DESCRIPTION
            "Sent to indicate the result of a ping test."
    ::= { ngEventNotification 26 }

evNoIPinCDPool NOTIFICATION-TYPE
    OBJECTS { ngevMac, evTrapCreatedTime
            }
    STATUS  current
    DESCRIPTION
            "Sent to indicate that there are no available IP addresses in the customer direct pool."
    ::= { ngEventNotification 27 }

evMaxInbTun NOTIFICATION-TYPE
    OBJECTS { ngevMac, evTrapCreatedTime
            }
    STATUS  current
    DESCRIPTION
            "Sent to indicate that there are no inbound tunnels available."
    ::= { ngEventNotification 28 }

evReportDualWanIP NOTIFICATION-TYPE
    OBJECTS { ngevMac, evTrapCreatedTime, 
              evWan1IPv4Name, evWan1IPv6Name,
              evWan1IPv4IP, evWan1IPv6IP,
              evWan2IPv4Name, evWan2IPv6Name,
              evWan2IPv4IP, evWan2IPv6IP
            }
    STATUS  current
    DESCRIPTION
            "Sent to report on the IP addresses in use when both Dual WAN 
             interfaces are up."
    ::= { ngEventNotification 29 }

--
-- Trap/inform compliance groups.
--
ngevBasicComplianceRev MODULE-COMPLIANCE
    STATUS  current
    DESCRIPTION
            "The compliance statement for AT&T VPN Gateway entities
             which implement this MIB module."
    MODULE  -- this module
        MANDATORY-GROUPS { ngevNotificationsGroup, ngevObjectsGroup,
                           ngEventDataUsageObjectsGroup }
    ::= { ngEventCompliances 1 }

ngevNotificationsGroup  NOTIFICATION-GROUP
    NOTIFICATIONS {
                    ngevIpConntrackTable, ngevIpConntrackTableFull,
                    ngevExcessiveDial, ngevActiveWanIpChanged,
                    ngevRogueMacDetected, ngevRogueMacNoFile,
                    ngevNoTeps, ngevDeviceDiscoOrNotFound,
                    ngevTunnelUp, ngevTunnelDown,
                    ngevDialAutotestFailure, ngevDeviceReboot,
                    ngevDeviceShutdown, ngevSshLogin,
                    ngevDhcpPoolExhausted, ngevForTestingOnly,
                    ngevSecondaryAuthAttempt, ngevSwitchUseridAttempt,
                    ngev8200VPortDown, ngevCellModemRequired,
                    evVrrpStateChange, evDualWanIfaceProblem,
                    evOOBCableRequired, evTunConfigChanged,
                    evDataUsageReport, evPingTestResult,
                    evNoIPinCDPool, evMaxInbTun,
                    evReportDualWanIP
                  }
    STATUS  current
    DESCRIPTION
            "The event notifications"
    ::= { ngEventGroups 1 }

ngevObjectsGroup   OBJECT-GROUP
    OBJECTS { ngevMac, ngevRogueMac, ngevActiveWanIp, 
              ngevIpConntrackMaxPercentage, ngevIpConntrackCurrentPercentage,
              ngevTimeInDial, ngevQueryProblem, ngevTunConnectionId,
              ngevConnectionType,
              ngevAccount, ngevUserid, ngevTunConReason,
              ngevDialTestFailReason, ngevSshSourceIp, 
              ngevTunnelDateAndTime, ngevRequestorIp,
              ngevDialTestFailCategory, ngevRogueIp,
              ngevRogueInterface, ngevTrapDescription,
              ngevMaxTimeInDialUntilAlert,
              ngevLoginResult, ngevNewLocalID,
              ngevOldLocalID, ngevPortDown,
              ngevIPv6ActiveWanIp, ngevIPv6RogueIp,
              ngevIPv6RequestorIp, ngevCardNotFoundTime,
              ngevVPNServiceIPv4Address, ngevVPNServiceIPv6Address,
              ngevTunConReasonNUM, evIface, evNotFoundTime,
              evTrapCreatedTime, evDualWanProb,
              evDualWanV6Prob, evFoundOOB, evExpectedOOB,
              evResult, evSrcV4, evDestV4,
              evSrcV6, evDestV6,
              evResponseMax, evFailureCount, evDescription,
              evSendTrapWhen, 
              evWan1IPv4IP, evWan1IPv6IP, evWan2IPv4IP, evWan2IPv6IP,
              evWan1IPv4Name, evWan1IPv6Name,
              evWan2IPv4Name, evWan2IPv6Name,
              evNatTEnabled, evESPAlgorithm, evAuthAlgorithm,
              evCompressionAlgorithm
            }
    STATUS  current
    DESCRIPTION
            "The event ojects."
    ::= { ngEventGroups 2 }

ngEventDataUsageObjectsGroup OBJECT-GROUP
    OBJECTS {
              evDataUpHwm, evDataDownHwm,
              evDataUp1, evDataUp2, evDataUp3, evDataUp4, evDataUp5, evDataUp6,
              evDataUp7, evDataUp8, evDataUp9, evDataUp10, evDataUp11, evDataUp12,
              evDataDown1, evDataDown2, evDataDown3, evDataDown4, evDataDown5, evDataDown6,
              evDataDown7, evDataDown8, evDataDown9, evDataDown10, evDataDown11, evDataDown12
            }
    STATUS  current
    DESCRIPTION
            "The event ojects used only for data usage statistics."
    ::= { ngEventGroups 3 }

-- 
-- Hardware Platform Designations for sysObjectID
-- 
attVpnGateway8200         OBJECT IDENTIFIER ::= { ngPlatforms 1}
attVpnGateway8300         OBJECT IDENTIFIER ::= { ngPlatforms 2}
attVpnGatewayVM           OBJECT IDENTIFIER ::= { ngPlatforms 3}

END
