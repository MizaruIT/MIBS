--
-- HW-IMAPV1NORTHBOUND-TRAP-MIB.mib
-- MIB generated by MG-SOFT Visual MIB Builder Version 4.0 Build 349
--
-- =================================================================   
-- Copyright (C) 2010 by HUAWEI TECHNOLOGIES. All rights reserved
--
-- Description	: This MIB defines the managed objects that are used
--                 by the function interfaces of the SNMP Northbound 
--                 Interface. The definitions decide what operations
--                 the NMS can do and what network management 
--                 information the NMS can obtain.
-- Reference	: 
-- Version		: V2.00
-- History		:
-- <Huawei Technologies Ltd.>,<Created>
-- =================================================================
--  
	HW-IMAPV2NORTHBOUND-TRAP-MIB DEFINITIONS ::= BEGIN
 
		IMPORTS
			OBJECT-GROUP, MODULE-COMPLIANCE, NOTIFICATION-GROUP			
				FROM SNMPv2-CONF			
			enterprises, Integer32, OBJECT-TYPE, MODULE-IDENTITY, OBJECT-IDENTITY, 
			NOTIFICATION-TYPE			
				FROM SNMPv2-SMI;
	
-- This MIB defines the managed objects that are used
-- by the function interfaces of the SNMP Northbound 
-- Interface.
		huawei MODULE-IDENTITY 
			LAST-UPDATED "201011241000Z"
			ORGANIZATION 
				"HUAWEI"
			CONTACT-INFO 
				"HUAWEI Technologies"
			DESCRIPTION 
				"This MIB defines the managed objects that are used
				by the function interfaces of the SNMP Northbound 
				Interface."
			::= { enterprises 2011 }
			
--  Node definitions

		-- 1.3.6.1.4.1.2011.2
		products OBJECT IDENTIFIER ::= { huawei 2 }


		-- 1.3.6.1.4.1.2011.2.15
		hwNetManagement OBJECT IDENTIFIER ::= { products 15 }


		-- 1.3.6.1.4.1.2011.2.15.1
		hwNmAgent OBJECT IDENTIFIER ::= { hwNetManagement 1 }

		
		-- 1.3.6.1.4.1.2011.2.15.1.3
		hwNmFault OBJECT IDENTIFIER ::= { hwNmAgent 3 }

		
-- Name        	: thirdNMSFaultFilter 
-- Description	: This provides the functionality of changing the alarm level and alarm category filters.
-- Type     	: Octet string
-- OID			: 1.3.6.1.4.1.2011.2.15.1.3.5
		thirdNMSFaultFilter OBJECT-TYPE
			SYNTAX OCTET STRING (SIZE (1..255))
			MAX-ACCESS read-write
			STATUS current
			DESCRIPTION
					"IP:Port:AlarmLevelFilter:AlarmCategoryFilter
					AlarmLevelFilter = xxxx (Critical, Major, Minor, Warning) (1 - filter, 0 - report)
					AlarmCategoryFilter = yyyyyy (Event, Fault, Recovery, Acknowledge, UnAcknowledge, Change) (1 - filter, 0 - report)
					Both AlarmLevelFilter and AlarmCategoryFilter are optional and both or any one can be set
					E.g.: 10.18.17.28:9999:0110:100000
					Only events of major and minor severity will be send to the OSS [10.18.17.28:9999] and rest filtered.
					The format to specify only AlarmLevelFilter is:
					10.18.17.28:9999:0110
					The format to specify only AlarmCategoryFilter is:
					10.18.17.28:9999::100000
					
					Get attempt on this node will result in error."		
					
			::= { hwNmFault 5 }
          
-- Name        	: hwNmClearAlarms 
-- Description	: This provides the functionality of clearing alarms to third party NMS.
-- Type     	: Octet string
-- OID			: 1.3.6.1.4.1.2011.2.15.1.3.6
		hwNmClearAlarms OBJECT-TYPE
			SYNTAX OCTET STRING (SIZE (1..2048))
			MAX-ACCESS read-write
			STATUS current
			DESCRIPTION
				"This provides the functionality of clearing alarms to third party NMS.
				The alarms can be cleared based on alarm serial number.
				Multiple serial numbers are separated by comma(,).
				Alarms serial number(s)are of type unsigned long and
				incompatible types are automatically considered
				as invalid serial number(s). Get attempt on this node
				will result in error.
				
				Output: Serial number(s) of alarms which could not be
				cleared. This also contains Alarm serial number(s)
				with incorrect syntax.  If all alarms are successfully
				cleared then output is blank."
			::= { hwNmFault 6 }


-- Name        	: hwNmAcknowledgeAlarms 
-- Description	: This provides the functionality of acknowledging alarms to third party NMS.
-- Type     	: Octet string
-- OID			: 1.3.6.1.4.1.2011.2.15.1.3.7
		hwNmAcknowledgeAlarms OBJECT-TYPE
			SYNTAX OCTET STRING (SIZE (1..2048))
			MAX-ACCESS read-write
			STATUS current
			DESCRIPTION
				"This provides the functionality of acknowledging alarms to third party NMS.
				The alarms can be acknowledged based on alarm serial number.
				Multiple serial numbers are separated by comma(,).
				Alarms serial number(s) are of type unsigned long and
				incompatible types are automatically considered
				as invalid serial number(s). Get attempt on this node
				will result in error.

				Output: Serial number(s) of alarms which could not be
				acknowledged. This also contains Alarm serial number(s)
				with incorrect syntax.  If all alarms are successfully
				acknowledged then output is blank."
			::= { hwNmFault 7 }

		
-- Name        	: hwNmUnAcknowledgeAlarms 
-- Description	: This provides the functionality of unacknowledging alarms to third party NMS.
-- Type     	: Octet string
-- OID			: 1.3.6.1.4.1.2011.2.15.1.3.8
		hwNmUnAcknowledgeAlarms OBJECT-TYPE
			SYNTAX OCTET STRING (SIZE (1..2048))
			MAX-ACCESS read-write
			STATUS current
			DESCRIPTION
				"This provides the functionality of unacknowledging alarms to third party NMS.
				The alarms can be unacknowledged based on alarm serial number.
				Multiple serial numbers are separated by comma(,).
				Alarms serial number(s) are of type unsigned long and
				incompatible types are automatically considered
				as invalid serial number(s). Get attempt on this node
				will result in error.
				
				Output: Serial number(s) of alarms which could not be
				unacknowledged. This also contains Alarm serial number(s)
				with incorrect syntax.  If all alarms are successfully
				unacknowledged then output is blank."
			::= { hwNmFault 8 }


		-- 1.3.6.1.4.1.2011.2.15.1.7
		hwNmNorthboundEvent OBJECT IDENTIFIER ::= { hwNmAgent 7 }


		-- 1.3.6.1.4.1.2011.2.15.1.7.1
		hwNmNorthboundEventInfo OBJECT IDENTIFIER ::= { hwNmNorthboundEvent 1 }
		
		hwNmNorthboundEventTrap OBJECT-IDENTITY
			STATUS current
			DESCRIPTION 
				"Event Traps"
			::= { hwNmNorthboundEventInfo 0 }

		
-- Name        	: hwNmNorthboundNEName 
-- Description	: The name of network element
-- Type     	: Octet string  (SIZE (1..255))
-- OID			: 1.3.6.1.4.1.2011.2.15.1.7.1.1
	
			hwNmNorthboundNEName OBJECT-TYPE
			SYNTAX OCTET STRING (SIZE (1..255))
			MAX-ACCESS read-only
			STATUS current
			DESCRIPTION
				"The name of network element,string (255)"
			::= { hwNmNorthboundEventInfo 1 }

		
-- Name        	: hwNmNorthboundNEType 
-- Description	: Device type of element
-- Type     	: Octet string  (SIZE (1..64))
-- OID			: 1.3.6.1.4.1.2011.2.15.1.7.1.2
		hwNmNorthboundNEType OBJECT-TYPE
			SYNTAX OCTET STRING (SIZE (0..64))
			MAX-ACCESS read-only
			STATUS current
			DESCRIPTION
				"Device type of element,string(64)"
			::= { hwNmNorthboundEventInfo 2 }

-- Name        	: hwNmNorthboundObjectInstance 
-- Description	: Instance of element,such as number of Rack, Frame, Slot, Subslot, Port and so on
-- Type     	: Octet string  (SIZE (1..255))
-- OID			: 1.3.6.1.4.1.2011.2.15.1.7.1.3
		hwNmNorthboundObjectInstance OBJECT-TYPE
			SYNTAX OCTET STRING (SIZE (0..255))
			MAX-ACCESS read-only
			STATUS current
			DESCRIPTION
				"Instance of element,such as number of Rack, Frame, Slot, Subslot, Port and so on,string(255)"
			::= { hwNmNorthboundEventInfo 3 }

		
-- Name        	: hwNmNorthboundEventType 
-- Description	: Event type 
-- Type     	: Octet string  (SIZE (1..64))
-- OID			: 1.3.6.1.4.1.2011.2.15.1.7.1.4
		hwNmNorthboundEventType OBJECT-TYPE
			SYNTAX OCTET STRING (SIZE (0..64))
			MAX-ACCESS read-only
			STATUS current
			DESCRIPTION
				"Type of Event,string(64)"
			::= { hwNmNorthboundEventInfo 4 }

		
-- Name        	: hwNmNorthboundEventTime 
-- Description	: Time at which the alarm was generated
-- Type     	: Octet string  (SIZE (1..64))
-- OID			: 1.3.6.1.4.1.2011.2.15.1.7.1.5
		hwNmNorthboundEventTime OBJECT-TYPE
			SYNTAX OCTET STRING (SIZE (0..64))
			MAX-ACCESS read-only
			STATUS current
			DESCRIPTION
				"Time at which the alarm was generated,string(64).
				It can be of any of the following formats:
				1. Local Time without timezone information - 'YYYY/MM/DD - hh:mm:ss'
				2. UTC Time - 'YYYY/MM/DD - hh:mm:ssZ'
				3. Local Time with timezone information - 'YYYY/MM/DD - hh:mm:ss,hh:mmTZ[DST]'
				   where TZ stands for timezone information."
			::= { hwNmNorthboundEventInfo 5 }

		
-- Name        	: hwNmNorthboundProbableCause 
-- Description	: Probable cause of the alarm
-- Type     	: Octet string  
-- OID			: 1.3.6.1.4.1.2011.2.15.1.7.1.6
		hwNmNorthboundProbableCause OBJECT-TYPE
			SYNTAX OCTET STRING (SIZE (0..4096))
			MAX-ACCESS read-only
			STATUS current
			DESCRIPTION
				"Probable cause of the alarm, string(255)"
			::= { hwNmNorthboundEventInfo 6 }

		
-- Name        	: hwNmNorthboundSeverity 
-- Description	: Level of Alarm
-- Type     	: Octet string  (SIZE (1..64))
-- OID			: 1.3.6.1.4.1.2011.2.15.1.7.1.7
		hwNmNorthboundSeverity OBJECT-TYPE
			SYNTAX OCTET STRING (SIZE (0..64))
			MAX-ACCESS read-only
			STATUS current
			DESCRIPTION
				"Level of Alarm., string(64)
				It can be any of the following: Critical, Major, Minor, Warning, Indeterminate."
			::= { hwNmNorthboundEventInfo 7 }

		
-- Name        	: hwNmNorthboundEventDetail 
-- Description	: Alarm ID and detail information
-- Type     	: Octet string  (SIZE (0..4096))
-- OID			: 1.3.6.1.4.1.2011.2.15.1.7.1.8
		hwNmNorthboundEventDetail OBJECT-TYPE
			SYNTAX OCTET STRING (SIZE (0..4096))
			MAX-ACCESS read-only
			STATUS current
			DESCRIPTION
				"Alarm ID and detail information, string(4096)"
			::= { hwNmNorthboundEventInfo 8 }

		
-- Name        	: hwNmNorthboundAdditionalInfo 
-- Description	: Additional infomation of device, such as Country, City and so on
-- Type     	: Octet string  (SIZE (1..255))
-- OID			: 1.3.6.1.4.1.2011.2.15.1.7.1.9
		hwNmNorthboundAdditionalInfo OBJECT-TYPE
			SYNTAX OCTET STRING (SIZE (0..255))
			MAX-ACCESS read-only
			STATUS current
			DESCRIPTION
				"Additional information of device, such as Country, City and so on, string(255)"
			::= { hwNmNorthboundEventInfo 9 }

		
-- Name        	: hwNmNorthboundFaultFlag 
-- Description	: Fault Flag
-- Type     	: Octet string  (SIZE (1..64))
-- OID			: 1.3.6.1.4.1.2011.2.15.1.7.1.10
		hwNmNorthboundFaultFlag OBJECT-TYPE
			SYNTAX OCTET STRING (SIZE (0..64))
			MAX-ACCESS read-only
			STATUS current
			DESCRIPTION
				"The flag which specifies whether the alarm is an Event, Fault, Recovery, Acknowledge
				Unacknowledge or Change."
			::= { hwNmNorthboundEventInfo 10 }

		
-- Name        	: hwNmNorthboundFaultFunction 
-- Description	: The function type of alarm.
-- Type     	: Octet string  (SIZE (1..64))
-- OID			: 1.3.6.1.4.1.2011.2.15.1.7.1.11
		hwNmNorthboundFaultFunction OBJECT-TYPE
			SYNTAX OCTET STRING (SIZE (0..64))
			MAX-ACCESS read-only
			STATUS current
			DESCRIPTION
				"The function type of the alarm.It can be one of these values:'Power','Environment','Signal','Relay','Hardware','Software','Run','Communication','Service','Processerror','UNKNOWN_FUNC_TYPE'"
			::= { hwNmNorthboundEventInfo 11 }

		
-- Name        	: hwNmNorthboundDeviceIP 
-- Description	: IP address of the device
-- Type     	: IpAddress
-- OID			: 1.3.6.1.4.1.2011.2.15.1.7.1.12
		hwNmNorthboundDeviceIP OBJECT-TYPE
			SYNTAX IpAddress
			MAX-ACCESS read-only
			STATUS current
			DESCRIPTION
				"IP address of the device"
			::= { hwNmNorthboundEventInfo 12 }

		
-- Name        	: hwNmNorthboundSerialNo 
-- Description	: The serial number of alarm.
-- Type     	: Integer32
-- OID			: 1.3.6.1.4.1.2011.2.15.1.7.1.13
		hwNmNorthboundSerialNo OBJECT-TYPE
			SYNTAX Integer32
			MAX-ACCESS read-only
			STATUS current
			DESCRIPTION
				"The serial number of alarm."
			::= { hwNmNorthboundEventInfo 13 }

		
-- Name        	: hwNmNorthboundProbableRepair 
-- Description	: Alarm repair recommendations.
-- Type     	: Octet string  (SIZE (0..4096))
-- OID			: 1.3.6.1.4.1.2011.2.15.1.7.1.14
		hwNmNorthboundProbableRepair OBJECT-TYPE
			SYNTAX OCTET STRING (SIZE (0..4096))
			MAX-ACCESS read-only
			STATUS current
			DESCRIPTION
				"Alarm repair recommendations."
			::= { hwNmNorthboundEventInfo 14 }

		
-- Name        	: hwNmNorthboundResourceIDs 
-- Description	: The ID of the resource.
-- Type     	: Octet string  (SIZE (1..255))
-- OID			: 1.3.6.1.4.1.2011.2.15.1.7.1.15
		hwNmNorthboundResourceIDs OBJECT-TYPE
			SYNTAX OCTET STRING (SIZE (1..255))
			MAX-ACCESS read-only
			STATUS current
			DESCRIPTION
				"The ID of the resource."
			::= { hwNmNorthboundEventInfo 15 }

		
-- Name        	: hwNmNorthboundsAdditionalVB1 
-- Description	: Additional information of the alarm
-- Type     	: Octet string  (SIZE (1..255))
-- OID			: 1.3.6.1.4.1.2011.2.15.1.7.1.16
		hwNmNorthboundsAdditionalVB1 OBJECT-TYPE
			SYNTAX OCTET STRING (SIZE (1..255))
			MAX-ACCESS read-only
			STATUS current
			DESCRIPTION
				"Additional information of the alarm. These 8 fields are decided by configuration in snmpsvc.xml"
			::= { hwNmNorthboundEventInfo 16 }

		
-- Name        	: hwNmNorthboundsAdditionalVB2 
-- Description	: Additional information of the alarm
-- Type     	: Octet string  (SIZE (1..255))
-- OID			: 1.3.6.1.4.1.2011.2.15.1.7.1.17
		hwNmNorthboundsAdditionalVB2 OBJECT-TYPE
			SYNTAX OCTET STRING (SIZE (1..255))
			MAX-ACCESS read-only
			STATUS current
			DESCRIPTION
				"Additional information of the alarm. These 8 fields are decided by configuration in snmpsvc.xml"
			::= { hwNmNorthboundEventInfo 17 }

		
-- Name        	: hwNmNorthboundsAdditionalVB3 
-- Description	: Additional information of the alarm
-- Type     	: Octet string  (SIZE (1..255))
-- OID			: 1.3.6.1.4.1.2011.2.15.1.7.1.18
		hwNmNorthboundsAdditionalVB3 OBJECT-TYPE
			SYNTAX OCTET STRING (SIZE (1..255))
			MAX-ACCESS read-only
			STATUS current
			DESCRIPTION
				"Additional information of the alarm. These 8 fields are decided by configuration in snmpsvc.xml"
			::= { hwNmNorthboundEventInfo 18 }

		
-- Name        	: hwNmNorthboundsAdditionalVB4 
-- Description	: Additional information of the alarm
-- Type     	: Octet string  (SIZE (1..255))
-- OID			: 1.3.6.1.4.1.2011.2.15.1.7.1.19
		hwNmNorthboundsAdditionalVB4 OBJECT-TYPE
			SYNTAX OCTET STRING (SIZE (1..255))
			MAX-ACCESS read-only
			STATUS current
			DESCRIPTION
				"Additional information of the alarm. These 8 fields are decided by configuration in snmpsvc.xml"
			::= { hwNmNorthboundEventInfo 19 }

		
-- Name        	: hwNmNorthboundsAdditionalVB5 
-- Description	: Additional information of the alarm
-- Type     	: Octet string  (SIZE (1..255))
-- OID			: 1.3.6.1.4.1.2011.2.15.1.7.1.20
		hwNmNorthboundsAdditionalVB5 OBJECT-TYPE
			SYNTAX OCTET STRING (SIZE (1..255))
			MAX-ACCESS read-only
			STATUS current
			DESCRIPTION
				"Additional information of the alarm. These 8 fields are decided by configuration in snmpsvc.xml"
			::= { hwNmNorthboundEventInfo 20 }

		
-- Name        	: hwNmNorthboundsAdditionalVB6 
-- Description	: Additional information of the alarm
-- Type     	: Octet string  (SIZE (1..255))
-- OID			: 1.3.6.1.4.1.2011.2.15.1.7.1.21
		hwNmNorthboundsAdditionalVB6 OBJECT-TYPE
			SYNTAX OCTET STRING (SIZE (1..255))
			MAX-ACCESS read-only
			STATUS current
			DESCRIPTION
				"Additional information of the alarm. These 8 fields are decided by configuration in snmpsvc.xml"
			::= { hwNmNorthboundEventInfo 21 }

		
-- Name        	: hwNmNorthboundsAdditionalVB7 
-- Description	: Additional information of the alarm
-- Type     	: Octet string  (SIZE (1..255))
-- OID			: 1.3.6.1.4.1.2011.2.15.1.7.1.22
		hwNmNorthboundsAdditionalVB7 OBJECT-TYPE
			SYNTAX OCTET STRING (SIZE (1..255))
			MAX-ACCESS read-only
			STATUS current
			DESCRIPTION
				"Additional information of the alarm. These 8 fields are decided by configuration in snmpsvc.xml"
			::= { hwNmNorthboundEventInfo 22 }

		
-- Name        	: hwNmNorthboundsAdditionalVB8 
-- Description	: Additional information of the alarm
-- Type     	: Octet string  (SIZE (1..255))
-- OID			: 1.3.6.1.4.1.2011.2.15.1.7.1.23
		hwNmNorthboundsAdditionalVB8 OBJECT-TYPE
			SYNTAX OCTET STRING (SIZE (1..255))
			MAX-ACCESS read-only
			STATUS current
			DESCRIPTION
				"Additional information of the alarm. These 8 fields are decided by configuration in snmpsvc.xml"
			::= { hwNmNorthboundEventInfo 23 }

		
-- Name        	: hwNmNorthboundEventName 
-- Description	: Name of the event.
-- Type     	: Octet string  (SIZE (0..4096))
-- OID			: 1.3.6.1.4.1.2011.2.15.1.7.1.24
		hwNmNorthboundEventName OBJECT-TYPE
			SYNTAX OCTET STRING (SIZE (0..4096))
			MAX-ACCESS read-only
			STATUS current
			DESCRIPTION
				"The name of event,string (4096)"
			::= { hwNmNorthboundEventInfo 24 }
			                                        
		                                        
-- Name        	: hwNmNorthboundReasonID 
-- Description	: Reason ID of the alarm
-- Type     	: Integer32
-- OID			: 1.3.6.1.4.1.2011.2.15.1.7.1.25
		hwNmNorthboundReasonID OBJECT-TYPE
			SYNTAX Integer32
			MAX-ACCESS read-only
			STATUS current
			DESCRIPTION
				"The Reason ID of the alarm"
			::= { hwNmNorthboundEventInfo 25 }    
			
-- Name        	: hwNmNorthboundFaultID 
-- Description	: Fault ID of the alarm
-- Type     	: Integer32
-- OID			: 1.3.6.1.4.1.2011.2.15.1.7.1.26
		hwNmNorthboundFaultID  OBJECT-TYPE
			SYNTAX Integer32
			MAX-ACCESS read-only
			STATUS current
			DESCRIPTION
				"The Fault ID of the alarm"
			::= { hwNmNorthboundEventInfo  26 }

                                                 
-- Name        	: hwNmNorthboundDeviceType 
-- Description	: Device Type ID of the alarm
-- Type     	: Octet string  (SIZE (1..255))
-- OID			: 1.3.6.1.4.1.2011.2.15.1.7.1.27
		hwNmNorthboundDeviceType  OBJECT-TYPE
			SYNTAX OCTET STRING (SIZE (1..255))
			MAX-ACCESS read-only
			STATUS current
			DESCRIPTION
				"The Device Type ID of the alarm"
			::= { hwNmNorthboundEventInfo  27 }

			
-- Name        	: hwNmNorthboundTrailName
-- Description	: TrailName effected by alarm
-- Type     	: Octet string  (SIZE (1..255))
-- OID			: 1.3.6.1.4.1.2011.2.15.1.7.1.28
		hwNmNorthboundTrailName  OBJECT-TYPE
			SYNTAX OCTET STRING (SIZE (1..255))
			MAX-ACCESS read-only
			STATUS current
			DESCRIPTION
				"TrailName effected by alarm"
			::= { hwNmNorthboundEventInfo  28 }


-- Name        	: hwNmNorthboundRootAlarm 
-- Description	: Specifies if the alarm is a root alarm
-- Type     	: Integer32
-- OID			: 1.3.6.1.4.1.2011.2.15.1.7.1.29
		hwNmNorthboundRootAlarm  OBJECT-TYPE
			SYNTAX Integer32
			MAX-ACCESS read-only
			STATUS current
			DESCRIPTION
				"Specifies if the alarm is a root alarm
				0 - Non-root alarm
				1 - Root alarm"
			::= { hwNmNorthboundEventInfo  29 }
			
			
-- Name        	: hwNmNorthboundGroupID 
-- Description	: Group ID of the alarm
-- Type     	: Integer32
-- OID			: 1.3.6.1.4.1.2011.2.15.1.7.1.30
		hwNmNorthboundGroupID  OBJECT-TYPE
			SYNTAX Integer32
			MAX-ACCESS read-only
			STATUS current
			DESCRIPTION
				"The Group ID of the alarm"
			::= { hwNmNorthboundEventInfo  30 }


-- Name        	: hwNmNorthboundMaintainStatus 
-- Description	: maintain status
-- Type     	: Integer32
-- OID			: 1.3.6.1.4.1.2011.2.15.1.7.1.31
		hwNmNorthboundMaintainStatus  OBJECT-TYPE
			SYNTAX Integer32
			MAX-ACCESS read-only
			STATUS current
			DESCRIPTION
				"maintain status"
			::= { hwNmNorthboundEventInfo  31 }
          	
		-- 1.3.6.1.4.1.2011.2.15.1.7.2
		hwNmNorthboundEventKeepAliveInfo OBJECT IDENTIFIER ::= { hwNmNorthboundEvent 2 }
		hwNmNorthboundEventKeepAliveInfoTrap OBJECT-IDENTITY
			STATUS current
			DESCRIPTION 
				"KeepAlive Trap"
			::= { hwNmNorthboundEventKeepAliveInfo 0 }

		
		-- 1.3.6.1.4.1.2011.2.15.1.7.7
		hwNmNorthboundEventSynchronization OBJECT IDENTIFIER ::= { hwNmNorthboundEvent 7 }

		
		-- 1.3.6.1.4.1.2011.2.15.1.7.7.1
		hwNmNorthboundEventSynchronizationStart OBJECT IDENTIFIER ::= { hwNmNorthboundEventSynchronization 1 }
		hwNmNorthboundEventSynchronizationStartTrap OBJECT-IDENTITY
			STATUS current
			DESCRIPTION 
				"Sync Start Trap"
			::= { hwNmNorthboundEventSynchronizationStart 0 }

		
		-- 1.3.6.1.4.1.2011.2.15.1.7.7.2
		hwNmNorthboundEventSynchronizationQueryResult OBJECT IDENTIFIER ::= { hwNmNorthboundEventSynchronization 2 }
		hwNmNorthboundEventSynchronizationQueryResultTrap OBJECT-IDENTITY
			STATUS current
			DESCRIPTION 
				"Sync Notification Trap"
			::= { hwNmNorthboundEventSynchronizationQueryResult 0 }

		
		-- 1.3.6.1.4.1.2011.2.15.1.7.7.3
		hwNmNorthboundEventSynchronizationEnd OBJECT IDENTIFIER ::= { hwNmNorthboundEventSynchronization 3 }
		hwNmNorthboundEventSynchronizationEndTrap OBJECT-IDENTITY
			STATUS current
			DESCRIPTION 
				"Sync End Trap"
			::= { hwNmNorthboundEventSynchronizationEnd 0 }
			
			
-- Name        	: hwNmNorthboundKeepAlive 
-- Description	: The Keep Alive variable binding
-- Type     	: OCTET STRING
-- OID			: 1.3.6.1.4.1.2011.2.15.1.7.2.1	
		hwNmNorthboundKeepAlive OBJECT-TYPE
			SYNTAX OCTET STRING
			MAX-ACCESS read-only
			STATUS current
			DESCRIPTION
				"Keep Alive"
			::= { hwNmNorthboundEventKeepAliveInfo 1 }

		
-- Name        	: hwNmNorthboundEventSynchronizationEndStatus 
-- Description	: It shows the result of alarm synchronization.
-- Type     	: INTEGER
--				{
--				normalEnd(1),
--				stopped(2),
--				error(3)
--				}
-- OID			: 1.3.6.1.4.1.2011.2.15.1.7.7.3.1
		hwNmNorthboundEventSynchronizationEndStatus OBJECT-TYPE
			SYNTAX INTEGER
				{
				normalEnd(1),
				stopped(2),
				error(3)
				}
			MAX-ACCESS read-only
			STATUS current
			DESCRIPTION
				"It shows the result of alarm synchronization.
				1 means the alarm synchronization successfully ended.
				2 means the alarm synchronization is stopped by the NMS's command.
				3 means some error occured during the alarm synchronization."
			::= { hwNmNorthboundEventSynchronizationEnd 1 }

		
-- Name        	: hwNmNorthboundEventSynchronizationEndStatusDetail 
-- Description	: The detail description of the alarm synchronization end status.
-- Type     	: OCTET STRING
-- OID			: 1.3.6.1.4.1.2011.2.15.1.7.7.3.2	
		hwNmNorthboundEventSynchronizationEndStatusDetail OBJECT-TYPE
			SYNTAX OCTET STRING (SIZE (1..255))
			MAX-ACCESS read-only
			STATUS current
			DESCRIPTION
				"The detail description of the alarm synchronization end status."
			::= { hwNmNorthboundEventSynchronizationEnd 2 }

		
-- Name        	: hwNmNorthboundEventSynchronizationCommandStart 
-- Description	: This node is to be set to start the alarm synchronization.
-- Type     	: OCTET STRING
-- OID			: 1.3.6.1.4.1.2011.2.15.1.7.7.4
		hwNmNorthboundEventSynchronizationCommandStart OBJECT-TYPE
			SYNTAX OCTET STRING (SIZE (1..255))
			MAX-ACCESS read-write
			STATUS current
			DESCRIPTION
				"This node is to be set to start the alarm synchronization.
				
				The format to query alarms is:- IP:port:start time:end time
				Query time can be UTC time, Local time or Local time with timezone.
				Syntax for start time and end time is - YYYYMMDDhhmmss. The interpretation of the start time and end time depends on 
				'AlarmTimeFormat' parameter in $IMAP_ROOT/etc/conf/snmpsvc.xml file.
				
				Query can be in any of the following formats:
				1. Local time(AlarmTimeFormat = 0):
				Format:- IP:port:start time:end time
				Here, the start time and end time will be considered to be in local time format.
				
				2. UTC time(AlarmTimeFormat = 1):
				Format:- IP:port:start time:end time
				Here, the start time and end time will be considered to be UTC format.				
				
				3. Local time with timezone(AlarmTimeFormat = 2):
				Format:- IP:port:start time:end time:timezone:dstflag
				Here, the user can mention the timezone and dst flag. 
				Format to mention timezone is +/-hh.mm
				if dstflag is 0 - DST disabled, 1- DST enabled.	
				
				Format to omit dst flag:- IP:port:start time:end time:timezone, will consider the dstflag to be 0.
				
				The agent will send alarm synchronization result to the IP and port specified which were raised between start time and end time.
				If start time and end time are missing all alarms are reported. 
				Start time and end time both are optional. 
				If end time is missing current time of the EMS is taken as end time.
				If end time is present start time is not optional, it means you cannot provide end time without specifying the start time.
				If there is already a running alarm synchronization for that IP and port,it will return a commit fail error."
			::= { hwNmNorthboundEventSynchronization 4 }

		
-- Name        	: hwNmNorthboundEventSynchronizationCommandStop 
-- Description	: This node is to be set to stop the alarm synchronization.
-- Type     	: OCTET STRING
-- OID			: 1.3.6.1.4.1.2011.2.15.1.7.7.5		
		hwNmNorthboundEventSynchronizationCommandStop OBJECT-TYPE
			SYNTAX OCTET STRING (SIZE (1..255))
			MAX-ACCESS read-write
			STATUS current
			DESCRIPTION
				"This node is to be set to stop the alarm synchronization.
				It should be set as NMS's IP:port,and the agent will stop alarm synchronization for the IP and port specified.
				If alarm synchronization is not in progress for the specified IP and port,it will return a commit fail error. "
			::= { hwNmNorthboundEventSynchronization 5 }

		
	
--
-- Trap definitions
--
	
-- Name        	: hwNmNorthboundEventNotify 
-- Description	: Notification for real-time alarm.
-- Type     	: Trap/Inform

		hwNmNorthboundEventNotify NOTIFICATION-TYPE			
			OBJECTS { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName, 
				hwNmNorthboundReasonID, hwNmNorthboundFaultID, hwNmNorthboundDeviceType, hwNmNorthboundTrailName, hwNmNorthboundRootAlarm, hwNmNorthboundGroupID,
				hwNmNorthboundMaintainStatus }
			STATUS current
			DESCRIPTION 
				"Notification for real-time alarm."
			::=  { hwNmNorthboundEventTrap 1 }

-- Name        	: hwNmNorthboundEventNotify 
-- Description	: Notification for keep alive traps.
-- Type     	: Trap/Inform

		hwNmNorthboundEventKeepAlive NOTIFICATION-TYPE
			OBJECTS { hwNmNorthboundKeepAlive }
			STATUS current			
			DESCRIPTION 
				"Notification for keep alive traps."
			::=  { hwNmNorthboundEventKeepAliveInfoTrap 2 }
 
-- Name        	: hwNmNorthboundEventNotifyCritical 
-- Description	: Notification for real-time alarm whose level is Critical.
-- Type     	: Trap/Inform

		hwNmNorthboundEventNotifyCritical NOTIFICATION-TYPE						
			OBJECTS { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName,
				hwNmNorthboundReasonID, hwNmNorthboundFaultID, hwNmNorthboundDeviceType, hwNmNorthboundTrailName, hwNmNorthboundRootAlarm, hwNmNorthboundGroupID,
				hwNmNorthboundMaintainStatus }
			STATUS current
			DESCRIPTION 
				"Notification for real-time alarm whose level is Critical."
			::=  { hwNmNorthboundEventTrap 3 }

-- Name        	: hwNmNorthboundEventNotifyMajor 
-- Description	: Notification for real-time alarm whose level is Major.
-- Type     	: Trap/Inform
		hwNmNorthboundEventNotifyMajor NOTIFICATION-TYPE
			OBJECTS { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName,
				hwNmNorthboundReasonID, hwNmNorthboundFaultID, hwNmNorthboundDeviceType, hwNmNorthboundTrailName, hwNmNorthboundRootAlarm, hwNmNorthboundGroupID,
				hwNmNorthboundMaintainStatus }
			STATUS current
			DESCRIPTION 
				"Notification for real-time alarm whose level is Major."
			::=  { hwNmNorthboundEventTrap 4 }

-- Name        	: hwNmNorthboundEventNotifyMinor 
-- Description	: Notification for real-time alarm whose level is Minor.
-- Type     	: Trap/Inform
		hwNmNorthboundEventNotifyMinor NOTIFICATION-TYPE
			OBJECTS { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName,
				hwNmNorthboundReasonID, hwNmNorthboundFaultID, hwNmNorthboundDeviceType, hwNmNorthboundTrailName, hwNmNorthboundRootAlarm, hwNmNorthboundGroupID,
				hwNmNorthboundMaintainStatus }
			STATUS current
			DESCRIPTION 
				"Notification for real-time alarm whose level is Minor."
			::=  { hwNmNorthboundEventTrap 5 }

-- Name        	: hwNmNorthboundEventNotifyWarning 
-- Description	: Notification for real-time alarm whose level is Warning.
-- Type     	: Trap/Inform

		hwNmNorthboundEventNotifyWarning NOTIFICATION-TYPE
			OBJECTS { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName,
				hwNmNorthboundReasonID, hwNmNorthboundFaultID, hwNmNorthboundDeviceType, hwNmNorthboundTrailName, hwNmNorthboundRootAlarm, hwNmNorthboundGroupID,
				hwNmNorthboundMaintainStatus }
			STATUS current
			DESCRIPTION 
				"Notification for real-time alarm whose level is Warning."
			::=  { hwNmNorthboundEventTrap 6 }

-- Name        	: hwNmNorthboundEventNotifyIndefinitely 
-- Description	: Notification for real-time alarm whose level is Indefinitely.
-- Type     	: Trap/Inform
		hwNmNorthboundEventNotifyIndefinitely NOTIFICATION-TYPE
			OBJECTS { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName,
				hwNmNorthboundReasonID, hwNmNorthboundFaultID, hwNmNorthboundDeviceType, hwNmNorthboundTrailName, hwNmNorthboundRootAlarm, hwNmNorthboundGroupID,
				hwNmNorthboundMaintainStatus }
			STATUS current
			DESCRIPTION 
				"Notification for real-time alarm whose level is Indefinitely."
			::=  { hwNmNorthboundEventTrap 7 }

-- Name        	: hwNmNorthboundEventNotifyUnknownSeverity 
-- Description	: Notification for real-time alarm whose level is UnknownSeverity.
-- Type     	: Trap/Inform
		hwNmNorthboundEventNotifyUnknownSeverity NOTIFICATION-TYPE
			OBJECTS { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName,
				hwNmNorthboundReasonID, hwNmNorthboundFaultID, hwNmNorthboundDeviceType, hwNmNorthboundTrailName, hwNmNorthboundRootAlarm, hwNmNorthboundGroupID,
				hwNmNorthboundMaintainStatus }
			STATUS current
			DESCRIPTION 
				"Notification for real-time alarm whose level is UnknownSeverity."
			::=  { hwNmNorthboundEventTrap 8 }
			
-- Name        	: hwNmNorthboundEventSynchronizationStartNotify 
-- Description	: Notification indicates the beginning of alarm synchronization.
-- Type     	: Trap/Inform

		hwNmNorthboundEventSynchronizationStartNotify NOTIFICATION-TYPE
			STATUS current
			DESCRIPTION 
				"Notification indicates the beginning of alarm synchronization."
			::=  { hwNmNorthboundEventSynchronizationStartTrap 9 }
			
-- Name        	: hwNmNorthboundEventSynchronizationQueryResultNotify 
-- Description	: Notification carries the query result of alarm synchronization.
-- Type     	: Trap/Inform

		hwNmNorthboundEventSynchronizationQueryResultNotify NOTIFICATION-TYPE
			OBJECTS { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName,
				hwNmNorthboundReasonID, hwNmNorthboundFaultID, hwNmNorthboundDeviceType, hwNmNorthboundTrailName, hwNmNorthboundRootAlarm, hwNmNorthboundGroupID,
				hwNmNorthboundMaintainStatus }
			STATUS current
			DESCRIPTION 
				"Notification carries the query result of alarm synchronization."
			::=  { hwNmNorthboundEventSynchronizationQueryResultTrap 10 }         
			
-- Name        	: hwNmNorthboundEventSynchronizationEndNotify 
-- Description	: Notification indicates the end of alarm synchronization.
-- Type     	: Trap/Inform
		hwNmNorthboundEventSynchronizationEndNotify NOTIFICATION-TYPE
			OBJECTS { hwNmNorthboundEventSynchronizationEndStatus, hwNmNorthboundEventSynchronizationEndStatusDetail }
			STATUS current
			DESCRIPTION 
				"Notification indicates the end of alarm synchronization."
			::=  { hwNmNorthboundEventSynchronizationEndTrap 11 }

	
	END

--
-- HW-IMAPV1NORTHBOUND-TRAP-MIB.mib
--
