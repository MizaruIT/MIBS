--
--
-- Copyright (C) 1996-1998 by SNMP Research, Incorporated.
--
-- This software is furnished under a license and may be used and copied
-- only in accordance with the terms of such license and with the
-- inclusion of the above copyright notice. This software or any other
-- copies thereof may not be provided or otherwise made available to any
-- other person. No title to and ownership of the software is hereby
-- transferred.
--
-- The information in this software is subject to change without notice
-- and should not be construed as a commitment by SNMP Research, Incorporated.
--
-- Restricted Rights Legend:
--  Use, duplication, or disclosure by the Government is subject to
--  restrictions as set forth in subparagraph (c)(1)(ii) of the Rights
--  in Technical Data and Computer Software clause at DFARS 252.227-7013;
--  subparagraphs (c)(4) and (d) of the Commercial Computer
--  Software-Restricted Rights Clause, FAR 52.227-19; and in similar
--  clauses in the NASA FAR Supplement and other corresponding
--  governmental regulations.
--
--

--
--                PROPRIETARY NOTICE
--
-- This software is an unpublished work subject to a confidentiality agreement
-- and is protected by copyright and trade secret law.  Unauthorized copying,
-- redistribution or other use of this work is prohibited.
--
-- The above notice of copyright on this source code product does not indicate
-- any actual or intended publication of such source code.
--

SR-TC DEFINITIONS ::= BEGIN

IMPORTS
    ObjectSyntax  FROM SNMPv2-SMI
    DisplayString FROM SNMPv2-TC;

SROwnerString ::= TEXTUAL-CONVENTION
    DISPLAY-HINT "127a"
    STATUS       current
    DESCRIPTION
              "This data type is used to model an administratively
              assigned name of the owner of a resource. This
              information is taken from the NVT ASCII character
              set.  It is suggested that this name contain one or
              more of the following: IP address, management station
              name, network manager's name, location, or phone
              number.
              In some cases the agent itself will be the owner of
              an entry.  In these cases, this string shall be set
              to a string starting with 'monitor'.
              
              SNMP access control is articulated entirely in terms
              of the contents of MIB views; access to a particular
              SNMP object instance depends only upon its presence
              or absence in a particular MIB view and never upon
              its value or the value of related object instances.
              Thus, objects of this type afford resolution of
              resource contention only among cooperating managers;
              they realize no access control function with respect
              to uncooperative parties."
    SYNTAX DisplayString (SIZE (0..127))

--
--  Used in Dr-Web MIBS
--

HttpTCPIPAddress ::= TEXTUAL-CONVENTION
    DISPLAY-HINT "1d.1d.1d.1d/2d"
    STATUS       current
    DESCRIPTION
            "Represents a TCP address:

               octets   contents        encoding
                1-4     IP-address      network-byte order
                5-6     TCP-port        network-byte order
            "
    SYNTAX       OCTET STRING (SIZE (6))

END
