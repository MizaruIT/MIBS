-- Ericsson Television Limited Standard MIB disclaimer
-- ###################################################
-- SNMP MIBs for Ericsson Television Limited products are developed 
-- primarily for use by Ericsson Television Limited control solutions.
-- Where MIBs are provided to a third party or other non-Ericsson 
-- Television Limited person, for the purposes of their development 
-- of a non-Ericsson Television Limited control or monitoring solution, 
-- they are provided free of charge, and without obligation on the
-- part of Ericsson Television Limited to offer priority support, or
-- changes to suit the third party.
--
-- $Date: 2010-02-17 17:09:20 +0000 (Wed, 17 Feb 2010) $
-- $Revision: 192 $

ETV-Types-TC DEFINITIONS ::= BEGIN

-- Ericsson Television Limited textual conventions

Uint8  ::= INTEGER (0..255)
--         "An unsigned 8 bits integer (byte)"

Uint16 ::= INTEGER (0..65535)
--         "An unsigned 16 bits integer (word)"

Uint32 ::= Unsigned32 (0.. 4294967295)
--         "An unsigned 32 bits integer (double word)"

SlotNumber   ::= INTEGER (0..19)
--         "The number of a slot in the cabinet."

SmartcardSlot ::= INTEGER (1..32)
--         "The number of the smartcard slot in a channel."

PIDNumber    ::= INTEGER (0..8191)
--         "The number of a PID."

RowStatus ::= INTEGER {
               active(1),
               notInService(2),
               notReady(3),
               createAndGo(4),  -- supported for setting
               createAndWait(5),
               destroy(6)       -- supported for setting
               }
--         "The RowStatus as defined in SNMPv2-TC (RFC1903). Used for creating
--         and deleting conceptual rows. For more information, please refer to
--         RFC1903."

ModuleType ::= INTEGER {
            compositeAudio (1),
            compositeVideo (2),
            dvbAsi         (3),
            ethernet       (4),
            qpsk           (5),
            qam            (6),
            upconverter    (7),
            atm            (8),
            dvbSpi         (9),
            referenceClock (10),
            ofdmIf         (11),
            ofdmBaseband   (12),
            ofdmUhf        (13),
            gps1Pps        (14),
            externalAlarm  (15),
            aRow           (16),
            bRow           (17),
            satIF          (18),
            aux            (19),
            data           (20),
            serialVideo    (21),
            remoteControl  (22),
            audio          (23),
            ssi            (24),
            optical-asi    (25),
            g703MkII       (26),
            pos            (27),
            smpte310       (28),
            cRow           (29),
            serialVideoHD  (30), -- HD SDI
            gpi            (31),  -- General Purpose Interface
            sVideo         (32),
          
          -- Range 100 to 299 reserved for MediaPlex and iPlex

            plex-encoder    (101),  -- MediaPlex and iPlex encoder
            plex-advEncoder (102),  -- MediaPlex and iPlex advanced encoder

            plex-mcm        (201),  -- MediaPlex and iPlex MCM blade
            plex-trm        (202),  -- MediaPlex TRM blade
            plex-scm        (203),  -- MediaPlex and iPlex SCM blade
            plex-fan        (204),  -- MediaPlex and iPlex fan
          -- Range 100 to 299 reserved for MediaPlex and iPlex


  		  -- Range 300 to 399 reserved for RX8000 port types
             qpsk-s2           (300),  -- DVB S2 input
             qpsk-s2-if        (301),  -- DVB S2 IF input
             vsb               (302)   -- VSB input

   }

END
