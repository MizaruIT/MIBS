ISHELF-ARCS-MIB DEFINITIONS ::= BEGIN

    IMPORTS
    enterprises
        FROM SNMPv2-SMI
    ;

telstrat OBJECT IDENTIFIER ::= { enterprises 9056 }

        osiCommon OBJECT IDENTIFIER ::= { telstrat 1 }

        osiOlt OBJECT IDENTIFIER ::= { telstrat 2 }

        osiOnt OBJECT IDENTIFIER ::= { telstrat 3 }

        osiUAPSys OBJECT IDENTIFIER ::= { telstrat 4 }

        osiIShelf OBJECT IDENTIFIER ::= { telstrat 5 }

        osiModules OBJECT IDENTIFIER ::= { telstrat 10 }


        iShelfSys OBJECT IDENTIFIER ::= { osiIShelf 1 }
        iShelfCard OBJECT IDENTIFIER ::= { osiIShelf 2 }
        iShelfFacility OBJECT IDENTIFIER ::= { osiIShelf 3 }
        iShelfPort OBJECT IDENTIFIER ::= { osiIShelf 4 }
        iShelfPstn OBJECT IDENTIFIER ::= { osiIShelf 5 }
        iShelfData OBJECT IDENTIFIER ::= { osiIShelf 6 }
        iShelfVideo OBJECT IDENTIFIER ::= { osiIShelf 7 }
        iShelfPm OBJECT IDENTIFIER ::= { osiIShelf 8 }
        iShelfTrap OBJECT IDENTIFIER ::= { osiIShelf 9 }
        iShelfBroadBand OBJECT IDENTIFIER ::= { osiIShelf 10 }
        iShelfModules OBJECT IDENTIFIER ::= { osiIShelf 11 }
        iShelfPrivate OBJECT IDENTIFIER ::= { osiIShelf 12 }

        iShelfTrapGroup OBJECT IDENTIFIER ::= { iShelfTrap 1 }
        iShelfTrapConfig OBJECT IDENTIFIER ::= { iShelfTrap 2 }
END
