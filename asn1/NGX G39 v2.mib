--  Title:    NGX_G39.MIB 
--  Version:  v3.9 for SNMPv2c
-- 
--  Copyright @ 2005 DPS Inc. All Rights Reserved 
-- 
--  This MIB defines supplemental objects for the NGDdx points and controls.
-- 
-- 

DPS-MIB-NGX-G39-V2 DEFINITIONS ::= BEGIN 

IMPORTS 
	dpsRTUv2 
		FROM DPS-MIB-V38-V2;

dpsRTUv2p6001Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 1 is set." 
	::= { dpsRTUv2 6001 }

dpsRTUv2p7001Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 1 clears." 
	::= { dpsRTUv2 7001 }

dpsRTUv2p6002Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 2 is set." 
	::= { dpsRTUv2 6002 }

dpsRTUv2p7002Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 2 clears." 
	::= { dpsRTUv2 7002 }

dpsRTUv2p6003Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 3 is set." 
	::= { dpsRTUv2 6003 }

dpsRTUv2p7003Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 3 clears." 
	::= { dpsRTUv2 7003 }

dpsRTUv2p6004Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 4 is set." 
	::= { dpsRTUv2 6004 }

dpsRTUv2p7004Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 4 clears." 
	::= { dpsRTUv2 7004 }

dpsRTUv2p6005Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 5 is set." 
	::= { dpsRTUv2 6005 }

dpsRTUv2p7005Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 5 clears." 
	::= { dpsRTUv2 7005 }

dpsRTUv2p6006Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 6 is set." 
	::= { dpsRTUv2 6006 }

dpsRTUv2p7006Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 6 clears." 
	::= { dpsRTUv2 7006 }

dpsRTUv2p6007Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 7 is set." 
	::= { dpsRTUv2 6007 }

dpsRTUv2p7007Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 7 clears." 
	::= { dpsRTUv2 7007 }

dpsRTUv2p6008Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 8 is set." 
	::= { dpsRTUv2 6008 }

dpsRTUv2p7008Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 8 clears." 
	::= { dpsRTUv2 7008 }

dpsRTUv2p6009Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 9 is set." 
	::= { dpsRTUv2 6009 }

dpsRTUv2p7009Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 9 clears." 
	::= { dpsRTUv2 7009 }

dpsRTUv2p6010Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 10 is set." 
	::= { dpsRTUv2 6010 }

dpsRTUv2p7010Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 10 clears." 
	::= { dpsRTUv2 7010 }

dpsRTUv2p6011Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 11 is set." 
	::= { dpsRTUv2 6011 }

dpsRTUv2p7011Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 11 clears." 
	::= { dpsRTUv2 7011 }

dpsRTUv2p6012Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 12 is set." 
	::= { dpsRTUv2 6012 }

dpsRTUv2p7012Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 12 clears." 
	::= { dpsRTUv2 7012 }

dpsRTUv2p6013Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 13 is set." 
	::= { dpsRTUv2 6013 }

dpsRTUv2p7013Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 13 clears." 
	::= { dpsRTUv2 7013 }

dpsRTUv2p6014Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 14 is set." 
	::= { dpsRTUv2 6014 }

dpsRTUv2p7014Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 14 clears." 
	::= { dpsRTUv2 7014 }

dpsRTUv2p6015Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 15 is set." 
	::= { dpsRTUv2 6015 }

dpsRTUv2p7015Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 15 clears." 
	::= { dpsRTUv2 7015 }

dpsRTUv2p6016Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 16 is set." 
	::= { dpsRTUv2 6016 }

dpsRTUv2p7016Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 16 clears." 
	::= { dpsRTUv2 7016 }

dpsRTUv2p6017Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 17 is set." 
	::= { dpsRTUv2 6017 }

dpsRTUv2p7017Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 17 clears." 
	::= { dpsRTUv2 7017 }

dpsRTUv2p6018Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 18 is set." 
	::= { dpsRTUv2 6018 }

dpsRTUv2p7018Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 18 clears." 
	::= { dpsRTUv2 7018 }

dpsRTUv2p6019Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 19 is set." 
	::= { dpsRTUv2 6019 }

dpsRTUv2p7019Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 19 clears." 
	::= { dpsRTUv2 7019 }

dpsRTUv2p6020Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 20 is set." 
	::= { dpsRTUv2 6020 }

dpsRTUv2p7020Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 20 clears." 
	::= { dpsRTUv2 7020 }

dpsRTUv2p6021Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 21 is set." 
	::= { dpsRTUv2 6021 }

dpsRTUv2p7021Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 21 clears." 
	::= { dpsRTUv2 7021 }

dpsRTUv2p6022Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 22 is set." 
	::= { dpsRTUv2 6022 }

dpsRTUv2p7022Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 22 clears." 
	::= { dpsRTUv2 7022 }

dpsRTUv2p6023Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 23 is set." 
	::= { dpsRTUv2 6023 }

dpsRTUv2p7023Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 23 clears." 
	::= { dpsRTUv2 7023 }

dpsRTUv2p6024Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 24 is set." 
	::= { dpsRTUv2 6024 }

dpsRTUv2p7024Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 24 clears." 
	::= { dpsRTUv2 7024 }

dpsRTUv2p6025Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 25 is set." 
	::= { dpsRTUv2 6025 }

dpsRTUv2p7025Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 25 clears." 
	::= { dpsRTUv2 7025 }

dpsRTUv2p6026Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 26 is set." 
	::= { dpsRTUv2 6026 }

dpsRTUv2p7026Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 26 clears." 
	::= { dpsRTUv2 7026 }

dpsRTUv2p6027Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 27 is set." 
	::= { dpsRTUv2 6027 }

dpsRTUv2p7027Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 27 clears." 
	::= { dpsRTUv2 7027 }

dpsRTUv2p6028Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 28 is set." 
	::= { dpsRTUv2 6028 }

dpsRTUv2p7028Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 28 clears." 
	::= { dpsRTUv2 7028 }

dpsRTUv2p6029Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 29 is set." 
	::= { dpsRTUv2 6029 }

dpsRTUv2p7029Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 29 clears." 
	::= { dpsRTUv2 7029 }

dpsRTUv2p6030Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 30 is set." 
	::= { dpsRTUv2 6030 }

dpsRTUv2p7030Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 30 clears." 
	::= { dpsRTUv2 7030 }

dpsRTUv2p6031Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 31 is set." 
	::= { dpsRTUv2 6031 }

dpsRTUv2p7031Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 31 clears." 
	::= { dpsRTUv2 7031 }

dpsRTUv2p6032Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 32 is set." 
	::= { dpsRTUv2 6032 }

dpsRTUv2p7032Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 32 clears." 
	::= { dpsRTUv2 7032 }

dpsRTUv2p6033Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 33 is set." 
	::= { dpsRTUv2 6033 }

dpsRTUv2p7033Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 33 clears." 
	::= { dpsRTUv2 7033 }

dpsRTUv2p6034Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 34 is set." 
	::= { dpsRTUv2 6034 }

dpsRTUv2p7034Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 34 clears." 
	::= { dpsRTUv2 7034 }

dpsRTUv2p6035Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 35 is set." 
	::= { dpsRTUv2 6035 }

dpsRTUv2p7035Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 35 clears." 
	::= { dpsRTUv2 7035 }

dpsRTUv2p6036Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 36 is set." 
	::= { dpsRTUv2 6036 }

dpsRTUv2p7036Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 36 clears." 
	::= { dpsRTUv2 7036 }

dpsRTUv2p6037Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 37 is set." 
	::= { dpsRTUv2 6037 }

dpsRTUv2p7037Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 37 clears." 
	::= { dpsRTUv2 7037 }

dpsRTUv2p6038Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 38 is set." 
	::= { dpsRTUv2 6038 }

dpsRTUv2p7038Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 38 clears." 
	::= { dpsRTUv2 7038 }

dpsRTUv2p6039Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 39 is set." 
	::= { dpsRTUv2 6039 }

dpsRTUv2p7039Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 39 clears." 
	::= { dpsRTUv2 7039 }

dpsRTUv2p6040Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 40 is set." 
	::= { dpsRTUv2 6040 }

dpsRTUv2p7040Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 40 clears." 
	::= { dpsRTUv2 7040 }

dpsRTUv2p6041Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 41 is set." 
	::= { dpsRTUv2 6041 }

dpsRTUv2p7041Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 41 clears." 
	::= { dpsRTUv2 7041 }

dpsRTUv2p6042Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 42 is set." 
	::= { dpsRTUv2 6042 }

dpsRTUv2p7042Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 42 clears." 
	::= { dpsRTUv2 7042 }

dpsRTUv2p6043Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 43 is set." 
	::= { dpsRTUv2 6043 }

dpsRTUv2p7043Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 43 clears." 
	::= { dpsRTUv2 7043 }

dpsRTUv2p6044Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 44 is set." 
	::= { dpsRTUv2 6044 }

dpsRTUv2p7044Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 44 clears." 
	::= { dpsRTUv2 7044 }

dpsRTUv2p6045Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 45 is set." 
	::= { dpsRTUv2 6045 }

dpsRTUv2p7045Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 45 clears." 
	::= { dpsRTUv2 7045 }

dpsRTUv2p6046Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 46 is set." 
	::= { dpsRTUv2 6046 }

dpsRTUv2p7046Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 46 clears." 
	::= { dpsRTUv2 7046 }

dpsRTUv2p6047Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 47 is set." 
	::= { dpsRTUv2 6047 }

dpsRTUv2p7047Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 47 clears." 
	::= { dpsRTUv2 7047 }

dpsRTUv2p6048Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 48 is set." 
	::= { dpsRTUv2 6048 }

dpsRTUv2p7048Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx1 point 48 clears." 
	::= { dpsRTUv2 7048 }

dpsRTUv2p6129Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 1 is set." 
	::= { dpsRTUv2 6129 }

dpsRTUv2p7129Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 1 clears." 
	::= { dpsRTUv2 7129 }

dpsRTUv2p6130Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 2 is set." 
	::= { dpsRTUv2 6130 }

dpsRTUv2p7130Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 2 clears." 
	::= { dpsRTUv2 7130 }

dpsRTUv2p6131Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 3 is set." 
	::= { dpsRTUv2 6131 }

dpsRTUv2p7131Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 3 clears." 
	::= { dpsRTUv2 7131 }

dpsRTUv2p6132Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 4 is set." 
	::= { dpsRTUv2 6132 }

dpsRTUv2p7132Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 4 clears." 
	::= { dpsRTUv2 7132 }

dpsRTUv2p6133Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 5 is set." 
	::= { dpsRTUv2 6133 }

dpsRTUv2p7133Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 5 clears." 
	::= { dpsRTUv2 7133 }

dpsRTUv2p6134Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 6 is set." 
	::= { dpsRTUv2 6134 }

dpsRTUv2p7134Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 6 clears." 
	::= { dpsRTUv2 7134 }

dpsRTUv2p6135Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 7 is set." 
	::= { dpsRTUv2 6135 }

dpsRTUv2p7135Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 7 clears." 
	::= { dpsRTUv2 7135 }

dpsRTUv2p6136Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 8 is set." 
	::= { dpsRTUv2 6136 }

dpsRTUv2p7136Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 8 clears." 
	::= { dpsRTUv2 7136 }

dpsRTUv2p6137Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 9 is set." 
	::= { dpsRTUv2 6137 }

dpsRTUv2p7137Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 9 clears." 
	::= { dpsRTUv2 7137 }

dpsRTUv2p6138Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 10 is set." 
	::= { dpsRTUv2 6138 }

dpsRTUv2p7138Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 10 clears." 
	::= { dpsRTUv2 7138 }

dpsRTUv2p6139Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 11 is set." 
	::= { dpsRTUv2 6139 }

dpsRTUv2p7139Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 11 clears." 
	::= { dpsRTUv2 7139 }

dpsRTUv2p6140Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 12 is set." 
	::= { dpsRTUv2 6140 }

dpsRTUv2p7140Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 12 clears." 
	::= { dpsRTUv2 7140 }

dpsRTUv2p6141Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 13 is set." 
	::= { dpsRTUv2 6141 }

dpsRTUv2p7141Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 13 clears." 
	::= { dpsRTUv2 7141 }

dpsRTUv2p6142Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 14 is set." 
	::= { dpsRTUv2 6142 }

dpsRTUv2p7142Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 14 clears." 
	::= { dpsRTUv2 7142 }

dpsRTUv2p6143Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 15 is set." 
	::= { dpsRTUv2 6143 }

dpsRTUv2p7143Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 15 clears." 
	::= { dpsRTUv2 7143 }

dpsRTUv2p6144Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 16 is set." 
	::= { dpsRTUv2 6144 }

dpsRTUv2p7144Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 16 clears." 
	::= { dpsRTUv2 7144 }

dpsRTUv2p6145Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 17 is set." 
	::= { dpsRTUv2 6145 }

dpsRTUv2p7145Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 17 clears." 
	::= { dpsRTUv2 7145 }

dpsRTUv2p6146Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 18 is set." 
	::= { dpsRTUv2 6146 }

dpsRTUv2p7146Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 18 clears." 
	::= { dpsRTUv2 7146 }

dpsRTUv2p6147Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 19 is set." 
	::= { dpsRTUv2 6147 }

dpsRTUv2p7147Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 19 clears." 
	::= { dpsRTUv2 7147 }

dpsRTUv2p6148Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 20 is set." 
	::= { dpsRTUv2 6148 }

dpsRTUv2p7148Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 20 clears." 
	::= { dpsRTUv2 7148 }

dpsRTUv2p6149Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 21 is set." 
	::= { dpsRTUv2 6149 }

dpsRTUv2p7149Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 21 clears." 
	::= { dpsRTUv2 7149 }

dpsRTUv2p6150Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 22 is set." 
	::= { dpsRTUv2 6150 }

dpsRTUv2p7150Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 22 clears." 
	::= { dpsRTUv2 7150 }

dpsRTUv2p6151Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 23 is set." 
	::= { dpsRTUv2 6151 }

dpsRTUv2p7151Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 23 clears." 
	::= { dpsRTUv2 7151 }

dpsRTUv2p6152Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 24 is set." 
	::= { dpsRTUv2 6152 }

dpsRTUv2p7152Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 24 clears." 
	::= { dpsRTUv2 7152 }

dpsRTUv2p6153Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 25 is set." 
	::= { dpsRTUv2 6153 }

dpsRTUv2p7153Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 25 clears." 
	::= { dpsRTUv2 7153 }

dpsRTUv2p6154Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 26 is set." 
	::= { dpsRTUv2 6154 }

dpsRTUv2p7154Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 26 clears." 
	::= { dpsRTUv2 7154 }

dpsRTUv2p6155Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 27 is set." 
	::= { dpsRTUv2 6155 }

dpsRTUv2p7155Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 27 clears." 
	::= { dpsRTUv2 7155 }

dpsRTUv2p6156Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 28 is set." 
	::= { dpsRTUv2 6156 }

dpsRTUv2p7156Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 28 clears." 
	::= { dpsRTUv2 7156 }

dpsRTUv2p6157Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 29 is set." 
	::= { dpsRTUv2 6157 }

dpsRTUv2p7157Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 29 clears." 
	::= { dpsRTUv2 7157 }

dpsRTUv2p6158Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 30 is set." 
	::= { dpsRTUv2 6158 }

dpsRTUv2p7158Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 30 clears." 
	::= { dpsRTUv2 7158 }

dpsRTUv2p6159Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 31 is set." 
	::= { dpsRTUv2 6159 }

dpsRTUv2p7159Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 31 clears." 
	::= { dpsRTUv2 7159 }

dpsRTUv2p6160Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 32 is set." 
	::= { dpsRTUv2 6160 }

dpsRTUv2p7160Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 32 clears." 
	::= { dpsRTUv2 7160 }

dpsRTUv2p6161Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 33 is set." 
	::= { dpsRTUv2 6161 }

dpsRTUv2p7161Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 33 clears." 
	::= { dpsRTUv2 7161 }

dpsRTUv2p6162Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 34 is set." 
	::= { dpsRTUv2 6162 }

dpsRTUv2p7162Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 34 clears." 
	::= { dpsRTUv2 7162 }

dpsRTUv2p6163Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 35 is set." 
	::= { dpsRTUv2 6163 }

dpsRTUv2p7163Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 35 clears." 
	::= { dpsRTUv2 7163 }

dpsRTUv2p6164Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 36 is set." 
	::= { dpsRTUv2 6164 }

dpsRTUv2p7164Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 36 clears." 
	::= { dpsRTUv2 7164 }

dpsRTUv2p6165Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 37 is set." 
	::= { dpsRTUv2 6165 }

dpsRTUv2p7165Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 37 clears." 
	::= { dpsRTUv2 7165 }

dpsRTUv2p6166Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 38 is set." 
	::= { dpsRTUv2 6166 }

dpsRTUv2p7166Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 38 clears." 
	::= { dpsRTUv2 7166 }

dpsRTUv2p6167Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 39 is set." 
	::= { dpsRTUv2 6167 }

dpsRTUv2p7167Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 39 clears." 
	::= { dpsRTUv2 7167 }

dpsRTUv2p6168Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 40 is set." 
	::= { dpsRTUv2 6168 }

dpsRTUv2p7168Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 40 clears." 
	::= { dpsRTUv2 7168 }

dpsRTUv2p6169Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 41 is set." 
	::= { dpsRTUv2 6169 }

dpsRTUv2p7169Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 41 clears." 
	::= { dpsRTUv2 7169 }

dpsRTUv2p6170Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 42 is set." 
	::= { dpsRTUv2 6170 }

dpsRTUv2p7170Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 42 clears." 
	::= { dpsRTUv2 7170 }

dpsRTUv2p6171Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 43 is set." 
	::= { dpsRTUv2 6171 }

dpsRTUv2p7171Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 43 clears." 
	::= { dpsRTUv2 7171 }

dpsRTUv2p6172Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 44 is set." 
	::= { dpsRTUv2 6172 }

dpsRTUv2p7172Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 44 clears." 
	::= { dpsRTUv2 7172 }

dpsRTUv2p6173Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 45 is set." 
	::= { dpsRTUv2 6173 }

dpsRTUv2p7173Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 45 clears." 
	::= { dpsRTUv2 7173 }

dpsRTUv2p6174Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 46 is set." 
	::= { dpsRTUv2 6174 }

dpsRTUv2p7174Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 46 clears." 
	::= { dpsRTUv2 7174 }

dpsRTUv2p6175Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 47 is set." 
	::= { dpsRTUv2 6175 }

dpsRTUv2p7175Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 47 clears." 
	::= { dpsRTUv2 7175 }

dpsRTUv2p6176Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 48 is set." 
	::= { dpsRTUv2 6176 }

dpsRTUv2p7176Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx2 point 48 clears." 
	::= { dpsRTUv2 7176 }

dpsRTUv2p6257Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 1 is set." 
	::= { dpsRTUv2 6257 }

dpsRTUv2p7257Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 1 clears." 
	::= { dpsRTUv2 7257 }

dpsRTUv2p6258Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 2 is set." 
	::= { dpsRTUv2 6258 }

dpsRTUv2p7258Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 2 clears." 
	::= { dpsRTUv2 7258 }

dpsRTUv2p6259Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 3 is set." 
	::= { dpsRTUv2 6259 }

dpsRTUv2p7259Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 3 clears." 
	::= { dpsRTUv2 7259 }

dpsRTUv2p6260Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 4 is set." 
	::= { dpsRTUv2 6260 }

dpsRTUv2p7260Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 4 clears." 
	::= { dpsRTUv2 7260 }

dpsRTUv2p6261Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 5 is set." 
	::= { dpsRTUv2 6261 }

dpsRTUv2p7261Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 5 clears." 
	::= { dpsRTUv2 7261 }

dpsRTUv2p6262Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 6 is set." 
	::= { dpsRTUv2 6262 }

dpsRTUv2p7262Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 6 clears." 
	::= { dpsRTUv2 7262 }

dpsRTUv2p6263Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 7 is set." 
	::= { dpsRTUv2 6263 }

dpsRTUv2p7263Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 7 clears." 
	::= { dpsRTUv2 7263 }

dpsRTUv2p6264Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 8 is set." 
	::= { dpsRTUv2 6264 }

dpsRTUv2p7264Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 8 clears." 
	::= { dpsRTUv2 7264 }

dpsRTUv2p6265Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 9 is set." 
	::= { dpsRTUv2 6265 }

dpsRTUv2p7265Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 9 clears." 
	::= { dpsRTUv2 7265 }

dpsRTUv2p6266Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 10 is set." 
	::= { dpsRTUv2 6266 }

dpsRTUv2p7266Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 10 clears." 
	::= { dpsRTUv2 7266 }

dpsRTUv2p6267Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 11 is set." 
	::= { dpsRTUv2 6267 }

dpsRTUv2p7267Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 11 clears." 
	::= { dpsRTUv2 7267 }

dpsRTUv2p6268Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 12 is set." 
	::= { dpsRTUv2 6268 }

dpsRTUv2p7268Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 12 clears." 
	::= { dpsRTUv2 7268 }

dpsRTUv2p6269Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 13 is set." 
	::= { dpsRTUv2 6269 }

dpsRTUv2p7269Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 13 clears." 
	::= { dpsRTUv2 7269 }

dpsRTUv2p6270Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 14 is set." 
	::= { dpsRTUv2 6270 }

dpsRTUv2p7270Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 14 clears." 
	::= { dpsRTUv2 7270 }

dpsRTUv2p6271Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 15 is set." 
	::= { dpsRTUv2 6271 }

dpsRTUv2p7271Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 15 clears." 
	::= { dpsRTUv2 7271 }

dpsRTUv2p6272Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 16 is set." 
	::= { dpsRTUv2 6272 }

dpsRTUv2p7272Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 16 clears." 
	::= { dpsRTUv2 7272 }

dpsRTUv2p6273Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 17 is set." 
	::= { dpsRTUv2 6273 }

dpsRTUv2p7273Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 17 clears." 
	::= { dpsRTUv2 7273 }

dpsRTUv2p6274Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 18 is set." 
	::= { dpsRTUv2 6274 }

dpsRTUv2p7274Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 18 clears." 
	::= { dpsRTUv2 7274 }

dpsRTUv2p6275Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 19 is set." 
	::= { dpsRTUv2 6275 }

dpsRTUv2p7275Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 19 clears." 
	::= { dpsRTUv2 7275 }

dpsRTUv2p6276Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 20 is set." 
	::= { dpsRTUv2 6276 }

dpsRTUv2p7276Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 20 clears." 
	::= { dpsRTUv2 7276 }

dpsRTUv2p6277Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 21 is set." 
	::= { dpsRTUv2 6277 }

dpsRTUv2p7277Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 21 clears." 
	::= { dpsRTUv2 7277 }

dpsRTUv2p6278Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 22 is set." 
	::= { dpsRTUv2 6278 }

dpsRTUv2p7278Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 22 clears." 
	::= { dpsRTUv2 7278 }

dpsRTUv2p6279Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 23 is set." 
	::= { dpsRTUv2 6279 }

dpsRTUv2p7279Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 23 clears." 
	::= { dpsRTUv2 7279 }

dpsRTUv2p6280Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 24 is set." 
	::= { dpsRTUv2 6280 }

dpsRTUv2p7280Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 24 clears." 
	::= { dpsRTUv2 7280 }

dpsRTUv2p6281Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 25 is set." 
	::= { dpsRTUv2 6281 }

dpsRTUv2p7281Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 25 clears." 
	::= { dpsRTUv2 7281 }

dpsRTUv2p6282Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 26 is set." 
	::= { dpsRTUv2 6282 }

dpsRTUv2p7282Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 26 clears." 
	::= { dpsRTUv2 7282 }

dpsRTUv2p6283Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 27 is set." 
	::= { dpsRTUv2 6283 }

dpsRTUv2p7283Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 27 clears." 
	::= { dpsRTUv2 7283 }

dpsRTUv2p6284Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 28 is set." 
	::= { dpsRTUv2 6284 }

dpsRTUv2p7284Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 28 clears." 
	::= { dpsRTUv2 7284 }

dpsRTUv2p6285Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 29 is set." 
	::= { dpsRTUv2 6285 }

dpsRTUv2p7285Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 29 clears." 
	::= { dpsRTUv2 7285 }

dpsRTUv2p6286Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 30 is set." 
	::= { dpsRTUv2 6286 }

dpsRTUv2p7286Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 30 clears." 
	::= { dpsRTUv2 7286 }

dpsRTUv2p6287Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 31 is set." 
	::= { dpsRTUv2 6287 }

dpsRTUv2p7287Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 31 clears." 
	::= { dpsRTUv2 7287 }

dpsRTUv2p6288Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 32 is set." 
	::= { dpsRTUv2 6288 }

dpsRTUv2p7288Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 32 clears." 
	::= { dpsRTUv2 7288 }

dpsRTUv2p6289Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 33 is set." 
	::= { dpsRTUv2 6289 }

dpsRTUv2p7289Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 33 clears." 
	::= { dpsRTUv2 7289 }

dpsRTUv2p6290Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 34 is set." 
	::= { dpsRTUv2 6290 }

dpsRTUv2p7290Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 34 clears." 
	::= { dpsRTUv2 7290 }

dpsRTUv2p6291Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 35 is set." 
	::= { dpsRTUv2 6291 }

dpsRTUv2p7291Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 35 clears." 
	::= { dpsRTUv2 7291 }

dpsRTUv2p6292Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 36 is set." 
	::= { dpsRTUv2 6292 }

dpsRTUv2p7292Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 36 clears." 
	::= { dpsRTUv2 7292 }

dpsRTUv2p6293Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 37 is set." 
	::= { dpsRTUv2 6293 }

dpsRTUv2p7293Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 37 clears." 
	::= { dpsRTUv2 7293 }

dpsRTUv2p6294Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 38 is set." 
	::= { dpsRTUv2 6294 }

dpsRTUv2p7294Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 38 clears." 
	::= { dpsRTUv2 7294 }

dpsRTUv2p6295Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 39 is set." 
	::= { dpsRTUv2 6295 }

dpsRTUv2p7295Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 39 clears." 
	::= { dpsRTUv2 7295 }

dpsRTUv2p6296Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 40 is set." 
	::= { dpsRTUv2 6296 }

dpsRTUv2p7296Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 40 clears." 
	::= { dpsRTUv2 7296 }

dpsRTUv2p6297Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 41 is set." 
	::= { dpsRTUv2 6297 }

dpsRTUv2p7297Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 41 clears." 
	::= { dpsRTUv2 7297 }

dpsRTUv2p6298Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 42 is set." 
	::= { dpsRTUv2 6298 }

dpsRTUv2p7298Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 42 clears." 
	::= { dpsRTUv2 7298 }

dpsRTUv2p6299Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 43 is set." 
	::= { dpsRTUv2 6299 }

dpsRTUv2p7299Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 43 clears." 
	::= { dpsRTUv2 7299 }

dpsRTUv2p6300Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 44 is set." 
	::= { dpsRTUv2 6300 }

dpsRTUv2p7300Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 44 clears." 
	::= { dpsRTUv2 7300 }

dpsRTUv2p6301Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 45 is set." 
	::= { dpsRTUv2 6301 }

dpsRTUv2p7301Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 45 clears." 
	::= { dpsRTUv2 7301 }

dpsRTUv2p6302Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 46 is set." 
	::= { dpsRTUv2 6302 }

dpsRTUv2p7302Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 46 clears." 
	::= { dpsRTUv2 7302 }

dpsRTUv2p6303Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 47 is set." 
	::= { dpsRTUv2 6303 }

dpsRTUv2p7303Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 47 clears." 
	::= { dpsRTUv2 7303 }

dpsRTUv2p6304Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 48 is set." 
	::= { dpsRTUv2 6304 }

dpsRTUv2p7304Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when NGDdx3 point 48 clears." 
	::= { dpsRTUv2 7304 }

dpsRTUv2p6065Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 1 is latched."
	::= { dpsRTUv2 6065 }

dpsRTUv2p7065Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 1 is released."
	::= { dpsRTUv2 7065 }

dpsRTUv2p6066Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 2 is latched."
	::= { dpsRTUv2 6066 }

dpsRTUv2p7066Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 2 is released."
	::= { dpsRTUv2 7066 }

dpsRTUv2p6067Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 3 is latched."
	::= { dpsRTUv2 6067 }

dpsRTUv2p7067Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 3 is released."
	::= { dpsRTUv2 7067 }

dpsRTUv2p6068Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 4 is latched."
	::= { dpsRTUv2 6068 }

dpsRTUv2p7068Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 4 is released."
	::= { dpsRTUv2 7068 }

dpsRTUv2p6069Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 5 is latched."
	::= { dpsRTUv2 6069 }

dpsRTUv2p7069Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 5 is released."
	::= { dpsRTUv2 7069 }

dpsRTUv2p6070Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 6 is latched."
	::= { dpsRTUv2 6070 }

dpsRTUv2p7070Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 6 is released."
	::= { dpsRTUv2 7070 }

dpsRTUv2p6071Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 7 is latched."
	::= { dpsRTUv2 6071 }

dpsRTUv2p7071Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 7 is released."
	::= { dpsRTUv2 7071 }

dpsRTUv2p6072Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 8 is latched."
	::= { dpsRTUv2 6072 }

dpsRTUv2p7072Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx1 control 8 is released."
	::= { dpsRTUv2 7072 }

dpsRTUv2p6193Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 1 is latched."
	::= { dpsRTUv2 6193 }

dpsRTUv2p7193Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 1 is released."
	::= { dpsRTUv2 7193 }

dpsRTUv2p6194Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 2 is latched."
	::= { dpsRTUv2 6194 }

dpsRTUv2p7194Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 2 is released."
	::= { dpsRTUv2 7194 }

dpsRTUv2p6195Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 3 is latched."
	::= { dpsRTUv2 6195 }

dpsRTUv2p7195Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 3 is released."
	::= { dpsRTUv2 7195 }

dpsRTUv2p6196Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 4 is latched."
	::= { dpsRTUv2 6196 }

dpsRTUv2p7196Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 4 is released."
	::= { dpsRTUv2 7196 }

dpsRTUv2p6197Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 5 is latched."
	::= { dpsRTUv2 6197 }

dpsRTUv2p7197Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 5 is released."
	::= { dpsRTUv2 7197 }

dpsRTUv2p6198Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 6 is latched."
	::= { dpsRTUv2 6198 }

dpsRTUv2p7198Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 6 is released."
	::= { dpsRTUv2 7198 }

dpsRTUv2p6199Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 7 is latched."
	::= { dpsRTUv2 6199 }

dpsRTUv2p7199Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 7 is released."
	::= { dpsRTUv2 7199 }

dpsRTUv2p6200Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 8 is latched."
	::= { dpsRTUv2 6200 }

dpsRTUv2p7200Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx2 control 8 is released."
	::= { dpsRTUv2 7200 }

dpsRTUv2p6321Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 1 is latched."
	::= { dpsRTUv2 6321 }

dpsRTUv2p7321Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 1 is released."
	::= { dpsRTUv2 7321 }

dpsRTUv2p6322Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 2 is latched."
	::= { dpsRTUv2 6322 }

dpsRTUv2p7322Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 2 is released."
	::= { dpsRTUv2 7322 }

dpsRTUv2p6323Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 3 is latched."
	::= { dpsRTUv2 6323 }

dpsRTUv2p7323Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 3 is released."
	::= { dpsRTUv2 7323 }

dpsRTUv2p6324Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 4 is latched."
	::= { dpsRTUv2 6324 }

dpsRTUv2p7324Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 4 is released."
	::= { dpsRTUv2 7324 }

dpsRTUv2p6325Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 5 is latched."
	::= { dpsRTUv2 6325 }

dpsRTUv2p7325Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 5 is released."
	::= { dpsRTUv2 7325 }

dpsRTUv2p6326Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 6 is latched."
	::= { dpsRTUv2 6326 }

dpsRTUv2p7326Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 6 is released."
	::= { dpsRTUv2 7326 }

dpsRTUv2p6327Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 7 is latched."
	::= { dpsRTUv2 6327 }

dpsRTUv2p7327Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 7 is released."
	::= { dpsRTUv2 7327 }

dpsRTUv2p6328Set NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 8 is latched."
	::= { dpsRTUv2 6328 }

dpsRTUv2p7328Clr NOTIFICATION-TYPE
	OBJECTS	 {	sysDescr, sysLocation, dpsRTUv2DateTime,
					dpsRTUv2APort, dpsRTUv2CAddress, dpsRTUv2ADisplay, dpsRTUv2APoint,
					dpsRTUv2APntDesc, dpsRTUv2AState }
	STATUS		current
	DESCRIPTION "Generated when NGDdx3 control 8 is released."
	::= { dpsRTUv2 7328 }

END
