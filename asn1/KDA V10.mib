--  Title:    KDA_V10.MIB
--  Version:  v1.0
--
--  Copyright @ 1997-2004 DPS Inc. All Rights Reserved
--
--  This MIB defines supplemental objects for the DPS NetGuardian series.
--
--

DPS-MIB-NGD-V10 DEFINITIONS ::= BEGIN

IMPORTS
	dpsRTU
		FROM DPS-MIB-V38;

dpsRTUp0001Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 1 is set."
	::= 10001

dpsRTUp0001Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 1 clears."
	::= 20001

dpsRTUp0002Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 2 is set."
	::= 10002

dpsRTUp0002Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 2 clears."
	::= 20002

dpsRTUp0003Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 3 is set."
	::= 10003

dpsRTUp0003Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 3 clears."
	::= 20003

dpsRTUp0004Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 4 is set."
	::= 10004

dpsRTUp0004Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 4 clears."
	::= 20004

dpsRTUp0005Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 5 is set."
	::= 10005

dpsRTUp0005Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 5 clears."
	::= 20005

dpsRTUp0006Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 6 is set."
	::= 10006

dpsRTUp0006Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 6 clears."
	::= 20006

dpsRTUp0007Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 7 is set."
	::= 10007

dpsRTUp0007Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 7 clears."
	::= 20007

dpsRTUp0008Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 8 is set."
	::= 10008

dpsRTUp0008Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 8 clears."
	::= 20008

dpsRTUp0009Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 9 is set."
	::= 10009

dpsRTUp0009Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 9 clears."
	::= 20009

dpsRTUp0010Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 10 is set."
	::= 10010

dpsRTUp0010Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 10 clears."
	::= 20010

dpsRTUp0011Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 11 is set."
	::= 10011

dpsRTUp0011Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 11 clears."
	::= 20011

dpsRTUp0012Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 12 is set."
	::= 10012

dpsRTUp0012Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 12 clears."
	::= 20012

dpsRTUp0013Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 13 is set."
	::= 10013

dpsRTUp0013Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 13 clears."
	::= 20013

dpsRTUp0014Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 14 is set."
	::= 10014

dpsRTUp0014Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 14 clears."
	::= 20014

dpsRTUp0015Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 15 is set."
	::= 10015

dpsRTUp0015Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 15 clears."
	::= 20015

dpsRTUp0016Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 16 is set."
	::= 10016

dpsRTUp0016Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 16 clears."
	::= 20016

dpsRTUp0017Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 17 is set."
	::= 10017

dpsRTUp0017Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 17 clears."
	::= 20017

dpsRTUp0018Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 18 is set."
	::= 10018

dpsRTUp0018Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 18 clears."
	::= 20018

dpsRTUp0019Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 19 is set."
	::= 10019

dpsRTUp0019Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 19 clears."
	::= 20019

dpsRTUp0020Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 20 is set."
	::= 10020

dpsRTUp0020Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 20 clears."
	::= 20020

dpsRTUp0021Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 21 is set."
	::= 10021

dpsRTUp0021Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 21 clears."
	::= 20021

dpsRTUp0022Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 22 is set."
	::= 10022

dpsRTUp0022Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 22 clears."
	::= 20022

dpsRTUp0023Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 23 is set."
	::= 10023

dpsRTUp0023Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 23 clears."
	::= 20023

dpsRTUp0024Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 24 is set."
	::= 10024

dpsRTUp0024Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 24 clears."
	::= 20024

dpsRTUp0025Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 25 is set."
	::= 10025

dpsRTUp0025Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 25 clears."
	::= 20025

dpsRTUp0026Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 26 is set."
	::= 10026

dpsRTUp0026Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 26 clears."
	::= 20026

dpsRTUp0027Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 27 is set."
	::= 10027

dpsRTUp0027Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 27 clears."
	::= 20027

dpsRTUp0028Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 28 is set."
	::= 10028

dpsRTUp0028Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 28 clears."
	::= 20028

dpsRTUp0029Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 29 is set."
	::= 10029

dpsRTUp0029Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 29 clears."
	::= 20029

dpsRTUp0030Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 30 is set."
	::= 10030

dpsRTUp0030Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 30 clears."
	::= 20030

dpsRTUp0031Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 31 is set."
	::= 10031

dpsRTUp0031Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 31 clears."
	::= 20031

dpsRTUp0032Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 32 is set."
	::= 10032

dpsRTUp0032Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 32 clears."
	::= 20032

dpsRTUp0033Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 33 is set."
	::= 10033

dpsRTUp0033Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 33 clears."
	::= 20033

dpsRTUp0034Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 34 is set."
	::= 10034

dpsRTUp0034Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 34 clears."
	::= 20034

dpsRTUp0035Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 35 is set."
	::= 10035

dpsRTUp0035Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 35 clears."
	::= 20035

dpsRTUp0036Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 36 is set."
	::= 10036

dpsRTUp0036Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 36 clears."
	::= 20036

dpsRTUp0037Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 37 is set."
	::= 10037

dpsRTUp0037Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 37 clears."
	::= 20037

dpsRTUp0038Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 38 is set."
	::= 10038

dpsRTUp0038Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 38 clears."
	::= 20038

dpsRTUp0039Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 39 is set."
	::= 10039

dpsRTUp0039Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 39 clears."
	::= 20039

dpsRTUp0040Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 40 is set."
	::= 10040

dpsRTUp0040Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 40 clears."
	::= 20040

dpsRTUp0041Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 41 is set."
	::= 10041

dpsRTUp0041Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 41 clears."
	::= 20041

dpsRTUp0042Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 42 is set."
	::= 10042

dpsRTUp0042Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 42 clears."
	::= 20042

dpsRTUp0043Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 43 is set."
	::= 10043

dpsRTUp0043Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 43 clears."
	::= 20043

dpsRTUp0044Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 44 is set."
	::= 10044

dpsRTUp0044Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 44 clears."
	::= 20044

dpsRTUp0045Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 45 is set."
	::= 10045

dpsRTUp0045Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 45 clears."
	::= 20045

dpsRTUp0046Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 46 is set."
	::= 10046

dpsRTUp0046Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 46 clears."
	::= 20046

dpsRTUp0047Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 47 is set."
	::= 10047

dpsRTUp0047Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 47 clears."
	::= 20047

dpsRTUp0048Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 48 is set."
	::= 10048

dpsRTUp0048Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 48 clears."
	::= 20048

dpsRTUp0049Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 49 is set."
	::= 10049

dpsRTUp0049Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 49 clears."
	::= 20049

dpsRTUp0050Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 50 is set."
	::= 10050

dpsRTUp0050Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 50 clears."
	::= 20050

dpsRTUp0051Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 51 is set."
	::= 10051

dpsRTUp0051Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 51 clears."
	::= 20051

dpsRTUp0052Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 52 is set."
	::= 10052

dpsRTUp0052Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 52 clears."
	::= 20052

dpsRTUp0053Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 53 is set."
	::= 10053

dpsRTUp0053Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 53 clears."
	::= 20053

dpsRTUp0054Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 54 is set."
	::= 10054

dpsRTUp0054Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 54 clears."
	::= 20054

dpsRTUp0055Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 55 is set."
	::= 10055

dpsRTUp0055Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 55 clears."
	::= 20055

dpsRTUp0056Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 56 is set."
	::= 10056

dpsRTUp0056Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 56 clears."
	::= 20056

dpsRTUp0057Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 57 is set."
	::= 10057

dpsRTUp0057Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 57 clears."
	::= 20057

dpsRTUp0058Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 58 is set."
	::= 10058

dpsRTUp0058Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 58 clears."
	::= 20058

dpsRTUp0059Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 59 is set."
	::= 10059

dpsRTUp0059Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 59 clears."
	::= 20059

dpsRTUp0060Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 60 is set."
	::= 10060

dpsRTUp0060Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 60 clears."
	::= 20060

dpsRTUp0061Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 61 is set."
	::= 10061

dpsRTUp0061Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 61 clears."
	::= 20061

dpsRTUp0062Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 62 is set."
	::= 10062

dpsRTUp0062Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 62 clears."
	::= 20062

dpsRTUp0063Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 63 is set."
	::= 10063

dpsRTUp0063Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 63 clears."
	::= 20063

dpsRTUp0064Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 64 is set."
	::= 10064

dpsRTUp0064Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when granular point 64 clears."
	::= 20064


END
