--  ============================================================================
-- Copyright (C) 2003 by  HUAWEI TECHNOLOGIES. All rights reserved.
--
-- Description:
-- Reference:
-- Version: V1.07
-- ============================================================================

	HUAWEI-CLK-MIB DEFINITIONS ::= BEGIN

		IMPORTS
			huaweiUtility
				FROM HUAWEI-MIB
			Integer32, OBJECT-TYPE, MODULE-IDENTITY
				FROM SNMPv2-SMI
			RowStatus, TruthValue
				FROM SNMPv2-TC;


		hwClock MODULE-IDENTITY
			LAST-UPDATED "0411051600Z"
			ORGANIZATION
				"Fix-Net Dept, Huawei Technologies Co.,Ltd."
			CONTACT-INFO
				"Floor 5 ,Block 4, R&D Building,
				Huawei Longgang Production Base,
				Shenzhen,   P.R.C.
				http://www.huawei.com
				Zip:518057
				"
			DESCRIPTION
				"Clock Management MIB .
				 Added the Nodes of hwUASystemWorkMode And hw3rdClkSubBoardWorkMode by fengjinchun
				 "
			::= { huaweiUtility 25 }


		hwClkMibObjects OBJECT IDENTIFIER ::= { hwClock 1 }


		hwClockInManageTable OBJECT-TYPE
			SYNTAX SEQUENCE OF HwClockInManageEntry
			MAX-ACCESS not-accessible
			STATUS current
			DESCRIPTION
				"Clock Source Management Table (the max record number is 10)"
			::= { hwClkMibObjects 1 }


		hwClockInManageEntry OBJECT-TYPE
			SYNTAX HwClockInManageEntry
			MAX-ACCESS not-accessible
			STATUS current
			DESCRIPTION
				"Clock Source Management Table Entity"
			INDEX { hwClkInIndex }
			::= { hwClockInManageTable 1 }

		HwClockInManageEntry ::=
			SEQUENCE {
				hwClkInIndex
					INTEGER,
				hwClkInPostion
					Integer32,
				hwClkInWorkMode
					INTEGER,
				hwClkInOperStatus
					INTEGER,
				hwClkInRowStatus
					RowStatus,
				hwClkInBitsImpedance
					INTEGER,
                                hwClkInBitsType
					INTEGER
			 }


		hwClkInIndex OBJECT-TYPE
			SYNTAX INTEGER (0..9 | 255)
			MAX-ACCESS not-accessible
			STATUS current
			DESCRIPTION
				"Clock source index: from 0 to 9 is effective, 255 indicates local source"
			::= { hwClockInManageEntry 1 }


		hwClkInPostion OBJECT-TYPE
			SYNTAX Integer32
			MAX-ACCESS read-create
			STATUS current
			DESCRIPTION
				" The ifIndex of physical position of clock source.If the clock source isn't
				a sysline clock, the value will be NULL_ULONG(0xFFFFFFFFFFFFFF).The highest
				byte is useless.The second byte describes the NO. of frame, the third byte
				describes the NO. of slot and the lowest byte describes the port ID.
				The following shows how to use parameter when getting or setting:
			        0x 0000, FFFF,0000,0000  Frame ID;     0~255
          			0x 0000, 0000,FFFF,0000  Slot  ID;     0~255
                                0x 0000, 0000,0000,FFFF  Port  ID;     0~255"
			::= { hwClockInManageEntry 2 }


		hwClkInWorkMode OBJECT-TYPE
			SYNTAX INTEGER
				{
				none(1),
				sysLine(2),
				cesLine(3),
				cesSrts(4),
				e1Bits0(5),
				e1Bits1(6),
				f2mhzBits0(7),
				f2mhzBits1(8),
				msuSdh(9),
				msuTdm(10),
				localSurge(11),
				xpm-8k(12)
				}
			MAX-ACCESS read-create
			STATUS current
			DESCRIPTION
				"Clock source type:
				none(1),    -- clock source not configuration
				sysLine(2), -- line clock source that need to specify frame/slot/port
				cesLine(3), -- line_clk of a ces clock source
				cesSrts(4), -- srts_clk of a ces clock source
				e1Bits0(5), -- e1 type of a bits0 clock source
				e1Bits1(6), -- e1 type of a bits1 clock source
				f2mhzBits0(7),-- 2MHZ type of a bits0 clock source
				f2mhzBits1(8),-- 2MHZ type of a bits1 clock source
				msuSdh(9),   -- sdh_clk of a msu clock source
				msuTdm(10),   -- tdm_clk of a msu clock source
				localSurge(11), -- local surge clock
				xpm-8k(12),  --xpm-8k type of a xpm-8k clock source
				includes line clock source,  bits clock source,local surge source,
				If it is line clock source of ces port, it may be ces line or ces srts clock source,.
				If it is bits clock source, it may be 2MHZ or e1 clock source of bits0, or 2MHZ or e1.
				clock source of bits1. if the value is 1, it indicates that clock source isn't configured"
			::= { hwClockInManageEntry 3 }


		hwClkInOperStatus OBJECT-TYPE
			SYNTAX INTEGER
				{
				none(1),
				normal(2),
				failure(3)
				}
			MAX-ACCESS read-only
			STATUS current
			DESCRIPTION
				"clock source state：
				none(1),   -- clock source index isn't configured
				normal(2), -- the state of clock source is active
				failure(3) -- the state of clock source fails."
			::= { hwClockInManageEntry 4 }


		hwClkInRowStatus OBJECT-TYPE
			SYNTAX RowStatus
			MAX-ACCESS read-create
			STATUS current
			DESCRIPTION
				"Clock Source operation：add clock source and clear
				clock source by user. when a user adds clock source, clock
				works in trace mode and when a user clears clock source
				clock works in srystal mode. To set position(frame,slot,port)
				and oper(4), these two operation should be set together.
				oper(6) could be set by itself. To set a bit clock source,
				the frame,slot,port parameters are useless.
				Oper(6) is used to clear a clock source."
			::= { hwClockInManageEntry 5 }


		hwClkInBitsImpedance OBJECT-TYPE
			SYNTAX INTEGER
				{
				bits_impedance_75ohm(1),
				bits_impedance_120ohm(2),
				bits_impedance_none(255)
				}
			MAX-ACCESS read-create
			STATUS current
			DESCRIPTION
				"BITS clock impedance type:
				bits_impedance_75ohm(1),  -- the impedance of this bits clock source is 75 ohm
				bits_impedance_120ohm(2),  -- the impedance of this bits clock source is 120 ohm
				bits_impedance_none(255),   -- this clock source is not a bits clock
				The impedance value must been set when the clock source is a bits clock"
			::= { hwClockInManageEntry 6 }

		hwClkInBitsType OBJECT-TYPE
			SYNTAX INTEGER
				{
				bits_type_2MHz(1),
				bits_type_2Mbps(2),
				bits_type_none(255)
				}
			MAX-ACCESS read-create
			STATUS current
			DESCRIPTION
				"BITS clock type:
				bits_2MHz(1),  -- the bits type is 2MHz
				bits_2Mbps(2),  -- the bits type is 2bps
				bits_type_none(255) -- the clock source is not a bits clock
				The impedance value must been set when the clock source is a bits clock"
			::= { hwClockInManageEntry 7 }


		hwClockOutManageTable OBJECT-TYPE
			SYNTAX SEQUENCE OF HwClockOutManageEntry
			MAX-ACCESS not-accessible
			STATUS current
			DESCRIPTION
				"Clock Out Management Table (the max record number is 10)
				"
			::= { hwClkMibObjects 2 }


		hwClockOutManageEntry OBJECT-TYPE
			SYNTAX HwClockOutManageEntry
			MAX-ACCESS not-accessible
			STATUS current
			DESCRIPTION
				"Clock Out Management Table Entity
				"
			INDEX { hwClkInIndex, hwClkOutIndex }
			::= { hwClockOutManageTable 1 }

		HwClockOutManageEntry ::=
			SEQUENCE {
				hwClkOutIndex
					INTEGER,
				hwClkOutType
					INTEGER,
				hwClkOutPriority
					INTEGER,
				hwClkOutWorkMode
					INTEGER,
				hwClkOutOperStatus
					TruthValue
			 }


		hwClkOutIndex OBJECT-TYPE
			SYNTAX INTEGER (1..4)
			MAX-ACCESS not-accessible
			STATUS current
			DESCRIPTION
				"index of clock out type, its meaning is the same as hwClkOutType.
				The clock out index must be 8k in UA system and must be sdh or
				tdm in MD/MA system during the setting of priority for a clock source."
			::= { hwClockOutManageEntry 1 }


		hwClkOutType OBJECT-TYPE
			SYNTAX INTEGER
				{
				sdh(1),
				tdm(2),
				clk8K(3),
				clk19M(4)
				}
			MAX-ACCESS read-only
			STATUS current
			DESCRIPTION
				"Clock Out Type, at present there are four types: sdh, tdm, 8k and 19m.
				"
			::= { hwClockOutManageEntry 2 }


		hwClkOutPriority OBJECT-TYPE
			SYNTAX INTEGER (0..9 | 255)
			MAX-ACCESS read-write
			STATUS current
			DESCRIPTION
				"Clock source priority, 0 is the highest priority and from 0 to 9 priority is descending
				If get value is 255, it indicates that the priority of the clock souce isn't configured.
				"
			DEFVAL { 255 }
			::= { hwClockOutManageEntry 3 }


		hwClkOutWorkMode OBJECT-TYPE
			SYNTAX INTEGER
				{
				trace(1),
				surge(2),
				keep(3),
				snap(4),
				thirdsurge(5)
				}
			MAX-ACCESS read-only
			STATUS current
			DESCRIPTION
				"The Out work mode of clock:
				trace(1) indicates clock is  working in tracing mode
				surge(2) indicates clock is working in surge mode
				keep(3) indicates clock is working in keeping mode
				snap(4) indicates clock is working in snapping mode"
			::= { hwClockOutManageEntry 4 }


		hwClkOutOperStatus OBJECT-TYPE
			SYNTAX TruthValue
			MAX-ACCESS read-only
			STATUS current
			DESCRIPTION
				"Clock source Out state. It indicates whether the clock source is
				the Out clock of system: 1--yes, 2--no
				"
			::= { hwClockOutManageEntry 5 }


	        hwSystemClockManagePara OBJECT IDENTIFIER ::= { hwClkMibObjects 3 }
	        hwUASystemWorkMode OBJECT-TYPE
	                        SYNTAX INTEGER
	                                {
	                                olt(1),
	                                onu(2)
	                                }
	                        MAX-ACCESS read-write
	                        STATUS current
	                        DESCRIPTION
	                                "UA work mode:
	                                 OLT(1),--UA works as OLT in VPRING
	                                 ONU(2),--UA works as ONU in VPRING"
	                        ::= { hwSystemClockManagePara 1 }

		hw3rdClkSubBoardWorkMode OBJECT-TYPE
                 		SYNTAX INTEGER
					{
					trace(1),
					keep(2),
					thirdsurge(3),
					snap(4),
					no3rdclksubboard(255)
					}
		        	MAX-ACCESS read-only
				STATUS current
				DESCRIPTION
					"The Out work mode of 3rd subboard clock:
					trace(1) indicates clock is working in tracing mode
					keep(2) indicates clock is working in keeping mode
					3rdsurge(3) indicates clock is working in 3rd subboard crystal
					snap(4) indicates clock is working in snap mode
					no3rdclksubboard(255) indicates does not have 3rd subboard"
				::= { hwSystemClockManagePara 2 }

		hwSystemClockMode OBJECT-TYPE
                 		SYNTAX INTEGER
					{
					clock-clksubboard(1),
					clock-localboard(2),
					}
		        	MAX-ACCESS read-only
				STATUS current
				DESCRIPTION
					"The Clock mode:
					clock-clksubboard(1) clock-subboard supply output clock
					clock-localboard(2) local-board supplay output clock"
				::= { hwSystemClockManagePara 3 }

		hw3rdClkSubBoardInputStatus OBJECT-TYPE
                 		SYNTAX INTEGER
					{
					none(1),
					normal(2),
					fault(3),
					no3rdclksubboard(255)
					}
		        	MAX-ACCESS read-only
				STATUS current
				DESCRIPTION
					"The Clock mode:
					none(1) clock-subboard have no clock-signal input
					normal(2) clock-subboard clock-signal input normal
					fault(3) clock-subboard clock-signal input fault
					no3rdclksubboard(255) indicates does not have 3rd subboard"
				::= { hwSystemClockManagePara 4 }

		hw3rdClkSubBoardOutputStatus OBJECT-TYPE
                 		SYNTAX INTEGER
					{
					normal(1),
					fault(2),
					no3rdclksubboard(255)
					}
		        	MAX-ACCESS read-only
				STATUS current
				DESCRIPTION
					"The Clock mode:
					normal(1) clock-subboard output status normal
					fault(2) clock-subboard output status fault
					no3rdclksubboard(255) indicates does not have 3rd subboard"
				::= { hwSystemClockManagePara 5 }

	-- BEGIN: Added by IASV500R003-PLT-C001  BITS  y60005409, 2006/8/9
	    hwClockOutPortManageTable OBJECT-TYPE
			SYNTAX SEQUENCE OF HwClockOutPortManageEntry
			MAX-ACCESS not-accessible
			STATUS current
			DESCRIPTION
				"Clock Out Port Management Table(the max record number is 24)
				"
			::= { hwClkMibObjects 4 }


		hwClockOutPortManageEntry OBJECT-TYPE
			SYNTAX HwClockOutPortManageEntry
			MAX-ACCESS not-accessible
			STATUS current
			DESCRIPTION
				"Clock Out Port Management Table Entity
				"
			INDEX { hwClkOutputPostion }
			::= { hwClockOutPortManageTable 1 }

		HwClockOutPortManageEntry ::=
			SEQUENCE {
		     	hwClkOutputPostion
					Integer32,

				hwClkOutPortEnable
					INTEGER
			 }

	    hwClkOutputPostion OBJECT-TYPE
			SYNTAX Integer32
			MAX-ACCESS read-create
			STATUS current
			DESCRIPTION
				" The ifIndex of physical position of clock source.The highest
				byte is useless.The second byte describes the NO. of frame, the third byte
				describes the NO. of slot and the lowest byte describes the NO. of port.
				How to use parameter when getting or setting is as below:
			        0x 0000, FFFF,0000,0000  Frame ID;     0~255
          			0x 0000, 0000,FFFF,0000  Slot  ID;     0~255
                                0x 0000, 0000,0000,FFFF  Port  ID;     0~255"
			::= { hwClockOutPortManageEntry 1 }


				hwClkOutPortEnable OBJECT-TYPE
			SYNTAX INTEGER
				{
				enable(0),
				disable(1)
     			}
			MAX-ACCESS read-create
			STATUS current
			DESCRIPTION
				"Clock source type:
				enable(0),    -- Enabled this bits-port clock source output
				              -- that need to specify frame/slot/port

				disable(1),   -- Disabled this bits-port clock source output
				              -- that need to specify frame/slot/port
				"
			::= { hwClockOutPortManageEntry 2 }





	END
