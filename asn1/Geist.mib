GEIST-MIB DEFINITIONS ::= BEGIN

IMPORTS 


DisplayString, TruthValue					FROM SNMPv2-TC
MODULE-IDENTITY, OBJECT-TYPE, enterprises, Unsigned32		FROM SNMPv2-SMI
TRAP-TYPE							FROM RFC-1215;

geistmfg MODULE-IDENTITY
	LAST-UPDATED "200601170000Z"
	ORGANIZATION "Geist Manufacturing"
	CONTACT-INFO "support@geistmfg.com"
	DESCRIPTION "The MIB for Geist Products"
	::= { enterprises 21239 }

geistmfg OBJECT IDENTIFIER
	::= { enterprises 21239 }
	
geist OBJECT IDENTIFIER
	::= { geistmfg 1 }

deviceInfo OBJECT IDENTIFIER
	::= { geist 1 }

productTitle OBJECT-TYPE
	SYNTAX DisplayString
	MAX-ACCESS read-only
	STATUS current
	DESCRIPTION "Product name"
	::= { deviceInfo 1 }

productVersion OBJECT-TYPE
	SYNTAX DisplayString
	MAX-ACCESS read-only
	STATUS current
	DESCRIPTION "Product version"
	::= { deviceInfo 2 }

productFriendlyName OBJECT-TYPE
	SYNTAX DisplayString
	MAX-ACCESS read-only
	STATUS current
	DESCRIPTION "User-assigned name"
	::= { deviceInfo 3 }

productMacAddress OBJECT-TYPE
	SYNTAX DisplayString
	MAX-ACCESS read-only
	STATUS current
	DESCRIPTION "Product's unique MAC address"
	::= { deviceInfo 4 }

productUrl OBJECT-TYPE
	SYNTAX DisplayString
	MAX-ACCESS read-only
	STATUS current
	DESCRIPTION "Product's main URL access point"
	::= { deviceInfo 5 }

alarmTripType OBJECT-TYPE
        SYNTAX INTEGER(0..9)
        MAX-ACCESS read-only
        STATUS current
        DESCRIPTION "Type of alarm trip. 0 = None, 1 = Low, 2 = High, 3 = Unplugged"
        ::= { deviceInfo 6 }

climateTable OBJECT-TYPE
	SYNTAX SEQUENCE OF ClimateEntry
	MAX-ACCESS  not-accessible
	STATUS current
	DESCRIPTION "Climate sensors (internal sensors for RacSense units)"
	::= { geist 2 }

powerMonitorTable OBJECT-TYPE
	SYNTAX SEQUENCE OF PowerMonitorEntry
	MAX-ACCESS  not-accessible
	STATUS current
	DESCRIPTION "A table of Power Monitors"
	::= { geist 3 }

tempSensorTable OBJECT-TYPE
	SYNTAX SEQUENCE OF TempSensorEntry
	MAX-ACCESS  not-accessible
	STATUS current
	DESCRIPTION "A table of temperature sensors"
	::= { geist 4 }

airFlowSensorTable OBJECT-TYPE
	SYNTAX SEQUENCE OF AirFlowSensorEntry
	MAX-ACCESS  not-accessible
	STATUS current
	DESCRIPTION "A table of airflow sensors"
	::= { geist 5 }

powerOnlyTable OBJECT-TYPE
	SYNTAX SEQUENCE OF PowerOnlyEntry
	MAX-ACCESS  not-accessible
	STATUS current
	DESCRIPTION "A table of Power-Only devices"
	::= { geist 6 }

doorSensorTable OBJECT-TYPE
	SYNTAX SEQUENCE OF DoorSensorEntry
	MAX-ACCESS  not-accessible
	STATUS current
	DESCRIPTION "A table of door sensors"
	::= { geist 7 }

waterSensorTable OBJECT-TYPE
	SYNTAX SEQUENCE OF WaterSensorEntry
	MAX-ACCESS  not-accessible
	STATUS current
	DESCRIPTION "A table of water sensors"
	::= { geist 8 }

currentMonitorTable OBJECT-TYPE
	SYNTAX SEQUENCE OF CurrentMonitorEntry
	MAX-ACCESS  not-accessible
	STATUS current
	DESCRIPTION "A table of current monitors"
	::= { geist 9 }

millivoltMonitorTable OBJECT-TYPE
	SYNTAX SEQUENCE OF MillivoltMonitorEntry
	MAX-ACCESS  not-accessible
	STATUS current
	DESCRIPTION "A table of millivolt monitors"
	::= { geist 10 }

power3ChTable OBJECT-TYPE
	SYNTAX SEQUENCE OF Power3ChEntry
	MAX-ACCESS  not-accessible
	STATUS current
	DESCRIPTION "A table of Power Monitor 3 Channel"
	::= { geist 11 }

outletTable OBJECT-TYPE
	SYNTAX SEQUENCE OF OutletEntry
	MAX-ACCESS  not-accessible
	STATUS current
	DESCRIPTION "A table of outlets"
	::= { geist 12 }

vsfcTable OBJECT-TYPE
	SYNTAX SEQUENCE OF VsfcEntry
	MAX-ACCESS  not-accessible
	STATUS current
	DESCRIPTION "VSFC sensors (internal sensors for VSFC units)"
	::= { geist 13 }

ctrl3ChTable OBJECT-TYPE
	SYNTAX SEQUENCE OF Ctrl3ChEntry
	MAX-ACCESS  not-accessible
	STATUS current
	DESCRIPTION "A table of a 3 phase outlet control"
	::= { geist 14 }

ctrlGrpAmpsTable OBJECT-TYPE
	SYNTAX SEQUENCE OF CtrlGrpAmpsEntry
	MAX-ACCESS  not-accessible
	STATUS current
	DESCRIPTION "A table of Control Group Amp readings"
	::= { geist 15 }

ctrlOutletTable OBJECT-TYPE
	SYNTAX SEQUENCE OF CtrlOutletEntry
	MAX-ACCESS  not-accessible
	STATUS current
	DESCRIPTION "A table of outlet information"
	::= { geist 16 }

dewPointSensorTable OBJECT-TYPE
	SYNTAX SEQUENCE OF DewPointSensorEntry
	MAX-ACCESS  not-accessible
	STATUS current
	DESCRIPTION "A table of dew point sensors"
	::= { geist 17 }

climateEntry OBJECT-TYPE
	SYNTAX  ClimateEntry
	MAX-ACCESS  not-accessible
	STATUS current
	DESCRIPTION 
		"Entry in the climate table: each entry contains
an index (climateIndex) and other power strip details"
	INDEX { climateIndex }
	::= { climateTable 1 }

ClimateEntry ::= SEQUENCE {
	climateIndex		INTEGER(1..1),
	climateSerial		DisplayString,
	climateName		DisplayString,
	climateAvail		TruthValue,
	climateTempC		INTEGER(-50..100),
	climateHumidity		INTEGER(0..100),
	climateAirflow		INTEGER(0..100),
	climateLight		INTEGER(0..100),
	climateSound		INTEGER(0..100),
	climateIO1		INTEGER(0..100),
	climateIO2		INTEGER(0..100),
	climateIO3		INTEGER(0..100),
	climateVolts		Unsigned32,
	climateVoltPeak		Unsigned32,
	climateAmpsA		Unsigned32,
	climateAmpPeakA		Unsigned32,
	climateRealPowerA		Unsigned32,
	climateApparentPowerA		Unsigned32,
	climatePowerFactorA		Unsigned32,
	climateAmpsB		Unsigned32,
	climateAmpPeakB		Unsigned32,
	climateRealPowerB		Unsigned32,
	climateApparentPowerB		Unsigned32,
	climatePowerFactorB		Unsigned32,
	climateAmpsC		Unsigned32,
	climateAmpPeakC		Unsigned32,
	climateRealPowerC		Unsigned32,
	climateApparentPowerC		Unsigned32,
	climatePowerFactorC		Unsigned32
}

climateIndex OBJECT-TYPE
	SYNTAX  INTEGER(1..1)
	MAX-ACCESS  not-accessible
	STATUS current
	DESCRIPTION "Table entry index value"
	::= { climateEntry  1 }
	
climateSerial OBJECT-TYPE
	SYNTAX  DisplayString
	MAX-ACCESS  read-only
	STATUS current
	DESCRIPTION "Serial Number"
	::= { climateEntry  2 }
	
climateName OBJECT-TYPE
	SYNTAX  DisplayString
	MAX-ACCESS  read-only
	STATUS current
	DESCRIPTION "Friendly Name"
	::= { climateEntry  3 }
	
climateAvail OBJECT-TYPE
	SYNTAX  TruthValue
	MAX-ACCESS  read-only
	STATUS current
	DESCRIPTION "Is device currently plugged in?"
	::= { climateEntry  4 }
	
climateTempC OBJECT-TYPE
	SYNTAX  INTEGER(-50..100)
	MAX-ACCESS  read-only
	STATUS current
	DESCRIPTION "Current reading for Temperature (C)"
	::= { climateEntry  5 }
	
climateHumidity OBJECT-TYPE
	SYNTAX  INTEGER(0..100)
	MAX-ACCESS  read-only
	STATUS current
	DESCRIPTION "Current reading for Humidity"
	::= { climateEntry  6 }
	
climateAirflow OBJECT-TYPE
	SYNTAX  INTEGER(0..100)
	MAX-ACCESS  read-only
	STATUS current
	DESCRIPTION "Current reading for Airflow"
	::= { climateEntry  7 }
	
climateLight OBJECT-TYPE
	SYNTAX  INTEGER(0..100)
	MAX-ACCESS  read-only
	STATUS current
	DESCRIPTION "Current reading for Ambient Light"
	::= { climateEntry  8 }
	
climateSound OBJECT-TYPE
	SYNTAX  INTEGER(0..100)
	MAX-ACCESS  read-only
	STATUS current
	DESCRIPTION "Current reading for Sound"
	::= { climateEntry  9 }
	
climateIO1 OBJECT-TYPE
	SYNTAX  INTEGER(0..100)
	MAX-ACCESS  read-only
	STATUS current
	DESCRIPTION "Current reading for Analog Input 1"
	::= { climateEntry  10 }
	
climateIO2 OBJECT-TYPE
	SYNTAX  INTEGER(0..100)
	MAX-ACCESS  read-only
	STATUS current
	DESCRIPTION "Current reading for Analog Input 2"
	::= { climateEntry  11 }
	
climateIO3 OBJECT-TYPE
	SYNTAX  INTEGER(0..100)
	MAX-ACCESS  read-only
	STATUS current
	DESCRIPTION "Current reading for Analog Input 3"
	::= { climateEntry  12 }
	
climateVolts OBJECT-TYPE
	SYNTAX  Unsigned32
	MAX-ACCESS  read-only
	STATUS current
	DESCRIPTION "Current reading for Volts"
	::= { climateEntry  13 }
	
climateVoltPeak OBJECT-TYPE
	SYNTAX  Unsigned32
	MAX-ACCESS  read-only
	STATUS current
	DESCRIPTION "Current reading for Peak-Volts"
	::= { climateEntry  14 }
	
climateAmpsA OBJECT-TYPE
	SYNTAX  Unsigned32
	MAX-ACCESS  read-only
	STATUS current
	DESCRIPTION "Current reading for Amps (Phase A)"
	::= { climateEntry  15 }
	
climateAmpPeakA OBJECT-TYPE
	SYNTAX  Unsigned32
	MAX-ACCESS  read-only
	STATUS current
	DESCRIPTION "Current reading for Peak-Amps (Phase A)"
	::= { climateEntry  16 }
	
climateRealPowerA OBJECT-TYPE
	SYNTAX  Unsigned32
	MAX-ACCESS  read-only
	STATUS current
	DESCRIPTION "Current reading for Real Power (Phase A)"
	::= { climateEntry  17 }
	
climateApparentPowerA OBJECT-TYPE
	SYNTAX  Unsigned32
	MAX-ACCESS  read-only
	STATUS current
	DESCRIPTION "Current reading for Apparent Power (Phase A)"
	::= { climateEntry  18 }
	
climatePowerFactorA OBJECT-TYPE
	SYNTAX  Unsigned32
	MAX-ACCESS  read-only
	STATUS current
	DESCRIPTION "Current reading for Power Factor (Phase A)"
	::= { climateEntry  19 }
	
climateAmpsB OBJECT-TYPE
	SYNTAX  Unsigned32
	MAX-ACCESS  read-only
	STATUS current
	DESCRIPTION "Current reading for Amps (Phase B)"
	::= { climateEntry  20 }
	
climateAmpPeakB OBJECT-TYPE
	SYNTAX  Unsigned32
	MAX-ACCESS  read-only
	STATUS current
	DESCRIPTION "Current reading for Peak-Amps (Phase B)"
	::= { climateEntry  21 }
	
climateRealPowerB OBJECT-TYPE
	SYNTAX  Unsigned32
	MAX-ACCESS  read-only
	STATUS current
	DESCRIPTION "Current reading for Real Power (Phase B)"
	::= { climateEntry  22 }
	
climateApparentPowerB OBJECT-TYPE
	SYNTAX  Unsigned32
	MAX-ACCESS  read-only
	STATUS current
	DESCRIPTION "Current reading for Apparent Power (Phase B)"
	::= { climateEntry  23 }
	
climatePowerFactorB OBJECT-TYPE
	SYNTAX  Unsigned32
	MAX-ACCESS  read-only
	STATUS current
	DESCRIPTION "Current reading for Power Factor (Phase B)"
	::= { climateEntry  24 }
	
climateAmpsC OBJECT-TYPE
	SYNTAX  Unsigned32
	MAX-ACCESS  read-only
	STATUS current
	DESCRIPTION "Current reading for Amps (Phase C)"
	::= { climateEntry  25 }
	
climateAmpPeakC OBJECT-TYPE
	SYNTAX  Unsigned32
	MAX-ACCESS  read-only
	STATUS current
	DESCRIPTION "Current reading for Peak-Amps (Phase C)"
	::= { climateEntry  26 }
	
climateRealPowerC OBJECT-TYPE
	SYNTAX  Unsigned32
	MAX-ACCESS  read-only
	STATUS current
	DESCRIPTION "Current reading for Real Power (Phase C)"
	::= { climateEntry  27 }
	
climateApparentPowerC OBJECT-TYPE
	SYNTAX  Unsigned32
	MAX-ACCESS  read-only
	STATUS current
	DESCRIPTION "Current reading for Apparent Power (Phase C)"
	::= { climateEntry  28 }
	
climatePowerFactorC OBJECT-TYPE
	SYNTAX  Unsigned32
	MAX-ACCESS  read-only
	STATUS current
	DESCRIPTION "Current reading for Power Factor (Phase C)"
	::= { climateEntry  29 }
	
powerMonitorEntry OBJECT-TYPE
	SYNTAX  PowerMonitorEntry
	MAX-ACCESS  not-accessible
	STATUS current
	DESCRIPTION 
		"Entry in the power monitor table: each entry contains
an index (powMonIndex) and other power monitoring details"
	INDEX { powMonIndex }
	::= { powerMonitorTable 1 }

PowerMonitorEntry ::= SEQUENCE {
	powMonIndex		INTEGER(1..100),
	powMonSerial		DisplayString,
	powMonName		DisplayString,
	powMonAvail		TruthValue,
	powMonKWattHrs		Unsigned32,
	powMonVolts		Unsigned32,
	powMonVoltMax		Unsigned32,
	powMonVoltMin		Unsigned32,
	powMonVoltPk		Unsigned32,
	powMonAmpsX10		Unsigned32,
	powMonRealPow		Unsigned32,
	powMonAppPow		Unsigned32,
	powMonPwrFact		INTEGER(0..100),
	powMonOutlet1		INTEGER(0..100),
	powMonOutlet2		INTEGER(0..100)
}

powMonIndex OBJECT-TYPE
	SYNTAX  INTEGER(1..100)
	MAX-ACCESS  not-accessible
	STATUS current
	DESCRIPTION "Table entry index value"
	::= { powerMonitorEntry  1 }
	
powMonSerial OBJECT-TYPE
	SYNTAX  DisplayString
	MAX-ACCESS  read-only
	STATUS current
	DESCRIPTION "Serial Number"
	::= { powerMonitorEntry  2 }
	
powMonName OBJECT-TYPE
	SYNTAX  DisplayString
	MAX-ACCESS  read-only
	STATUS current
	DESCRIPTION "Friendly Name"
	::= { powerMonitorEntry  3 }
	
powMonAvail OBJECT-TYPE
	SYNTAX  TruthValue
	MAX-ACCESS  read-only
	STATUS current
	DESCRIPTION "Is device currently plugged in?"
	::= { powerMonitorEntry  4 }
	
powMonKWattHrs OBJECT-TYPE
	SYNTAX  Unsigned32
	MAX-ACCESS  read-only
	STATUS current
	DESCRIPTION "KWatt-Hours"
	::= { powerMonitorEntry  5 }
	
powMonVolts OBJECT-TYPE
	SYNTAX  Unsigned32
	MAX-ACCESS  read-only
	STATUS current
	DESCRIPTION "Volts"
	::= { powerMonitorEntry  6 }
	
powMonVoltMax OBJECT-TYPE
	SYNTAX  Unsigned32
	MAX-ACCESS  read-only
	STATUS current
	DESCRIPTION "Volts (Max)"
	::= { powerMonitorEntry  7 }
	
powMonVoltMin OBJECT-TYPE
	SYNTAX  Unsigned32
	MAX-ACCESS  read-only
	STATUS current
	DESCRIPTION "Volts (Min)"
	::= { powerMonitorEntry  8 }
	
powMonVoltPk OBJECT-TYPE
	SYNTAX  Unsigned32
	MAX-ACCESS  read-only
	STATUS current
	DESCRIPTION "Volts (Peak)"
	::= { powerMonitorEntry  9 }
	
powMonAmpsX10 OBJECT-TYPE
	SYNTAX  Unsigned32
	MAX-ACCESS  read-only
	STATUS current
	DESCRIPTION "Amps x 10"
	::= { powerMonitorEntry  10 }
	
powMonRealPow OBJECT-TYPE
	SYNTAX  Unsigned32
	MAX-ACCESS  read-only
	STATUS current
	DESCRIPTION "Real Power"
	::= { powerMonitorEntry  11 }
	
powMonAppPow OBJECT-TYPE
	SYNTAX  Unsigned32
	MAX-ACCESS  read-only
	STATUS current
	DESCRIPTION "Apparent Power"
	::= { powerMonitorEntry  12 }
	
powMonPwrFact OBJECT-TYPE
	SYNTAX  INTEGER(0..100)
	MAX-ACCESS  read-only
	STATUS current
	DESCRIPTION "Power Factor"
	::= { powerMonitorEntry  13 }
	
powMonOutlet1 OBJECT-TYPE
	SYNTAX  INTEGER(0..100)
	MAX-ACCESS  read-only
	STATUS current
	DESCRIPTION "Outlet 1"
	::= { powerMonitorEntry  14 }
	
powMonOutlet2 OBJECT-TYPE
	SYNTAX  INTEGER(0..100)
	MAX-ACCESS  read-only
	STATUS current
	DESCRIPTION "Outlet 2"
	::= { powerMonitorEntry  15 }
	
tempSensorEntry OBJECT-TYPE
	SYNTAX  TempSensorEntry
	MAX-ACCESS  not-accessible
	STATUS current
	DESCRIPTION 
		"Entry in the temperature sensor table: each entry contains
an index (tempIndex) and other sensor details"
	INDEX { tempSensorIndex }
	::= { tempSensorTable 1 }

TempSensorEntry ::= SEQUENCE {
	tempSensorIndex		INTEGER(1..100),
	tempSensorSerial		DisplayString,
	tempSensorName		DisplayString,
	tempSensorAvail		TruthValue,
	tempSensorTempC		INTEGER(-50..100)
}

tempSensorIndex OBJECT-TYPE
	SYNTAX  INTEGER(1..100)
	MAX-ACCESS  not-accessible
	STATUS current
	DESCRIPTION "Table entry index value"
	::= { tempSensorEntry  1 }
	
tempSensorSerial OBJECT-TYPE
	SYNTAX  DisplayString
	MAX-ACCESS  read-only
	STATUS current
	DESCRIPTION "Serial Number"
	::= { tempSensorEntry  2 }
	
tempSensorName OBJECT-TYPE
	SYNTAX  DisplayString
	MAX-ACCESS  read-only
	STATUS current
	DESCRIPTION "Friendly Name"
	::= { tempSensorEntry  3 }
	
tempSensorAvail OBJECT-TYPE
	SYNTAX  TruthValue
	MAX-ACCESS  read-only
	STATUS current
	DESCRIPTION "Is device currently plugged in?"
	::= { tempSensorEntry  4 }
	
tempSensorTempC OBJECT-TYPE
	SYNTAX  INTEGER(-50..100)
	MAX-ACCESS  read-only
	STATUS current
	DESCRIPTION "Temperature in Celsius"
	::= { tempSensorEntry  5 }
	
airFlowSensorEntry OBJECT-TYPE
	SYNTAX  AirFlowSensorEntry
	MAX-ACCESS  not-accessible
	STATUS current
	DESCRIPTION 
		"Entry in the air flow sensor table: each entry contains
an index (airFlowSensorIndex) and other sensor details"
	INDEX { airFlowSensorIndex }
	::= { airFlowSensorTable 1 }

AirFlowSensorEntry ::= SEQUENCE {
	airFlowSensorIndex		INTEGER(1..100),
	airFlowSensorSerial		DisplayString,
	airFlowSensorName		DisplayString,
	airFlowSensorAvail		TruthValue,
	airFlowSensorFlow		INTEGER(0..100),
	airFlowSensorTempC		INTEGER(-50..100),
	airFlowSensorHumidity		INTEGER(0..100)
}

airFlowSensorIndex OBJECT-TYPE
	SYNTAX  INTEGER(1..100)
	MAX-ACCESS  not-accessible
	STATUS current
	DESCRIPTION "Table entry index value"
	::= { airFlowSensorEntry  1 }
	
airFlowSensorSerial OBJECT-TYPE
	SYNTAX  DisplayString
	MAX-ACCESS  read-only
	STATUS current
	DESCRIPTION "Serial Number"
	::= { airFlowSensorEntry  2 }
	
airFlowSensorName OBJECT-TYPE
	SYNTAX  DisplayString
	MAX-ACCESS  read-only
	STATUS current
	DESCRIPTION "Friendly Name"
	::= { airFlowSensorEntry  3 }
	
airFlowSensorAvail OBJECT-TYPE
	SYNTAX  TruthValue
	MAX-ACCESS  read-only
	STATUS current
	DESCRIPTION "Is device currently plugged in?"
	::= { airFlowSensorEntry  4 }
	
airFlowSensorFlow OBJECT-TYPE
	SYNTAX  INTEGER(0..100)
	MAX-ACCESS  read-only
	STATUS current
	DESCRIPTION "Air flow reading"
	::= { airFlowSensorEntry  5 }
	
airFlowSensorTempC OBJECT-TYPE
	SYNTAX  INTEGER(-50..100)
	MAX-ACCESS  read-only
	STATUS current
	DESCRIPTION "Temperature reading in C"
	::= { airFlowSensorEntry  6 }
	
airFlowSensorHumidity OBJECT-TYPE
	SYNTAX  INTEGER(0..100)
	MAX-ACCESS  read-only
	STATUS current
	DESCRIPTION "Humidity reading"
	::= { airFlowSensorEntry  7 }
	
powerOnlyEntry OBJECT-TYPE
	SYNTAX  PowerOnlyEntry
	MAX-ACCESS  not-accessible
	STATUS current
	DESCRIPTION 
		"Entry in the power-only device table: each entry contains
an index (powerIndex) and other power details"
	INDEX { powerIndex }
	::= { powerOnlyTable 1 }

PowerOnlyEntry ::= SEQUENCE {
	powerIndex		INTEGER(1..100),
	powerSerial		DisplayString,
	powerName		DisplayString,
	powerAvail		TruthValue,
	powerVolts		Unsigned32,
	powerAmps		Unsigned32,
	powerRealPow		Unsigned32,
	powerAppPow		Unsigned32,
	powerPwrFactor		INTEGER(0..100)
}

powerIndex OBJECT-TYPE
	SYNTAX  INTEGER(1..100)
	MAX-ACCESS  not-accessible
	STATUS current
	DESCRIPTION "Table entry index value"
	::= { powerOnlyEntry  1 }
	
powerSerial OBJECT-TYPE
	SYNTAX  DisplayString
	MAX-ACCESS  read-only
	STATUS current
	DESCRIPTION "Serial Number"
	::= { powerOnlyEntry  2 }
	
powerName OBJECT-TYPE
	SYNTAX  DisplayString
	MAX-ACCESS  read-only
	STATUS current
	DESCRIPTION "Friendly Name"
	::= { powerOnlyEntry  3 }
	
powerAvail OBJECT-TYPE
	SYNTAX  TruthValue
	MAX-ACCESS  read-only
	STATUS current
	DESCRIPTION "Is device currently plugged in?"
	::= { powerOnlyEntry  4 }
	
powerVolts OBJECT-TYPE
	SYNTAX  Unsigned32
	MAX-ACCESS  read-only
	STATUS current
	DESCRIPTION "Volts"
	::= { powerOnlyEntry  5 }
	
powerAmps OBJECT-TYPE
	SYNTAX  Unsigned32
	MAX-ACCESS  read-only
	STATUS current
	DESCRIPTION "Amps"
	::= { powerOnlyEntry  6 }
	
powerRealPow OBJECT-TYPE
	SYNTAX  Unsigned32
	MAX-ACCESS  read-only
	STATUS current
	DESCRIPTION "Real Power"
	::= { powerOnlyEntry  7 }
	
powerAppPow OBJECT-TYPE
	SYNTAX  Unsigned32
	MAX-ACCESS  read-only
	STATUS current
	DESCRIPTION "Apparent Power"
	::= { powerOnlyEntry  8 }
	
powerPwrFactor OBJECT-TYPE
	SYNTAX  INTEGER(0..100)
	MAX-ACCESS  read-only
	STATUS current
	DESCRIPTION "Power Factor"
	::= { powerOnlyEntry  9 }
	
doorSensorEntry OBJECT-TYPE
	SYNTAX  DoorSensorEntry
	MAX-ACCESS  not-accessible
	STATUS current
	DESCRIPTION 
		"Entry in the door sensor table: each entry contains
an index (doorSensorIndex) and other sensor details"
	INDEX { doorSensorIndex }
	::= { doorSensorTable 1 }

DoorSensorEntry ::= SEQUENCE {
	doorSensorIndex		INTEGER(1..100),
	doorSensorSerial		DisplayString,
	doorSensorName		DisplayString,
	doorSensorAvail		TruthValue,
	doorSensorStatus		INTEGER(0..100)
}

doorSensorIndex OBJECT-TYPE
	SYNTAX  INTEGER(1..100)
	MAX-ACCESS  not-accessible
	STATUS current
	DESCRIPTION "Table entry index value"
	::= { doorSensorEntry  1 }
	
doorSensorSerial OBJECT-TYPE
	SYNTAX  DisplayString
	MAX-ACCESS  read-only
	STATUS current
	DESCRIPTION "Serial Number"
	::= { doorSensorEntry  2 }
	
doorSensorName OBJECT-TYPE
	SYNTAX  DisplayString
	MAX-ACCESS  read-only
	STATUS current
	DESCRIPTION "Friendly Name"
	::= { doorSensorEntry  3 }
	
doorSensorAvail OBJECT-TYPE
	SYNTAX  TruthValue
	MAX-ACCESS  read-only
	STATUS current
	DESCRIPTION "Is device currently plugged in?"
	::= { doorSensorEntry  4 }
	
doorSensorStatus OBJECT-TYPE
	SYNTAX  INTEGER(0..100)
	MAX-ACCESS  read-only
	STATUS current
	DESCRIPTION "Door sensor status"
	::= { doorSensorEntry  5 }
	
waterSensorEntry OBJECT-TYPE
	SYNTAX  WaterSensorEntry
	MAX-ACCESS  not-accessible
	STATUS current
	DESCRIPTION 
		"Entry in the water sensor table: each entry contains
an index (waterSensorIndex) and other sensor details"
	INDEX { waterSensorIndex }
	::= { waterSensorTable 1 }

WaterSensorEntry ::= SEQUENCE {
	waterSensorIndex		INTEGER(1..100),
	waterSensorSerial		DisplayString,
	waterSensorName		DisplayString,
	waterSensorAvail		TruthValue,
	waterSensorDampness		INTEGER(0..100)
}

waterSensorIndex OBJECT-TYPE
	SYNTAX  INTEGER(1..100)
	MAX-ACCESS  not-accessible
	STATUS current
	DESCRIPTION "Table entry index value"
	::= { waterSensorEntry  1 }
	
waterSensorSerial OBJECT-TYPE
	SYNTAX  DisplayString
	MAX-ACCESS  read-only
	STATUS current
	DESCRIPTION "Serial Number"
	::= { waterSensorEntry  2 }
	
waterSensorName OBJECT-TYPE
	SYNTAX  DisplayString
	MAX-ACCESS  read-only
	STATUS current
	DESCRIPTION "Friendly Name"
	::= { waterSensorEntry  3 }
	
waterSensorAvail OBJECT-TYPE
	SYNTAX  TruthValue
	MAX-ACCESS  read-only
	STATUS current
	DESCRIPTION "Is device currently plugged in?"
	::= { waterSensorEntry  4 }
	
waterSensorDampness OBJECT-TYPE
	SYNTAX  INTEGER(0..100)
	MAX-ACCESS  read-only
	STATUS current
	DESCRIPTION "Dampness of the water sensor"
	::= { waterSensorEntry  5 }
	
currentMonitorEntry OBJECT-TYPE
	SYNTAX  CurrentMonitorEntry
	MAX-ACCESS  not-accessible
	STATUS current
	DESCRIPTION 
		"Entry in the current monitor table: each entry contains
an index (currentMonitorIndex) and other sensor details"
	INDEX { currentMonitorIndex }
	::= { currentMonitorTable 1 }

CurrentMonitorEntry ::= SEQUENCE {
	currentMonitorIndex		INTEGER(1..100),
	currentMonitorSerial		DisplayString,
	currentMonitorName		DisplayString,
	currentMonitorAvail		TruthValue,
	currentMonitorAmps		INTEGER(0..30)
}

currentMonitorIndex OBJECT-TYPE
	SYNTAX  INTEGER(1..100)
	MAX-ACCESS  not-accessible
	STATUS current
	DESCRIPTION "Table entry index value"
	::= { currentMonitorEntry  1 }
	
currentMonitorSerial OBJECT-TYPE
	SYNTAX  DisplayString
	MAX-ACCESS  read-only
	STATUS current
	DESCRIPTION "Serial Number"
	::= { currentMonitorEntry  2 }
	
currentMonitorName OBJECT-TYPE
	SYNTAX  DisplayString
	MAX-ACCESS  read-only
	STATUS current
	DESCRIPTION "Friendly Name"
	::= { currentMonitorEntry  3 }
	
currentMonitorAvail OBJECT-TYPE
	SYNTAX  TruthValue
	MAX-ACCESS  read-only
	STATUS current
	DESCRIPTION "Is device currently plugged in?"
	::= { currentMonitorEntry  4 }
	
currentMonitorAmps OBJECT-TYPE
	SYNTAX  INTEGER(0..30)
	MAX-ACCESS  read-only
	STATUS current
	DESCRIPTION "Current in amps"
	::= { currentMonitorEntry  5 }
	
millivoltMonitorEntry OBJECT-TYPE
	SYNTAX  MillivoltMonitorEntry
	MAX-ACCESS  not-accessible
	STATUS current
	DESCRIPTION 
		"Entry in the millivolt monitor table: each entry contains
an index (millivoltMonitorIndex) and other sensor details"
	INDEX { millivoltMonitorIndex }
	::= { millivoltMonitorTable 1 }

MillivoltMonitorEntry ::= SEQUENCE {
	millivoltMonitorIndex		INTEGER(1..100),
	millivoltMonitorSerial		DisplayString,
	millivoltMonitorName		DisplayString,
	millivoltMonitorAvail		TruthValue,
	millivoltMonitorMV		INTEGER(0..5000)
}

millivoltMonitorIndex OBJECT-TYPE
	SYNTAX  INTEGER(1..100)
	MAX-ACCESS  not-accessible
	STATUS current
	DESCRIPTION "Table entry index value"
	::= { millivoltMonitorEntry  1 }
	
millivoltMonitorSerial OBJECT-TYPE
	SYNTAX  DisplayString
	MAX-ACCESS  read-only
	STATUS current
	DESCRIPTION "Serial Number"
	::= { millivoltMonitorEntry  2 }
	
millivoltMonitorName OBJECT-TYPE
	SYNTAX  DisplayString
	MAX-ACCESS  read-only
	STATUS current
	DESCRIPTION "Friendly Name"
	::= { millivoltMonitorEntry  3 }
	
millivoltMonitorAvail OBJECT-TYPE
	SYNTAX  TruthValue
	MAX-ACCESS  read-only
	STATUS current
	DESCRIPTION "Is device currently plugged in?"
	::= { millivoltMonitorEntry  4 }
	
millivoltMonitorMV OBJECT-TYPE
	SYNTAX  INTEGER(0..5000)
	MAX-ACCESS  read-only
	STATUS current
	DESCRIPTION "millivolts"
	::= { millivoltMonitorEntry  5 }
	
power3ChEntry OBJECT-TYPE
	SYNTAX  Power3ChEntry
	MAX-ACCESS  not-accessible
	STATUS current
	DESCRIPTION 
		"Entry in the power monitor 3 channel table: each entry contains
an index (pow3ChIndex) and other power monitoring details"
	INDEX { pow3ChIndex }
	::= { power3ChTable 1 }

Power3ChEntry ::= SEQUENCE {
	pow3ChIndex		INTEGER(1..100),
	pow3ChSerial		DisplayString,
	pow3ChName		DisplayString,
	pow3ChAvail		TruthValue,
	pow3ChKWattHrsA		Unsigned32,
	pow3ChVoltsA		Unsigned32,
	pow3ChVoltMaxA		Unsigned32,
	pow3ChVoltMinA		Unsigned32,
	pow3ChVoltPkA		Unsigned32,
	pow3ChAmpsX10A		Unsigned32,
	pow3ChRealPowA		Unsigned32,
	pow3ChAppPowA		Unsigned32,
	pow3ChPwrFactA		INTEGER(0..100),
	pow3ChKWattHrsB		Unsigned32,
	pow3ChVoltsB		Unsigned32,
	pow3ChVoltMaxB		Unsigned32,
	pow3ChVoltMinB		Unsigned32,
	pow3ChVoltPkB		Unsigned32,
	pow3ChAmpsX10B		Unsigned32,
	pow3ChRealPowB		Unsigned32,
	pow3ChAppPowB		Unsigned32,
	pow3ChPwrFactB		INTEGER(0..100),
	pow3ChKWattHrsC		Unsigned32,
	pow3ChVoltsC		Unsigned32,
	pow3ChVoltMaxC		Unsigned32,
	pow3ChVoltMinC		Unsigned32,
	pow3ChVoltPkC		Unsigned32,
	pow3ChAmpsX10C		Unsigned32,
	pow3ChRealPowC		Unsigned32,
	pow3ChAppPowC		Unsigned32,
	pow3ChPwrFactC		INTEGER(0..100)
}

pow3ChIndex OBJECT-TYPE
	SYNTAX  INTEGER(1..100)
	MAX-ACCESS  not-accessible
	STATUS current
	DESCRIPTION "Table entry index value"
	::= { power3ChEntry  1 }
	
pow3ChSerial OBJECT-TYPE
	SYNTAX  DisplayString
	MAX-ACCESS  read-only
	STATUS current
	DESCRIPTION "Serial Number"
	::= { power3ChEntry  2 }
	
pow3ChName OBJECT-TYPE
	SYNTAX  DisplayString
	MAX-ACCESS  read-only
	STATUS current
	DESCRIPTION "Friendly Name"
	::= { power3ChEntry  3 }
	
pow3ChAvail OBJECT-TYPE
	SYNTAX  TruthValue
	MAX-ACCESS  read-only
	STATUS current
	DESCRIPTION "Is device currently plugged in?"
	::= { power3ChEntry  4 }
	
pow3ChKWattHrsA OBJECT-TYPE
	SYNTAX  Unsigned32
	MAX-ACCESS  read-only
	STATUS current
	DESCRIPTION "KWatt-Hours A"
	::= { power3ChEntry  5 }
	
pow3ChVoltsA OBJECT-TYPE
	SYNTAX  Unsigned32
	MAX-ACCESS  read-only
	STATUS current
	DESCRIPTION "Volts A"
	::= { power3ChEntry  6 }
	
pow3ChVoltMaxA OBJECT-TYPE
	SYNTAX  Unsigned32
	MAX-ACCESS  read-only
	STATUS current
	DESCRIPTION "Volts (Max) A"
	::= { power3ChEntry  7 }
	
pow3ChVoltMinA OBJECT-TYPE
	SYNTAX  Unsigned32
	MAX-ACCESS  read-only
	STATUS current
	DESCRIPTION "Volts (Min) A"
	::= { power3ChEntry  8 }
	
pow3ChVoltPkA OBJECT-TYPE
	SYNTAX  Unsigned32
	MAX-ACCESS  read-only
	STATUS current
	DESCRIPTION "Volts (Peak) A"
	::= { power3ChEntry  9 }
	
pow3ChAmpsX10A OBJECT-TYPE
	SYNTAX  Unsigned32
	MAX-ACCESS  read-only
	STATUS current
	DESCRIPTION "Amps x 10 A"
	::= { power3ChEntry  10 }
	
pow3ChRealPowA OBJECT-TYPE
	SYNTAX  Unsigned32
	MAX-ACCESS  read-only
	STATUS current
	DESCRIPTION "Real Power A"
	::= { power3ChEntry  11 }
	
pow3ChAppPowA OBJECT-TYPE
	SYNTAX  Unsigned32
	MAX-ACCESS  read-only
	STATUS current
	DESCRIPTION "Apparent Power A"
	::= { power3ChEntry  12 }
	
pow3ChPwrFactA OBJECT-TYPE
	SYNTAX  INTEGER(0..100)
	MAX-ACCESS  read-only
	STATUS current
	DESCRIPTION "Power Factor A"
	::= { power3ChEntry  13 }
	
pow3ChKWattHrsB OBJECT-TYPE
	SYNTAX  Unsigned32
	MAX-ACCESS  read-only
	STATUS current
	DESCRIPTION "KWatt-Hours B"
	::= { power3ChEntry  14 }
	
pow3ChVoltsB OBJECT-TYPE
	SYNTAX  Unsigned32
	MAX-ACCESS  read-only
	STATUS current
	DESCRIPTION "Volts B"
	::= { power3ChEntry  15 }
	
pow3ChVoltMaxB OBJECT-TYPE
	SYNTAX  Unsigned32
	MAX-ACCESS  read-only
	STATUS current
	DESCRIPTION "Volts (Max) B"
	::= { power3ChEntry  16 }
	
pow3ChVoltMinB OBJECT-TYPE
	SYNTAX  Unsigned32
	MAX-ACCESS  read-only
	STATUS current
	DESCRIPTION "Volts (Min) B"
	::= { power3ChEntry  17 }
	
pow3ChVoltPkB OBJECT-TYPE
	SYNTAX  Unsigned32
	MAX-ACCESS  read-only
	STATUS current
	DESCRIPTION "Volts (Peak) B"
	::= { power3ChEntry  18 }
	
pow3ChAmpsX10B OBJECT-TYPE
	SYNTAX  Unsigned32
	MAX-ACCESS  read-only
	STATUS current
	DESCRIPTION "Amps x 10 B"
	::= { power3ChEntry  19 }
	
pow3ChRealPowB OBJECT-TYPE
	SYNTAX  Unsigned32
	MAX-ACCESS  read-only
	STATUS current
	DESCRIPTION "Real Power B"
	::= { power3ChEntry  20 }
	
pow3ChAppPowB OBJECT-TYPE
	SYNTAX  Unsigned32
	MAX-ACCESS  read-only
	STATUS current
	DESCRIPTION "Apparent Power B"
	::= { power3ChEntry  21 }
	
pow3ChPwrFactB OBJECT-TYPE
	SYNTAX  INTEGER(0..100)
	MAX-ACCESS  read-only
	STATUS current
	DESCRIPTION "Power Factor B"
	::= { power3ChEntry  22 }
	
pow3ChKWattHrsC OBJECT-TYPE
	SYNTAX  Unsigned32
	MAX-ACCESS  read-only
	STATUS current
	DESCRIPTION "KWatt-Hours C"
	::= { power3ChEntry  23 }
	
pow3ChVoltsC OBJECT-TYPE
	SYNTAX  Unsigned32
	MAX-ACCESS  read-only
	STATUS current
	DESCRIPTION "Volts C"
	::= { power3ChEntry  24 }
	
pow3ChVoltMaxC OBJECT-TYPE
	SYNTAX  Unsigned32
	MAX-ACCESS  read-only
	STATUS current
	DESCRIPTION "Volts (Max) C"
	::= { power3ChEntry  25 }
	
pow3ChVoltMinC OBJECT-TYPE
	SYNTAX  Unsigned32
	MAX-ACCESS  read-only
	STATUS current
	DESCRIPTION "Volts (Min) C"
	::= { power3ChEntry  26 }
	
pow3ChVoltPkC OBJECT-TYPE
	SYNTAX  Unsigned32
	MAX-ACCESS  read-only
	STATUS current
	DESCRIPTION "Volts (Peak) C"
	::= { power3ChEntry  27 }
	
pow3ChAmpsX10C OBJECT-TYPE
	SYNTAX  Unsigned32
	MAX-ACCESS  read-only
	STATUS current
	DESCRIPTION "Amps x 10 C"
	::= { power3ChEntry  28 }
	
pow3ChRealPowC OBJECT-TYPE
	SYNTAX  Unsigned32
	MAX-ACCESS  read-only
	STATUS current
	DESCRIPTION "Real Power C"
	::= { power3ChEntry  29 }
	
pow3ChAppPowC OBJECT-TYPE
	SYNTAX  Unsigned32
	MAX-ACCESS  read-only
	STATUS current
	DESCRIPTION "Apparent Power C"
	::= { power3ChEntry  30 }
	
pow3ChPwrFactC OBJECT-TYPE
	SYNTAX  INTEGER(0..100)
	MAX-ACCESS  read-only
	STATUS current
	DESCRIPTION "Power Factor C"
	::= { power3ChEntry  31 }
	
outletEntry OBJECT-TYPE
	SYNTAX  OutletEntry
	MAX-ACCESS  not-accessible
	STATUS current
	DESCRIPTION 
		"Entry in the outlet table: each entry contains
an index (outletIndex) and other sensor details"
	INDEX { outletIndex }
	::= { outletTable 1 }

OutletEntry ::= SEQUENCE {
	outletIndex		INTEGER(1..100),
	outletSerial		DisplayString,
	outletName		DisplayString,
	outletAvail		TruthValue,
	outlet1Status		INTEGER(0..100),
	outlet2Status		INTEGER(0..100)
}

outletIndex OBJECT-TYPE
	SYNTAX  INTEGER(1..100)
	MAX-ACCESS  not-accessible
	STATUS current
	DESCRIPTION "Table entry index value"
	::= { outletEntry  1 }
	
outletSerial OBJECT-TYPE
	SYNTAX  DisplayString
	MAX-ACCESS  read-only
	STATUS current
	DESCRIPTION "Serial Number"
	::= { outletEntry  2 }
	
outletName OBJECT-TYPE
	SYNTAX  DisplayString
	MAX-ACCESS  read-only
	STATUS current
	DESCRIPTION "Friendly Name"
	::= { outletEntry  3 }
	
outletAvail OBJECT-TYPE
	SYNTAX  TruthValue
	MAX-ACCESS  read-only
	STATUS current
	DESCRIPTION "Is device currently plugged in?"
	::= { outletEntry  4 }
	
outlet1Status OBJECT-TYPE
	SYNTAX  INTEGER(0..100)
	MAX-ACCESS  read-only
	STATUS current
	DESCRIPTION "Outlet 1 status"
	::= { outletEntry  5 }
	
outlet2Status OBJECT-TYPE
	SYNTAX  INTEGER(0..100)
	MAX-ACCESS  read-only
	STATUS current
	DESCRIPTION "Outlet 2 status"
	::= { outletEntry  6 }
	
vsfcEntry OBJECT-TYPE
	SYNTAX  VsfcEntry
	MAX-ACCESS  not-accessible
	STATUS current
	DESCRIPTION 
		"Entry in the vsfc table: each entry contains
an index (vsfcIndex) and other details"
	INDEX { vsfcIndex }
	::= { vsfcTable 1 }

VsfcEntry ::= SEQUENCE {
	vsfcIndex		INTEGER(1..1),
	vsfcSerial		DisplayString,
	vsfcName		DisplayString,
	vsfcAvail		TruthValue,
	vsfcSetPointC		INTEGER(18..38),
	vsfcIntTempC		INTEGER(-20..50),
	vsfcExt1TempC		INTEGER(-20..50),
	vsfcExt2TempC		INTEGER(-20..50),
	vsfcExt3TempC		INTEGER(-20..50),
	vsfcExt4TempC		INTEGER(-20..50),
	vsfcFanSpeed		INTEGER(0..100)
}

vsfcIndex OBJECT-TYPE
	SYNTAX  INTEGER(1..1)
	MAX-ACCESS  not-accessible
	STATUS current
	DESCRIPTION "Table entry index value"
	::= { vsfcEntry  1 }
	
vsfcSerial OBJECT-TYPE
	SYNTAX  DisplayString
	MAX-ACCESS  read-only
	STATUS current
	DESCRIPTION "Serial Number"
	::= { vsfcEntry  2 }
	
vsfcName OBJECT-TYPE
	SYNTAX  DisplayString
	MAX-ACCESS  read-only
	STATUS current
	DESCRIPTION "Friendly Name"
	::= { vsfcEntry  3 }
	
vsfcAvail OBJECT-TYPE
	SYNTAX  TruthValue
	MAX-ACCESS  read-only
	STATUS current
	DESCRIPTION "Is device currently plugged in?"
	::= { vsfcEntry  4 }
	
vsfcSetPointC OBJECT-TYPE
	SYNTAX  INTEGER(18..38)
	MAX-ACCESS  read-only
	STATUS current
	DESCRIPTION "Current temperature set point in C"
	::= { vsfcEntry  5 }
	
vsfcIntTempC OBJECT-TYPE
	SYNTAX  INTEGER(-20..50)
	MAX-ACCESS  read-only
	STATUS current
	DESCRIPTION "Current internal temperature reading in C"
	::= { vsfcEntry  6 }
	
vsfcExt1TempC OBJECT-TYPE
	SYNTAX  INTEGER(-20..50)
	MAX-ACCESS  read-only
	STATUS current
	DESCRIPTION "Current reading for external temp 1 in C"
	::= { vsfcEntry  7 }
	
vsfcExt2TempC OBJECT-TYPE
	SYNTAX  INTEGER(-20..50)
	MAX-ACCESS  read-only
	STATUS current
	DESCRIPTION "Current reading for external temp 2 in C"
	::= { vsfcEntry  8 }
	
vsfcExt3TempC OBJECT-TYPE
	SYNTAX  INTEGER(-20..50)
	MAX-ACCESS  read-only
	STATUS current
	DESCRIPTION "Current reading for external temp 3 in C"
	::= { vsfcEntry  9 }
	
vsfcExt4TempC OBJECT-TYPE
	SYNTAX  INTEGER(-20..50)
	MAX-ACCESS  read-only
	STATUS current
	DESCRIPTION "Current reading for external temp 4 in C"
	::= { vsfcEntry  10 }
	
vsfcFanSpeed OBJECT-TYPE
	SYNTAX  INTEGER(0..100)
	MAX-ACCESS  read-only
	STATUS current
	DESCRIPTION "Current reading for Fan Speed"
	::= { vsfcEntry  11 }
	
ctrl3ChEntry OBJECT-TYPE
	SYNTAX  Ctrl3ChEntry
	MAX-ACCESS  not-accessible
	STATUS current
	DESCRIPTION 
		"Entry in the 3 phase outlet control table: each entry contains
an index (ctrl3ChIndex) and other outlet control monitoring details"
	INDEX { ctrl3ChIndex }
	::= { ctrl3ChTable 1 }

Ctrl3ChEntry ::= SEQUENCE {
	ctrl3ChIndex		INTEGER(1..1),
	ctrl3ChSerial		DisplayString,
	ctrl3ChName		DisplayString,
	ctrl3ChAvail		TruthValue,
	ctrl3ChVoltsA		Unsigned32,
	ctrl3ChVoltPkA		Unsigned32,
	ctrl3ChAmpsA		Unsigned32,
	ctrl3ChAmpPkA		Unsigned32,
	ctrl3ChRealPowA		Unsigned32,
	ctrl3ChAppPowA		Unsigned32,
	ctrl3ChPwrFactA		INTEGER(0..100),
	ctrl3ChVoltsB		Unsigned32,
	ctrl3ChVoltPkB		Unsigned32,
	ctrl3ChAmpsB		Unsigned32,
	ctrl3ChAmpPkB		Unsigned32,
	ctrl3ChRealPowB		Unsigned32,
	ctrl3ChAppPowB		Unsigned32,
	ctrl3ChPwrFactB		INTEGER(0..100),
	ctrl3ChVoltsC		Unsigned32,
	ctrl3ChVoltPkC		Unsigned32,
	ctrl3ChAmpsC		Unsigned32,
	ctrl3ChAmpPkC		Unsigned32,
	ctrl3ChRealPowC		Unsigned32,
	ctrl3ChAppPowC		Unsigned32,
	ctrl3ChPwrFactC		INTEGER(0..100)
}

ctrl3ChIndex OBJECT-TYPE
	SYNTAX  INTEGER(1..1)
	MAX-ACCESS  not-accessible
	STATUS current
	DESCRIPTION "Table entry index value"
	::= { ctrl3ChEntry  1 }
	
ctrl3ChSerial OBJECT-TYPE
	SYNTAX  DisplayString
	MAX-ACCESS  read-only
	STATUS current
	DESCRIPTION "Serial Number"
	::= { ctrl3ChEntry  2 }
	
ctrl3ChName OBJECT-TYPE
	SYNTAX  DisplayString
	MAX-ACCESS  read-only
	STATUS current
	DESCRIPTION "Friendly Name"
	::= { ctrl3ChEntry  3 }
	
ctrl3ChAvail OBJECT-TYPE
	SYNTAX  TruthValue
	MAX-ACCESS  read-only
	STATUS current
	DESCRIPTION "Is device currently plugged in?"
	::= { ctrl3ChEntry  4 }
	
ctrl3ChVoltsA OBJECT-TYPE
	SYNTAX  Unsigned32
	MAX-ACCESS  read-only
	STATUS current
	DESCRIPTION "Volts A"
	::= { ctrl3ChEntry  5 }
	
ctrl3ChVoltPkA OBJECT-TYPE
	SYNTAX  Unsigned32
	MAX-ACCESS  read-only
	STATUS current
	DESCRIPTION "Volts (Peak) A"
	::= { ctrl3ChEntry  6 }
	
ctrl3ChAmpsA OBJECT-TYPE
	SYNTAX  Unsigned32
	MAX-ACCESS  read-only
	STATUS current
	DESCRIPTION "Amps A"
	::= { ctrl3ChEntry  7 }
	
ctrl3ChAmpPkA OBJECT-TYPE
	SYNTAX  Unsigned32
	MAX-ACCESS  read-only
	STATUS current
	DESCRIPTION "Amps Peak A"
	::= { ctrl3ChEntry  8 }
	
ctrl3ChRealPowA OBJECT-TYPE
	SYNTAX  Unsigned32
	MAX-ACCESS  read-only
	STATUS current
	DESCRIPTION "Real Power A"
	::= { ctrl3ChEntry  9 }
	
ctrl3ChAppPowA OBJECT-TYPE
	SYNTAX  Unsigned32
	MAX-ACCESS  read-only
	STATUS current
	DESCRIPTION "Apparent Power A"
	::= { ctrl3ChEntry  10 }
	
ctrl3ChPwrFactA OBJECT-TYPE
	SYNTAX  INTEGER(0..100)
	MAX-ACCESS  read-only
	STATUS current
	DESCRIPTION "Power Factor A"
	::= { ctrl3ChEntry  11 }
	
ctrl3ChVoltsB OBJECT-TYPE
	SYNTAX  Unsigned32
	MAX-ACCESS  read-only
	STATUS current
	DESCRIPTION "Volts B"
	::= { ctrl3ChEntry  12 }
	
ctrl3ChVoltPkB OBJECT-TYPE
	SYNTAX  Unsigned32
	MAX-ACCESS  read-only
	STATUS current
	DESCRIPTION "Volts (Peak) B"
	::= { ctrl3ChEntry  13 }
	
ctrl3ChAmpsB OBJECT-TYPE
	SYNTAX  Unsigned32
	MAX-ACCESS  read-only
	STATUS current
	DESCRIPTION "Amps B"
	::= { ctrl3ChEntry  14 }
	
ctrl3ChAmpPkB OBJECT-TYPE
	SYNTAX  Unsigned32
	MAX-ACCESS  read-only
	STATUS current
	DESCRIPTION "Amps Peak B"
	::= { ctrl3ChEntry  15 }
	
ctrl3ChRealPowB OBJECT-TYPE
	SYNTAX  Unsigned32
	MAX-ACCESS  read-only
	STATUS current
	DESCRIPTION "Real Power B"
	::= { ctrl3ChEntry  16 }
	
ctrl3ChAppPowB OBJECT-TYPE
	SYNTAX  Unsigned32
	MAX-ACCESS  read-only
	STATUS current
	DESCRIPTION "Apparent Power B"
	::= { ctrl3ChEntry  17 }
	
ctrl3ChPwrFactB OBJECT-TYPE
	SYNTAX  INTEGER(0..100)
	MAX-ACCESS  read-only
	STATUS current
	DESCRIPTION "Power Factor B"
	::= { ctrl3ChEntry  18 }
	
ctrl3ChVoltsC OBJECT-TYPE
	SYNTAX  Unsigned32
	MAX-ACCESS  read-only
	STATUS current
	DESCRIPTION "Volts C"
	::= { ctrl3ChEntry  19 }
	
ctrl3ChVoltPkC OBJECT-TYPE
	SYNTAX  Unsigned32
	MAX-ACCESS  read-only
	STATUS current
	DESCRIPTION "Volts (Peak) C"
	::= { ctrl3ChEntry  20 }
	
ctrl3ChAmpsC OBJECT-TYPE
	SYNTAX  Unsigned32
	MAX-ACCESS  read-only
	STATUS current
	DESCRIPTION "Amps C"
	::= { ctrl3ChEntry  21 }
	
ctrl3ChAmpPkC OBJECT-TYPE
	SYNTAX  Unsigned32
	MAX-ACCESS  read-only
	STATUS current
	DESCRIPTION "Amps Peak C"
	::= { ctrl3ChEntry  22 }
	
ctrl3ChRealPowC OBJECT-TYPE
	SYNTAX  Unsigned32
	MAX-ACCESS  read-only
	STATUS current
	DESCRIPTION "Real Power C"
	::= { ctrl3ChEntry  23 }
	
ctrl3ChAppPowC OBJECT-TYPE
	SYNTAX  Unsigned32
	MAX-ACCESS  read-only
	STATUS current
	DESCRIPTION "Apparent Power C"
	::= { ctrl3ChEntry  24 }
	
ctrl3ChPwrFactC OBJECT-TYPE
	SYNTAX  INTEGER(0..100)
	MAX-ACCESS  read-only
	STATUS current
	DESCRIPTION "Power Factor C"
	::= { ctrl3ChEntry  25 }
	
ctrlGrpAmpsEntry OBJECT-TYPE
	SYNTAX  CtrlGrpAmpsEntry
	MAX-ACCESS  not-accessible
	STATUS current
	DESCRIPTION 
		"Entry in the Control Group Amps table: each entry contains
an index (ctrlGrpAmpsIndex) and other sensor details"
	INDEX { ctrlGrpAmpsIndex }
	::= { ctrlGrpAmpsTable 1 }

CtrlGrpAmpsEntry ::= SEQUENCE {
	ctrlGrpAmpsIndex		INTEGER(1..1),
	ctrlGrpAmpsSerial		DisplayString,
	ctrlGrpAmpsName		DisplayString,
	ctrlGrpAmpsAvail		TruthValue,
	ctrlGrpAmpsA		Unsigned32,
	ctrlGrpAmpsB		Unsigned32,
	ctrlGrpAmpsC		Unsigned32,
	ctrlGrpAmpsD		Unsigned32,
	ctrlGrpAmpsE		Unsigned32,
	ctrlGrpAmpsF		Unsigned32
}

ctrlGrpAmpsIndex OBJECT-TYPE
	SYNTAX  INTEGER(1..1)
	MAX-ACCESS  not-accessible
	STATUS current
	DESCRIPTION "Table entry index value"
	::= { ctrlGrpAmpsEntry  1 }
	
ctrlGrpAmpsSerial OBJECT-TYPE
	SYNTAX  DisplayString
	MAX-ACCESS  read-only
	STATUS current
	DESCRIPTION "Serial Number"
	::= { ctrlGrpAmpsEntry  2 }
	
ctrlGrpAmpsName OBJECT-TYPE
	SYNTAX  DisplayString
	MAX-ACCESS  read-only
	STATUS current
	DESCRIPTION "Friendly Name"
	::= { ctrlGrpAmpsEntry  3 }
	
ctrlGrpAmpsAvail OBJECT-TYPE
	SYNTAX  TruthValue
	MAX-ACCESS  read-only
	STATUS current
	DESCRIPTION "Is device currently plugged in?"
	::= { ctrlGrpAmpsEntry  4 }
	
ctrlGrpAmpsA OBJECT-TYPE
	SYNTAX  Unsigned32
	MAX-ACCESS  read-only
	STATUS current
	DESCRIPTION "Amps Group A"
	::= { ctrlGrpAmpsEntry  5 }
	
ctrlGrpAmpsB OBJECT-TYPE
	SYNTAX  Unsigned32
	MAX-ACCESS  read-only
	STATUS current
	DESCRIPTION "Amps Group B"
	::= { ctrlGrpAmpsEntry  6 }
	
ctrlGrpAmpsC OBJECT-TYPE
	SYNTAX  Unsigned32
	MAX-ACCESS  read-only
	STATUS current
	DESCRIPTION "Amps Group C"
	::= { ctrlGrpAmpsEntry  7 }
	
ctrlGrpAmpsD OBJECT-TYPE
	SYNTAX  Unsigned32
	MAX-ACCESS  read-only
	STATUS current
	DESCRIPTION "Amps Group D"
	::= { ctrlGrpAmpsEntry  8 }
	
ctrlGrpAmpsE OBJECT-TYPE
	SYNTAX  Unsigned32
	MAX-ACCESS  read-only
	STATUS current
	DESCRIPTION "Amps Group E"
	::= { ctrlGrpAmpsEntry  9 }
	
ctrlGrpAmpsF OBJECT-TYPE
	SYNTAX  Unsigned32
	MAX-ACCESS  read-only
	STATUS current
	DESCRIPTION "Amps Group F"
	::= { ctrlGrpAmpsEntry  10 }
	
ctrlOutletEntry OBJECT-TYPE
	SYNTAX  CtrlOutletEntry
	MAX-ACCESS  not-accessible
	STATUS current
	DESCRIPTION 
		"Entry in the control outlet table: each entry contains
an index (ctrlOutletIndex) and other sensor details"
	INDEX { ctrlOutletIndex }
	::= { ctrlOutletTable 1 }

CtrlOutletEntry ::= SEQUENCE {
	ctrlOutletIndex		INTEGER(1..100),
	ctrlOutletName		DisplayString,
	ctrlOutletStatus		TruthValue,
	ctrlOutletFeedback		TruthValue,
	ctrlOutletPending		TruthValue,
	ctrlOutletAmps		Unsigned32,
	ctrlOutletGroup		DisplayString,
	ctrlOutletUpDelay		Unsigned32,
	ctrlOutletDwnDelay		Unsigned32,
	ctrlOutletRbtDelay		Unsigned32,
	ctrlOutletURL		DisplayString
}

ctrlOutletIndex OBJECT-TYPE
	SYNTAX  INTEGER(1..100)
	MAX-ACCESS  not-accessible
	STATUS current
	DESCRIPTION "Outlet Number"
	::= { ctrlOutletEntry  1 }
	
ctrlOutletName OBJECT-TYPE
	SYNTAX  DisplayString
	MAX-ACCESS  read-only
	STATUS current
	DESCRIPTION "Outlet Friendly Name"
	::= { ctrlOutletEntry  2 }
	
ctrlOutletStatus OBJECT-TYPE
	SYNTAX  TruthValue
	MAX-ACCESS  read-only
	STATUS current
	DESCRIPTION "Current Outlet Status"
	::= { ctrlOutletEntry  3 }
	
ctrlOutletFeedback OBJECT-TYPE
	SYNTAX  TruthValue
	MAX-ACCESS  read-only
	STATUS current
	DESCRIPTION "Outlet Feedback Value, should be equal to status"
	::= { ctrlOutletEntry  4 }
	
ctrlOutletPending OBJECT-TYPE
	SYNTAX  TruthValue
	MAX-ACCESS  read-only
	STATUS current
	DESCRIPTION "Outlet Status to be set to"
	::= { ctrlOutletEntry  5 }
	
ctrlOutletAmps OBJECT-TYPE
	SYNTAX  Unsigned32
	MAX-ACCESS  read-only
	STATUS current
	DESCRIPTION "Outlet Amps readings"
	::= { ctrlOutletEntry  6 }
	
ctrlOutletGroup OBJECT-TYPE
	SYNTAX  DisplayString
	MAX-ACCESS  read-only
	STATUS current
	DESCRIPTION "Outlet Group"
	::= { ctrlOutletEntry  7 }
	
ctrlOutletUpDelay OBJECT-TYPE
	SYNTAX  Unsigned32
	MAX-ACCESS  read-only
	STATUS current
	DESCRIPTION "Outlet Power Up Delay"
	::= { ctrlOutletEntry  8 }
	
ctrlOutletDwnDelay OBJECT-TYPE
	SYNTAX  Unsigned32
	MAX-ACCESS  read-only
	STATUS current
	DESCRIPTION "Outlet Power Down Delay"
	::= { ctrlOutletEntry  9 }
	
ctrlOutletRbtDelay OBJECT-TYPE
	SYNTAX  Unsigned32
	MAX-ACCESS  read-only
	STATUS current
	DESCRIPTION "Outlet Reboot Delay"
	::= { ctrlOutletEntry  10 }
	
ctrlOutletURL OBJECT-TYPE
	SYNTAX  DisplayString
	MAX-ACCESS  read-only
	STATUS current
	DESCRIPTION "Outlet URL"
	::= { ctrlOutletEntry  11 }
	
dewPointSensorEntry OBJECT-TYPE
	SYNTAX  DewPointSensorEntry
	MAX-ACCESS  not-accessible
	STATUS current
	DESCRIPTION 
		"Entry in the dew point sensor table: each entry contains
an index (dewPointSensorIndex) and other sensor details"
	INDEX { dewPointSensorIndex }
	::= { dewPointSensorTable 1 }

DewPointSensorEntry ::= SEQUENCE {
	dewPointSensorIndex		INTEGER(1..100),
	dewPointSensorSerial		DisplayString,
	dewPointSensorName		DisplayString,
	dewPointSensorAvail		TruthValue,
	dewPointSensorDewPoint		INTEGER(-50..100),
	dewPointSensorTempC		INTEGER(-50..100),
	dewPointSensorHumidity		INTEGER(0..100)
}

dewPointSensorIndex OBJECT-TYPE
	SYNTAX  INTEGER(1..100)
	MAX-ACCESS  not-accessible
	STATUS current
	DESCRIPTION "Table entry index value"
	::= { dewPointSensorEntry  1 }
	
dewPointSensorSerial OBJECT-TYPE
	SYNTAX  DisplayString
	MAX-ACCESS  read-only
	STATUS current
	DESCRIPTION "Serial Number"
	::= { dewPointSensorEntry  2 }
	
dewPointSensorName OBJECT-TYPE
	SYNTAX  DisplayString
	MAX-ACCESS  read-only
	STATUS current
	DESCRIPTION "Friendly Name"
	::= { dewPointSensorEntry  3 }
	
dewPointSensorAvail OBJECT-TYPE
	SYNTAX  TruthValue
	MAX-ACCESS  read-only
	STATUS current
	DESCRIPTION "Is device currently plugged in?"
	::= { dewPointSensorEntry  4 }
	
dewPointSensorDewPoint OBJECT-TYPE
	SYNTAX  INTEGER(-50..100)
	MAX-ACCESS  read-only
	STATUS current
	DESCRIPTION "Dew point reading in C"
	::= { dewPointSensorEntry  5 }
	
dewPointSensorTempC OBJECT-TYPE
	SYNTAX  INTEGER(-50..100)
	MAX-ACCESS  read-only
	STATUS current
	DESCRIPTION "Temperature reading in C"
	::= { dewPointSensorEntry  6 }
	
dewPointSensorHumidity OBJECT-TYPE
	SYNTAX  INTEGER(0..100)
	MAX-ACCESS  read-only
	STATUS current
	DESCRIPTION "Humidity reading"
	::= { dewPointSensorEntry  7 }
	
gstTestTRAP TRAP-TYPE
	ENTERPRISE geistmfg
	DESCRIPTION "Test SNMP Trap"
	::= 10101
	
gstClimateTempCTRAP TRAP-TYPE
ENTERPRISE geistmfg
VARIABLES { climateTempC, climateName, productFriendlyName, alarmTripType }
DESCRIPTION "Climate Temperature Sensor Trap"
::= 10205

gstClimateHumidityTRAP TRAP-TYPE
ENTERPRISE geistmfg
VARIABLES { climateHumidity, climateName, productFriendlyName, alarmTripType }
DESCRIPTION "Climate Humidity Sensor Trap"
::= 10206

gstClimateAirflowTRAP TRAP-TYPE
ENTERPRISE geistmfg
VARIABLES { climateAirflow, climateName, productFriendlyName, alarmTripType }
DESCRIPTION "Climate Air Flow Sensor Trap"
::= 10207

gstClimateLightTRAP TRAP-TYPE
ENTERPRISE geistmfg
VARIABLES { climateLight, climateName, productFriendlyName, alarmTripType }
DESCRIPTION "Climate Light Sensor Trap"
::= 10208

gstClimateSoundTRAP TRAP-TYPE
ENTERPRISE geistmfg
VARIABLES { climateSound, climateName, productFriendlyName, alarmTripType }
DESCRIPTION "Climate Sound Sensor Trap"
::= 10209

gstClimateIO1TRAP TRAP-TYPE
ENTERPRISE geistmfg
VARIABLES { climateIO1, climateName, productFriendlyName, alarmTripType }
DESCRIPTION "Climate IO1 Sensor Trap"
::= 10210

gstClimateIO2TRAP TRAP-TYPE
ENTERPRISE geistmfg
VARIABLES { climateIO2, climateName, productFriendlyName, alarmTripType }
DESCRIPTION "Climate IO2 Sensor Trap"
::= 10211

gstClimateIO3TRAP TRAP-TYPE
ENTERPRISE geistmfg
VARIABLES { climateIO3, climateName, productFriendlyName, alarmTripType }
DESCRIPTION "Climate IO3 Sensor Trap"
::= 10212

gstClimateVoltsTRAP TRAP-TYPE
ENTERPRISE geistmfg
VARIABLES { climateVolts, climateName, productFriendlyName, alarmTripType }
DESCRIPTION "Climate Volts Trap"
::= 10213

gstClimateVoltPeakTRAP TRAP-TYPE
ENTERPRISE geistmfg
VARIABLES { climateVoltPeak, climateName, productFriendlyName, alarmTripType }
DESCRIPTION "Climate Volts Peak Trap"
::= 10214

gstClimateAmpsATRAP TRAP-TYPE
ENTERPRISE geistmfg
VARIABLES { climateAmpsA, climateName, productFriendlyName, alarmTripType }
DESCRIPTION "Climate Amps A Trap"
::= 10215

gstClimateAmpPeakATRAP TRAP-TYPE
ENTERPRISE geistmfg
VARIABLES { climateAmpPeakA, climateName, productFriendlyName, alarmTripType }
DESCRIPTION "Climate Amp Peak A Trap"
::= 10216

gstClimateRealPowerATRAP TRAP-TYPE
ENTERPRISE geistmfg
VARIABLES { climateRealPowerA, climateName, productFriendlyName, alarmTripType }
DESCRIPTION "Climate Real Power A Trap"
::= 10217

gstClimateApparentPowerATRAP TRAP-TYPE
ENTERPRISE geistmfg
VARIABLES { climateApparentPowerA, climateName, productFriendlyName, alarmTripType }
DESCRIPTION "Climate Apparent Power A Trap"
::= 10218

gstClimatePowerFactorATRAP TRAP-TYPE
ENTERPRISE geistmfg
VARIABLES { climatePowerFactorA, climateName, productFriendlyName, alarmTripType }
DESCRIPTION "Climate Power Factor A Trap"
::= 10219

gstClimateAmpsBTRAP TRAP-TYPE
ENTERPRISE geistmfg
VARIABLES { climateAmpsB, climateName, productFriendlyName, alarmTripType }
DESCRIPTION "Climate Amps B Trap"
::= 10220

gstClimateAmpPeakBTRAP TRAP-TYPE
ENTERPRISE geistmfg
VARIABLES { climateAmpPeakB, climateName, productFriendlyName, alarmTripType }
DESCRIPTION "Climate Amp Peak B Trap"
::= 10221

gstClimateRealPowerBTRAP TRAP-TYPE
ENTERPRISE geistmfg
VARIABLES { climateRealPowerB, climateName, productFriendlyName, alarmTripType }
DESCRIPTION "Climate Real Power B Trap"
::= 10222

gstClimateApparentPowerBTRAP TRAP-TYPE
ENTERPRISE geistmfg
VARIABLES { climateApparentPowerB, climateName, productFriendlyName, alarmTripType }
DESCRIPTION "Climate Apparent Power B Trap"
::= 10223

gstClimatePowerFactorBTRAP TRAP-TYPE
ENTERPRISE geistmfg
VARIABLES { climatePowerFactorB, climateName, productFriendlyName, alarmTripType }
DESCRIPTION "Climate Power Factor B Trap"
::= 10224

gstClimateAmpsCTRAP TRAP-TYPE
ENTERPRISE geistmfg
VARIABLES { climateAmpsC, climateName, productFriendlyName, alarmTripType }
DESCRIPTION "Climate Amps C Trap"
::= 10225

gstClimateAmpPeakCTRAP TRAP-TYPE
ENTERPRISE geistmfg
VARIABLES { climateAmpPeakC, climateName, productFriendlyName, alarmTripType }
DESCRIPTION "Climate Amp Peak C Trap"
::= 10226

gstClimateRealPowerCTRAP TRAP-TYPE
ENTERPRISE geistmfg
VARIABLES { climateRealPowerC, climateName, productFriendlyName, alarmTripType }
DESCRIPTION "Climate Real Power C Trap"
::= 10227

gstClimateApparentPowerCTRAP TRAP-TYPE
ENTERPRISE geistmfg
VARIABLES { climateApparentPowerC, climateName, productFriendlyName, alarmTripType }
DESCRIPTION "Climate Apparent Power C Trap"
::= 10228

gstClimatePowerFactorCTRAP TRAP-TYPE
ENTERPRISE geistmfg
VARIABLES { climatePowerFactorC, climateName, productFriendlyName, alarmTripType }
DESCRIPTION "Climate Power Factor C Trap"
::= 10229

gstPowMonKWattHrsTRAP TRAP-TYPE
ENTERPRISE geistmfg
VARIABLES { powMonKWattHrs, powMonName, productFriendlyName, alarmTripType }
DESCRIPTION "Kilo Watt Hours Trap"
::= 10305

gstPowMonVoltsTRAP TRAP-TYPE
ENTERPRISE geistmfg
VARIABLES { powMonVolts, powMonName, productFriendlyName, alarmTripType }
DESCRIPTION "Volts Trap"
::= 10306

gstPowMonVoltMaxTRAP TRAP-TYPE
ENTERPRISE geistmfg
VARIABLES { powMonVoltMax, powMonName, productFriendlyName, alarmTripType }
DESCRIPTION "Volts Max Trap"
::= 10307

gstPowMonVoltMinTRAP TRAP-TYPE
ENTERPRISE geistmfg
VARIABLES { powMonVoltMin, powMonName, productFriendlyName, alarmTripType }
DESCRIPTION "Volts Min Trap"
::= 10308

gstPowMonVoltPkTRAP TRAP-TYPE
ENTERPRISE geistmfg
VARIABLES { powMonVoltPk, powMonName, productFriendlyName, alarmTripType }
DESCRIPTION "Volt Peak Trap"
::= 10309

gstPowMonAmpsX10TRAP TRAP-TYPE
ENTERPRISE geistmfg
VARIABLES { powMonAmpsX10, powMonName, productFriendlyName, alarmTripType }
DESCRIPTION "Amps x 10 Trap"
::= 10310

gstPowMonRealPowTRAP TRAP-TYPE
ENTERPRISE geistmfg
VARIABLES { powMonRealPow, powMonName, productFriendlyName, alarmTripType }
DESCRIPTION "Real Power Trap"
::= 10311

gstPowMonAppPowTRAP TRAP-TYPE
ENTERPRISE geistmfg
VARIABLES { powMonAppPow, powMonName, productFriendlyName, alarmTripType }
DESCRIPTION "Apparent Power Trap"
::= 10312

gstPowMonPwrFactTRAP TRAP-TYPE
ENTERPRISE geistmfg
VARIABLES { powMonPwrFact, powMonName, productFriendlyName, alarmTripType }
DESCRIPTION "Power Factor Trap"
::= 10313

gstPowMonOutlet1TRAP TRAP-TYPE
ENTERPRISE geistmfg
VARIABLES { powMonOutlet1, powMonName, productFriendlyName, alarmTripType }
DESCRIPTION "Outlet 1 Trap"
::= 10314

gstPowMonOutlet2TRAP TRAP-TYPE
ENTERPRISE geistmfg
VARIABLES { powMonOutlet2, powMonName, productFriendlyName, alarmTripType }
DESCRIPTION "Outlet 2 Trap"
::= 10315

gstTempSensorTempCTRAP TRAP-TYPE
ENTERPRISE geistmfg
VARIABLES { tempSensorTempC, tempSensorName, productFriendlyName, alarmTripType }
DESCRIPTION "Remote Temp Sensor - Temperature Trap"
::= 10405

gstAirFlowSensorFlowTRAP TRAP-TYPE
ENTERPRISE geistmfg
VARIABLES { airFlowSensorFlow, airFlowSensorName, productFriendlyName, alarmTripType }
DESCRIPTION "Remote Air Flow Sensor - Air Flow Trap"
::= 10505

gstAirFlowSensorTempCTRAP TRAP-TYPE
ENTERPRISE geistmfg
VARIABLES { airFlowSensorTempC, airFlowSensorName, productFriendlyName, alarmTripType }
DESCRIPTION "Remote Air Flow Sensor - Temperature Trap"
::= 10506

gstAirFlowSensorHumidityTRAP TRAP-TYPE
ENTERPRISE geistmfg
VARIABLES { airFlowSensorHumidity, airFlowSensorName, productFriendlyName, alarmTripType }
DESCRIPTION "Remote Air Flow Sensor - Humidity"
::= 10507

gstPowerVoltsTRAP TRAP-TYPE
ENTERPRISE geistmfg
VARIABLES { powerVolts, powerName, productFriendlyName, alarmTripType }
DESCRIPTION "Power-Only Volts Trap"
::= 10605

gstPowerAmpsTRAP TRAP-TYPE
ENTERPRISE geistmfg
VARIABLES { powerAmps, powerName, productFriendlyName, alarmTripType }
DESCRIPTION "Power-Only Amps Trap"
::= 10606

gstPowerRealPowTRAP TRAP-TYPE
ENTERPRISE geistmfg
VARIABLES { powerRealPow, powerName, productFriendlyName, alarmTripType }
DESCRIPTION "Power-Only Watts Trap"
::= 10607

gstPowerAppPowTRAP TRAP-TYPE
ENTERPRISE geistmfg
VARIABLES { powerAppPow, powerName, productFriendlyName, alarmTripType }
DESCRIPTION "Power-Only Volt Amps Trap"
::= 10608

gstPowerPwrFactorTRAP TRAP-TYPE
ENTERPRISE geistmfg
VARIABLES { powerPwrFactor, powerName, productFriendlyName, alarmTripType }
DESCRIPTION "Power-Only Power Factor Trap"
::= 10609

gstDoorSensorStatusTRAP TRAP-TYPE
ENTERPRISE geistmfg
VARIABLES { doorSensorStatus, doorSensorName, productFriendlyName, alarmTripType }
DESCRIPTION "Door sensor Trap"
::= 10705

gstWaterSensorDampnessTRAP TRAP-TYPE
ENTERPRISE geistmfg
VARIABLES { waterSensorDampness, waterSensorName, productFriendlyName, alarmTripType }
DESCRIPTION "Water sensor Trap"
::= 10805

gstCurrentMonitorAmpsTRAP TRAP-TYPE
ENTERPRISE geistmfg
VARIABLES { currentMonitorAmps, currentMonitorName, productFriendlyName, alarmTripType }
DESCRIPTION "Current Monitor Amps Trap"
::= 10905

gstMillivoltMonitorMVTRAP TRAP-TYPE
ENTERPRISE geistmfg
VARIABLES { millivoltMonitorMV, millivoltMonitorName, productFriendlyName, alarmTripType }
DESCRIPTION "Millivolt Monitor Trap"
::= 11005

gstPow3ChKWattHrsATRAP TRAP-TYPE
ENTERPRISE geistmfg
VARIABLES { pow3ChKWattHrsA, pow3ChName, productFriendlyName, alarmTripType }
DESCRIPTION "Kilo Watt Hours A Trap"
::= 11105

gstPow3ChVoltsATRAP TRAP-TYPE
ENTERPRISE geistmfg
VARIABLES { pow3ChVoltsA, pow3ChName, productFriendlyName, alarmTripType }
DESCRIPTION "Volts A Trap"
::= 11106

gstPow3ChVoltMaxATRAP TRAP-TYPE
ENTERPRISE geistmfg
VARIABLES { pow3ChVoltMaxA, pow3ChName, productFriendlyName, alarmTripType }
DESCRIPTION "Volts Max A Trap"
::= 11107

gstPow3ChVoltMinATRAP TRAP-TYPE
ENTERPRISE geistmfg
VARIABLES { pow3ChVoltMinA, pow3ChName, productFriendlyName, alarmTripType }
DESCRIPTION "Volts Min A Trap"
::= 11108

gstPow3ChVoltPkATRAP TRAP-TYPE
ENTERPRISE geistmfg
VARIABLES { pow3ChVoltPkA, pow3ChName, productFriendlyName, alarmTripType }
DESCRIPTION "Volt Peak A Trap"
::= 11109

gstPow3ChAmpsX10ATRAP TRAP-TYPE
ENTERPRISE geistmfg
VARIABLES { pow3ChAmpsX10A, pow3ChName, productFriendlyName, alarmTripType }
DESCRIPTION "Amps x 10 A Trap"
::= 11110

gstPow3ChRealPowATRAP TRAP-TYPE
ENTERPRISE geistmfg
VARIABLES { pow3ChRealPowA, pow3ChName, productFriendlyName, alarmTripType }
DESCRIPTION "Real Power A Trap"
::= 11111

gstPow3ChAppPowATRAP TRAP-TYPE
ENTERPRISE geistmfg
VARIABLES { pow3ChAppPowA, pow3ChName, productFriendlyName, alarmTripType }
DESCRIPTION "Apparent Power A Trap"
::= 11112

gstPow3ChPwrFactATRAP TRAP-TYPE
ENTERPRISE geistmfg
VARIABLES { pow3ChPwrFactA, pow3ChName, productFriendlyName, alarmTripType }
DESCRIPTION "Power Factor A Trap"
::= 11113

gstPow3ChKWattHrsBTRAP TRAP-TYPE
ENTERPRISE geistmfg
VARIABLES { pow3ChKWattHrsB, pow3ChName, productFriendlyName, alarmTripType }
DESCRIPTION "Kilo Watt Hours B Trap"
::= 11114

gstPow3ChVoltsBTRAP TRAP-TYPE
ENTERPRISE geistmfg
VARIABLES { pow3ChVoltsB, pow3ChName, productFriendlyName, alarmTripType }
DESCRIPTION "Volts B Trap"
::= 11115

gstPow3ChVoltMaxBTRAP TRAP-TYPE
ENTERPRISE geistmfg
VARIABLES { pow3ChVoltMaxB, pow3ChName, productFriendlyName, alarmTripType }
DESCRIPTION "Volts Max B Trap"
::= 11116

gstPow3ChVoltMinBTRAP TRAP-TYPE
ENTERPRISE geistmfg
VARIABLES { pow3ChVoltMinB, pow3ChName, productFriendlyName, alarmTripType }
DESCRIPTION "Volts Min B Trap"
::= 11117

gstPow3ChVoltPkBTRAP TRAP-TYPE
ENTERPRISE geistmfg
VARIABLES { pow3ChVoltPkB, pow3ChName, productFriendlyName, alarmTripType }
DESCRIPTION "Volt Peak B Trap"
::= 11118

gstPow3ChAmpsX10BTRAP TRAP-TYPE
ENTERPRISE geistmfg
VARIABLES { pow3ChAmpsX10B, pow3ChName, productFriendlyName, alarmTripType }
DESCRIPTION "Amps x 10 B Trap"
::= 11119

gstPow3ChRealPowBTRAP TRAP-TYPE
ENTERPRISE geistmfg
VARIABLES { pow3ChRealPowB, pow3ChName, productFriendlyName, alarmTripType }
DESCRIPTION "Real Power B Trap"
::= 11120

gstPow3ChAppPowBTRAP TRAP-TYPE
ENTERPRISE geistmfg
VARIABLES { pow3ChAppPowB, pow3ChName, productFriendlyName, alarmTripType }
DESCRIPTION "Apparent Power B Trap"
::= 11121

gstPow3ChPwrFactBTRAP TRAP-TYPE
ENTERPRISE geistmfg
VARIABLES { pow3ChPwrFactB, pow3ChName, productFriendlyName, alarmTripType }
DESCRIPTION "Power Factor B Trap"
::= 11122

gstPow3ChKWattHrsCTRAP TRAP-TYPE
ENTERPRISE geistmfg
VARIABLES { pow3ChKWattHrsC, pow3ChName, productFriendlyName, alarmTripType }
DESCRIPTION "Kilo Watt Hours C Trap"
::= 11123

gstPow3ChVoltsCTRAP TRAP-TYPE
ENTERPRISE geistmfg
VARIABLES { pow3ChVoltsC, pow3ChName, productFriendlyName, alarmTripType }
DESCRIPTION "Volts C Trap"
::= 11124

gstPow3ChVoltMaxCTRAP TRAP-TYPE
ENTERPRISE geistmfg
VARIABLES { pow3ChVoltMaxC, pow3ChName, productFriendlyName, alarmTripType }
DESCRIPTION "Volts Max C Trap"
::= 11125

gstPow3ChVoltMinCTRAP TRAP-TYPE
ENTERPRISE geistmfg
VARIABLES { pow3ChVoltMinC, pow3ChName, productFriendlyName, alarmTripType }
DESCRIPTION "Volts Min C Trap"
::= 11126

gstPow3ChVoltPkCTRAP TRAP-TYPE
ENTERPRISE geistmfg
VARIABLES { pow3ChVoltPkC, pow3ChName, productFriendlyName, alarmTripType }
DESCRIPTION "Volt Peak C Trap"
::= 11127

gstPow3ChAmpsX10CTRAP TRAP-TYPE
ENTERPRISE geistmfg
VARIABLES { pow3ChAmpsX10C, pow3ChName, productFriendlyName, alarmTripType }
DESCRIPTION "Amps x 10 C Trap"
::= 11128

gstPow3ChRealPowCTRAP TRAP-TYPE
ENTERPRISE geistmfg
VARIABLES { pow3ChRealPowC, pow3ChName, productFriendlyName, alarmTripType }
DESCRIPTION "Real Power C Trap"
::= 11129

gstPow3ChAppPowCTRAP TRAP-TYPE
ENTERPRISE geistmfg
VARIABLES { pow3ChAppPowC, pow3ChName, productFriendlyName, alarmTripType }
DESCRIPTION "Apparent Power C Trap"
::= 11130

gstPow3ChPwrFactCTRAP TRAP-TYPE
ENTERPRISE geistmfg
VARIABLES { pow3ChPwrFactC, pow3ChName, productFriendlyName, alarmTripType }
DESCRIPTION "Power Factor C Trap"
::= 11131

gstOutlet1StatusTRAP TRAP-TYPE
ENTERPRISE geistmfg
VARIABLES { outlet1Status, outletName, productFriendlyName, alarmTripType }
DESCRIPTION "Outlet 1 Status Trap"
::= 11205

gstOutlet2StatusTRAP TRAP-TYPE
ENTERPRISE geistmfg
VARIABLES { outlet2Status, outletName, productFriendlyName, alarmTripType }
DESCRIPTION "Outlet 2 Status Trap"
::= 11206

gstVsfcSetPointCTRAP TRAP-TYPE
ENTERPRISE geistmfg
VARIABLES { vsfcSetPointC, vsfcName, productFriendlyName, alarmTripType }
DESCRIPTION "Vsfc Temp Set Point Sensor Trap"
::= 11305

gstVsfcIntTempCTRAP TRAP-TYPE
ENTERPRISE geistmfg
VARIABLES { vsfcIntTempC, vsfcName, productFriendlyName, alarmTripType }
DESCRIPTION "Vsfc Internal Temp Sensor Trap"
::= 11306

gstVsfcExt1TempCTRAP TRAP-TYPE
ENTERPRISE geistmfg
VARIABLES { vsfcExt1TempC, vsfcName, productFriendlyName, alarmTripType }
DESCRIPTION "Vsfc External Temp 1 Sensor Trap"
::= 11307

gstVsfcExt2TempCTRAP TRAP-TYPE
ENTERPRISE geistmfg
VARIABLES { vsfcExt2TempC, vsfcName, productFriendlyName, alarmTripType }
DESCRIPTION "Vsfc External Temp 2 Sensor Trap"
::= 11308

gstVsfcExt3TempCTRAP TRAP-TYPE
ENTERPRISE geistmfg
VARIABLES { vsfcExt3TempC, vsfcName, productFriendlyName, alarmTripType }
DESCRIPTION "Vsfc External Temp 3 Sensor Trap"
::= 11309

gstVsfcExt4TempCTRAP TRAP-TYPE
ENTERPRISE geistmfg
VARIABLES { vsfcExt4TempC, vsfcName, productFriendlyName, alarmTripType }
DESCRIPTION "Vsfc External Temp 4 Sensor Trap"
::= 11310

gstVsfcFanSpeedTRAP TRAP-TYPE
ENTERPRISE geistmfg
VARIABLES { vsfcFanSpeed, vsfcName, productFriendlyName, alarmTripType }
DESCRIPTION "Vsfc Fan Speed Sensor Trap"
::= 11311

gstCtrl3ChVoltsATRAP TRAP-TYPE
ENTERPRISE geistmfg
VARIABLES { ctrl3ChVoltsA, ctrl3ChName, productFriendlyName, alarmTripType }
DESCRIPTION "Volts A Trap"
::= 11405

gstCtrl3ChVoltPkATRAP TRAP-TYPE
ENTERPRISE geistmfg
VARIABLES { ctrl3ChVoltPkA, ctrl3ChName, productFriendlyName, alarmTripType }
DESCRIPTION "Volt Peak A Trap"
::= 11406

gstCtrl3ChAmpsATRAP TRAP-TYPE
ENTERPRISE geistmfg
VARIABLES { ctrl3ChAmpsA, ctrl3ChName, productFriendlyName, alarmTripType }
DESCRIPTION "Amps A Trap"
::= 11407

gstCtrl3ChAmpPkATRAP TRAP-TYPE
ENTERPRISE geistmfg
VARIABLES { ctrl3ChAmpPkA, ctrl3ChName, productFriendlyName, alarmTripType }
DESCRIPTION "Amps Peak A Trap"
::= 11408

gstCtrl3ChRealPowATRAP TRAP-TYPE
ENTERPRISE geistmfg
VARIABLES { ctrl3ChRealPowA, ctrl3ChName, productFriendlyName, alarmTripType }
DESCRIPTION "Real Power A Trap"
::= 11409

gstCtrl3ChAppPowATRAP TRAP-TYPE
ENTERPRISE geistmfg
VARIABLES { ctrl3ChAppPowA, ctrl3ChName, productFriendlyName, alarmTripType }
DESCRIPTION "Apparent Power A Trap"
::= 11410

gstCtrl3ChPwrFactATRAP TRAP-TYPE
ENTERPRISE geistmfg
VARIABLES { ctrl3ChPwrFactA, ctrl3ChName, productFriendlyName, alarmTripType }
DESCRIPTION "Power Factor A Trap"
::= 11411

gstCtrl3ChVoltsBTRAP TRAP-TYPE
ENTERPRISE geistmfg
VARIABLES { ctrl3ChVoltsB, ctrl3ChName, productFriendlyName, alarmTripType }
DESCRIPTION "Volts B Trap"
::= 11412

gstCtrl3ChVoltPkBTRAP TRAP-TYPE
ENTERPRISE geistmfg
VARIABLES { ctrl3ChVoltPkB, ctrl3ChName, productFriendlyName, alarmTripType }
DESCRIPTION "Volt Peak B Trap"
::= 11413

gstCtrl3ChAmpsBTRAP TRAP-TYPE
ENTERPRISE geistmfg
VARIABLES { ctrl3ChAmpsB, ctrl3ChName, productFriendlyName, alarmTripType }
DESCRIPTION "Amps B Trap"
::= 11414

gstCtrl3ChAmpPkBTRAP TRAP-TYPE
ENTERPRISE geistmfg
VARIABLES { ctrl3ChAmpPkB, ctrl3ChName, productFriendlyName, alarmTripType }
DESCRIPTION "Amps Peak B Trap"
::= 11415

gstCtrl3ChRealPowBTRAP TRAP-TYPE
ENTERPRISE geistmfg
VARIABLES { ctrl3ChRealPowB, ctrl3ChName, productFriendlyName, alarmTripType }
DESCRIPTION "Real Power B Trap"
::= 11416

gstCtrl3ChAppPowBTRAP TRAP-TYPE
ENTERPRISE geistmfg
VARIABLES { ctrl3ChAppPowB, ctrl3ChName, productFriendlyName, alarmTripType }
DESCRIPTION "Apparent Power B Trap"
::= 11417

gstCtrl3ChPwrFactBTRAP TRAP-TYPE
ENTERPRISE geistmfg
VARIABLES { ctrl3ChPwrFactB, ctrl3ChName, productFriendlyName, alarmTripType }
DESCRIPTION "Power Factor B Trap"
::= 11418

gstCtrl3ChVoltsCTRAP TRAP-TYPE
ENTERPRISE geistmfg
VARIABLES { ctrl3ChVoltsC, ctrl3ChName, productFriendlyName, alarmTripType }
DESCRIPTION "Volts C Trap"
::= 11419

gstCtrl3ChVoltPkCTRAP TRAP-TYPE
ENTERPRISE geistmfg
VARIABLES { ctrl3ChVoltPkC, ctrl3ChName, productFriendlyName, alarmTripType }
DESCRIPTION "Volt Peak C Trap"
::= 11420

gstCtrl3ChAmpsCTRAP TRAP-TYPE
ENTERPRISE geistmfg
VARIABLES { ctrl3ChAmpsC, ctrl3ChName, productFriendlyName, alarmTripType }
DESCRIPTION "Amps C Trap"
::= 11421

gstCtrl3ChAmpPkCTRAP TRAP-TYPE
ENTERPRISE geistmfg
VARIABLES { ctrl3ChAmpPkC, ctrl3ChName, productFriendlyName, alarmTripType }
DESCRIPTION "Amps Peak C Trap"
::= 11422

gstCtrl3ChRealPowCTRAP TRAP-TYPE
ENTERPRISE geistmfg
VARIABLES { ctrl3ChRealPowC, ctrl3ChName, productFriendlyName, alarmTripType }
DESCRIPTION "Real Power C Trap"
::= 11423

gstCtrl3ChAppPowCTRAP TRAP-TYPE
ENTERPRISE geistmfg
VARIABLES { ctrl3ChAppPowC, ctrl3ChName, productFriendlyName, alarmTripType }
DESCRIPTION "Apparent Power C Trap"
::= 11424

gstCtrl3ChPwrFactCTRAP TRAP-TYPE
ENTERPRISE geistmfg
VARIABLES { ctrl3ChPwrFactC, ctrl3ChName, productFriendlyName, alarmTripType }
DESCRIPTION "Power Factor C Trap"
::= 11425

gstCtrlGrpAmpsATRAP TRAP-TYPE
ENTERPRISE geistmfg
VARIABLES { ctrlGrpAmpsA, ctrlGrpAmpsName, productFriendlyName, alarmTripType }
DESCRIPTION "Group A Amps Trap"
::= 11505

gstCtrlGrpAmpsBTRAP TRAP-TYPE
ENTERPRISE geistmfg
VARIABLES { ctrlGrpAmpsB, ctrlGrpAmpsName, productFriendlyName, alarmTripType }
DESCRIPTION "Group B Amps Trap"
::= 11506

gstCtrlGrpAmpsCTRAP TRAP-TYPE
ENTERPRISE geistmfg
VARIABLES { ctrlGrpAmpsC, ctrlGrpAmpsName, productFriendlyName, alarmTripType }
DESCRIPTION "Group C Amps Trap"
::= 11507

gstCtrlGrpAmpsDTRAP TRAP-TYPE
ENTERPRISE geistmfg
VARIABLES { ctrlGrpAmpsD, ctrlGrpAmpsName, productFriendlyName, alarmTripType }
DESCRIPTION "Group D Amps Trap"
::= 11508

gstCtrlGrpAmpsETRAP TRAP-TYPE
ENTERPRISE geistmfg
VARIABLES { ctrlGrpAmpsE, ctrlGrpAmpsName, productFriendlyName, alarmTripType }
DESCRIPTION "Group E Amps Trap"
::= 11509

gstCtrlGrpAmpsFTRAP TRAP-TYPE
ENTERPRISE geistmfg
VARIABLES { ctrlGrpAmpsF, ctrlGrpAmpsName, productFriendlyName, alarmTripType }
DESCRIPTION "Group F Amps Trap"
::= 11510

gstDewPointSensorDewPointTRAP TRAP-TYPE
ENTERPRISE geistmfg
VARIABLES { dewPointSensorDewPoint, dewPointSensorName, productFriendlyName, alarmTripType }
DESCRIPTION "Remote Dew Point Sensor - Dew Point Trap"
::= 11705

gstDewPointSensorTempCTRAP TRAP-TYPE
ENTERPRISE geistmfg
VARIABLES { dewPointSensorTempC, dewPointSensorName, productFriendlyName, alarmTripType }
DESCRIPTION "Remote Dew Point Sensor - Temperature Trap"
::= 11706

gstDewPointSensorHumidityTRAP TRAP-TYPE
ENTERPRISE geistmfg
VARIABLES { dewPointSensorHumidity, dewPointSensorName, productFriendlyName, alarmTripType }
DESCRIPTION "Remote Dew Point Sensor - Humidity"
::= 11707

gstClimateTempCCLEAR TRAP-TYPE
ENTERPRISE geistmfg
VARIABLES { climateTempC, climateName, productFriendlyName, alarmTripType }
DESCRIPTION "Climate Temperature Sensor Clear Trap"
::= 20205

gstClimateHumidityCLEAR TRAP-TYPE
ENTERPRISE geistmfg
VARIABLES { climateHumidity, climateName, productFriendlyName, alarmTripType }
DESCRIPTION "Climate Humidity Sensor Clear Trap"
::= 20206

gstClimateAirflowCLEAR TRAP-TYPE
ENTERPRISE geistmfg
VARIABLES { climateAirflow, climateName, productFriendlyName, alarmTripType }
DESCRIPTION "Climate Air Flow Sensor Clear Trap"
::= 20207

gstClimateLightCLEAR TRAP-TYPE
ENTERPRISE geistmfg
VARIABLES { climateLight, climateName, productFriendlyName, alarmTripType }
DESCRIPTION "Climate Light Sensor Clear Trap"
::= 20208

gstClimateSoundCLEAR TRAP-TYPE
ENTERPRISE geistmfg
VARIABLES { climateSound, climateName, productFriendlyName, alarmTripType }
DESCRIPTION "Climate Sound Sensor Clear Trap"
::= 20209

gstClimateIO1CLEAR TRAP-TYPE
ENTERPRISE geistmfg
VARIABLES { climateIO1, climateName, productFriendlyName, alarmTripType }
DESCRIPTION "Climate IO1 Sensor Clear Trap"
::= 20210

gstClimateIO2CLEAR TRAP-TYPE
ENTERPRISE geistmfg
VARIABLES { climateIO2, climateName, productFriendlyName, alarmTripType }
DESCRIPTION "Climate IO2 Sensor Clear Trap"
::= 20211

gstClimateIO3CLEAR TRAP-TYPE
ENTERPRISE geistmfg
VARIABLES { climateIO3, climateName, productFriendlyName, alarmTripType }
DESCRIPTION "Climate IO3 Sensor Clear Trap"
::= 20212

gstClimateVoltsCLEAR TRAP-TYPE
ENTERPRISE geistmfg
VARIABLES { climateVolts, climateName, productFriendlyName, alarmTripType }
DESCRIPTION "Climate Volts Clear Trap"
::= 20213

gstClimateVoltPeakCLEAR TRAP-TYPE
ENTERPRISE geistmfg
VARIABLES { climateVoltPeak, climateName, productFriendlyName, alarmTripType }
DESCRIPTION "Climate Volts Peak Clear Trap"
::= 20214

gstClimateAmpsACLEAR TRAP-TYPE
ENTERPRISE geistmfg
VARIABLES { climateAmpsA, climateName, productFriendlyName, alarmTripType }
DESCRIPTION "Climate Amps A Clear Trap"
::= 20215

gstClimateAmpPeakACLEAR TRAP-TYPE
ENTERPRISE geistmfg
VARIABLES { climateAmpPeakA, climateName, productFriendlyName, alarmTripType }
DESCRIPTION "Climate Amp Peak A Clear Trap"
::= 20216

gstClimateRealPowerACLEAR TRAP-TYPE
ENTERPRISE geistmfg
VARIABLES { climateRealPowerA, climateName, productFriendlyName, alarmTripType }
DESCRIPTION "Climate Real Power A Clear Trap"
::= 20217

gstClimateApparentPowerACLEAR TRAP-TYPE
ENTERPRISE geistmfg
VARIABLES { climateApparentPowerA, climateName, productFriendlyName, alarmTripType }
DESCRIPTION "Climate Apparent Power A Clear Trap"
::= 20218

gstClimatePowerFactorACLEAR TRAP-TYPE
ENTERPRISE geistmfg
VARIABLES { climatePowerFactorA, climateName, productFriendlyName, alarmTripType }
DESCRIPTION "Climate Power Factor A Clear Trap"
::= 20219

gstClimateAmpsBCLEAR TRAP-TYPE
ENTERPRISE geistmfg
VARIABLES { climateAmpsB, climateName, productFriendlyName, alarmTripType }
DESCRIPTION "Climate Amps B Clear Trap"
::= 20220

gstClimateAmpPeakBCLEAR TRAP-TYPE
ENTERPRISE geistmfg
VARIABLES { climateAmpPeakB, climateName, productFriendlyName, alarmTripType }
DESCRIPTION "Climate Amp Peak B Clear Trap"
::= 20221

gstClimateRealPowerBCLEAR TRAP-TYPE
ENTERPRISE geistmfg
VARIABLES { climateRealPowerB, climateName, productFriendlyName, alarmTripType }
DESCRIPTION "Climate Real Power B Clear Trap"
::= 20222

gstClimateApparentPowerBCLEAR TRAP-TYPE
ENTERPRISE geistmfg
VARIABLES { climateApparentPowerB, climateName, productFriendlyName, alarmTripType }
DESCRIPTION "Climate Apparent Power B Clear Trap"
::= 20223

gstClimatePowerFactorBCLEAR TRAP-TYPE
ENTERPRISE geistmfg
VARIABLES { climatePowerFactorB, climateName, productFriendlyName, alarmTripType }
DESCRIPTION "Climate Power Factor B Clear Trap"
::= 20224

gstClimateAmpsCCLEAR TRAP-TYPE
ENTERPRISE geistmfg
VARIABLES { climateAmpsC, climateName, productFriendlyName, alarmTripType }
DESCRIPTION "Climate Amps C Clear Trap"
::= 20225

gstClimateAmpPeakCCLEAR TRAP-TYPE
ENTERPRISE geistmfg
VARIABLES { climateAmpPeakC, climateName, productFriendlyName, alarmTripType }
DESCRIPTION "Climate Amp Peak C Clear Trap"
::= 20226

gstClimateRealPowerCCLEAR TRAP-TYPE
ENTERPRISE geistmfg
VARIABLES { climateRealPowerC, climateName, productFriendlyName, alarmTripType }
DESCRIPTION "Climate Real Power C Clear Trap"
::= 20227

gstClimateApparentPowerCCLEAR TRAP-TYPE
ENTERPRISE geistmfg
VARIABLES { climateApparentPowerC, climateName, productFriendlyName, alarmTripType }
DESCRIPTION "Climate Apparent Power C Clear Trap"
::= 20228

gstClimatePowerFactorCCLEAR TRAP-TYPE
ENTERPRISE geistmfg
VARIABLES { climatePowerFactorC, climateName, productFriendlyName, alarmTripType }
DESCRIPTION "Climate Power Factor C Clear Trap"
::= 20229

gstPowMonKWattHrsCLEAR TRAP-TYPE
ENTERPRISE geistmfg
VARIABLES { powMonKWattHrs, powMonName, productFriendlyName, alarmTripType }
DESCRIPTION "Kilo Watt Hours Clear Trap"
::= 20305

gstPowMonVoltsCLEAR TRAP-TYPE
ENTERPRISE geistmfg
VARIABLES { powMonVolts, powMonName, productFriendlyName, alarmTripType }
DESCRIPTION "Volts Clear Trap"
::= 20306

gstPowMonVoltMaxCLEAR TRAP-TYPE
ENTERPRISE geistmfg
VARIABLES { powMonVoltMax, powMonName, productFriendlyName, alarmTripType }
DESCRIPTION "Volts Max Clear Trap"
::= 20307

gstPowMonVoltMinCLEAR TRAP-TYPE
ENTERPRISE geistmfg
VARIABLES { powMonVoltMin, powMonName, productFriendlyName, alarmTripType }
DESCRIPTION "Volts Min Clear Trap"
::= 20308

gstPowMonVoltPkCLEAR TRAP-TYPE
ENTERPRISE geistmfg
VARIABLES { powMonVoltPk, powMonName, productFriendlyName, alarmTripType }
DESCRIPTION "Volt Peak Clear Trap"
::= 20309

gstPowMonAmpsX10CLEAR TRAP-TYPE
ENTERPRISE geistmfg
VARIABLES { powMonAmpsX10, powMonName, productFriendlyName, alarmTripType }
DESCRIPTION "Amps x 10 Clear Trap"
::= 20310

gstPowMonRealPowCLEAR TRAP-TYPE
ENTERPRISE geistmfg
VARIABLES { powMonRealPow, powMonName, productFriendlyName, alarmTripType }
DESCRIPTION "Real Power Clear Trap"
::= 20311

gstPowMonAppPowCLEAR TRAP-TYPE
ENTERPRISE geistmfg
VARIABLES { powMonAppPow, powMonName, productFriendlyName, alarmTripType }
DESCRIPTION "Apparent Power Clear Trap"
::= 20312

gstPowMonPwrFactCLEAR TRAP-TYPE
ENTERPRISE geistmfg
VARIABLES { powMonPwrFact, powMonName, productFriendlyName, alarmTripType }
DESCRIPTION "Power Factor Clear Trap"
::= 20313

gstPowMonOutlet1CLEAR TRAP-TYPE
ENTERPRISE geistmfg
VARIABLES { powMonOutlet1, powMonName, productFriendlyName, alarmTripType }
DESCRIPTION "Outlet 1 Clear Trap"
::= 20314

gstPowMonOutlet2CLEAR TRAP-TYPE
ENTERPRISE geistmfg
VARIABLES { powMonOutlet2, powMonName, productFriendlyName, alarmTripType }
DESCRIPTION "Outlet 2 Clear Trap"
::= 20315

gstTempSensorTempCCLEAR TRAP-TYPE
ENTERPRISE geistmfg
VARIABLES { tempSensorTempC, tempSensorName, productFriendlyName, alarmTripType }
DESCRIPTION "Remote Temp Sensor - Temperature Clear Trap"
::= 20405

gstAirFlowSensorFlowCLEAR TRAP-TYPE
ENTERPRISE geistmfg
VARIABLES { airFlowSensorFlow, airFlowSensorName, productFriendlyName, alarmTripType }
DESCRIPTION "Remote Air Flow Sensor - Air Flow Clear Trap"
::= 20505

gstAirFlowSensorTempCCLEAR TRAP-TYPE
ENTERPRISE geistmfg
VARIABLES { airFlowSensorTempC, airFlowSensorName, productFriendlyName, alarmTripType }
DESCRIPTION "Remote Air Flow Sensor - Temperature Clear Trap"
::= 20506

gstAirFlowSensorHumidityCLEAR TRAP-TYPE
ENTERPRISE geistmfg
VARIABLES { airFlowSensorHumidity, airFlowSensorName, productFriendlyName, alarmTripType }
DESCRIPTION "Remote Air Flow Sensor - Humidity Clear Trap"
::= 20507

gstPowerVoltsCLEAR TRAP-TYPE
ENTERPRISE geistmfg
VARIABLES { powerVolts, powerName, productFriendlyName, alarmTripType }
DESCRIPTION "Power-Only Volts Clear Trap"
::= 20605

gstPowerAmpsCLEAR TRAP-TYPE
ENTERPRISE geistmfg
VARIABLES { powerAmps, powerName, productFriendlyName, alarmTripType }
DESCRIPTION "Power-Only Amps Clear Trap"
::= 20606

gstPowerRealPowCLEAR TRAP-TYPE
ENTERPRISE geistmfg
VARIABLES { powerRealPow, powerName, productFriendlyName, alarmTripType }
DESCRIPTION "Power-Only Watts Clear Trap"
::= 20607

gstPowerAppPowCLEAR TRAP-TYPE
ENTERPRISE geistmfg
VARIABLES { powerAppPow, powerName, productFriendlyName, alarmTripType }
DESCRIPTION "Power-Only Volt Amps Clear Trap"
::= 20608

gstPowerPwrFactorCLEAR TRAP-TYPE
ENTERPRISE geistmfg
VARIABLES { powerPwrFactor, powerName, productFriendlyName, alarmTripType }
DESCRIPTION "Power-Only Power Factor Clear Trap"
::= 20609

gstDoorSensorStatusCLEAR TRAP-TYPE
ENTERPRISE geistmfg
VARIABLES { doorSensorStatus, doorSensorName, productFriendlyName, alarmTripType }
DESCRIPTION "Door sensor Clear Trap"
::= 20705

gstWaterSensorDampnessCLEAR TRAP-TYPE
ENTERPRISE geistmfg
VARIABLES { waterSensorDampness, waterSensorName, productFriendlyName, alarmTripType }
DESCRIPTION "Water sensor Clear Trap"
::= 20805

gstCurrentMonitorAmpsCLEAR TRAP-TYPE
ENTERPRISE geistmfg
VARIABLES { currentMonitorAmps, currentMonitorName, productFriendlyName, alarmTripType }
DESCRIPTION "Current Monitor Amps Clear Trap"
::= 20905

gstMillivoltMonitorMVCLEAR TRAP-TYPE
ENTERPRISE geistmfg
VARIABLES { millivoltMonitorMV, millivoltMonitorName, productFriendlyName, alarmTripType }
DESCRIPTION "Millivolt Monitor Clear Trap"
::= 21005

gstPow3ChKWattHrsACLEAR TRAP-TYPE
ENTERPRISE geistmfg
VARIABLES { pow3ChKWattHrsA, pow3ChName, productFriendlyName, alarmTripType }
DESCRIPTION "Kilo Watt Hours A Clear Trap"
::= 21105

gstPow3ChVoltsACLEAR TRAP-TYPE
ENTERPRISE geistmfg
VARIABLES { pow3ChVoltsA, pow3ChName, productFriendlyName, alarmTripType }
DESCRIPTION "Volts A Clear Trap"
::= 21106

gstPow3ChVoltMaxACLEAR TRAP-TYPE
ENTERPRISE geistmfg
VARIABLES { pow3ChVoltMaxA, pow3ChName, productFriendlyName, alarmTripType }
DESCRIPTION "Volts Max A Clear Trap"
::= 21107

gstPow3ChVoltMinACLEAR TRAP-TYPE
ENTERPRISE geistmfg
VARIABLES { pow3ChVoltMinA, pow3ChName, productFriendlyName, alarmTripType }
DESCRIPTION "Volts Min A Clear Trap"
::= 21108

gstPow3ChVoltPkACLEAR TRAP-TYPE
ENTERPRISE geistmfg
VARIABLES { pow3ChVoltPkA, pow3ChName, productFriendlyName, alarmTripType }
DESCRIPTION "Volt Peak A Clear Trap"
::= 21109

gstPow3ChAmpsX10ACLEAR TRAP-TYPE
ENTERPRISE geistmfg
VARIABLES { pow3ChAmpsX10A, pow3ChName, productFriendlyName, alarmTripType }
DESCRIPTION "Amps x 10 A Clear Trap"
::= 21110

gstPow3ChRealPowACLEAR TRAP-TYPE
ENTERPRISE geistmfg
VARIABLES { pow3ChRealPowA, pow3ChName, productFriendlyName, alarmTripType }
DESCRIPTION "Real Power A Clear Trap"
::= 21111

gstPow3ChAppPowACLEAR TRAP-TYPE
ENTERPRISE geistmfg
VARIABLES { pow3ChAppPowA, pow3ChName, productFriendlyName, alarmTripType }
DESCRIPTION "Apparent Power A Clear Trap"
::= 21112

gstPow3ChPwrFactACLEAR TRAP-TYPE
ENTERPRISE geistmfg
VARIABLES { pow3ChPwrFactA, pow3ChName, productFriendlyName, alarmTripType }
DESCRIPTION "Power Factor A Clear Trap"
::= 21113

gstPow3ChKWattHrsBCLEAR TRAP-TYPE
ENTERPRISE geistmfg
VARIABLES { pow3ChKWattHrsB, pow3ChName, productFriendlyName, alarmTripType }
DESCRIPTION "Kilo Watt Hours B Clear Trap"
::= 21114

gstPow3ChVoltsBCLEAR TRAP-TYPE
ENTERPRISE geistmfg
VARIABLES { pow3ChVoltsB, pow3ChName, productFriendlyName, alarmTripType }
DESCRIPTION "Volts B Clear Trap"
::= 21115

gstPow3ChVoltMaxBCLEAR TRAP-TYPE
ENTERPRISE geistmfg
VARIABLES { pow3ChVoltMaxB, pow3ChName, productFriendlyName, alarmTripType }
DESCRIPTION "Volts Max B Clear Trap"
::= 21116

gstPow3ChVoltMinBCLEAR TRAP-TYPE
ENTERPRISE geistmfg
VARIABLES { pow3ChVoltMinB, pow3ChName, productFriendlyName, alarmTripType }
DESCRIPTION "Volts Min B Clear Trap"
::= 21117

gstPow3ChVoltPkBCLEAR TRAP-TYPE
ENTERPRISE geistmfg
VARIABLES { pow3ChVoltPkB, pow3ChName, productFriendlyName, alarmTripType }
DESCRIPTION "Volt Peak B Clear Trap"
::= 21118

gstPow3ChAmpsX10BCLEAR TRAP-TYPE
ENTERPRISE geistmfg
VARIABLES { pow3ChAmpsX10B, pow3ChName, productFriendlyName, alarmTripType }
DESCRIPTION "Amps x 10 B Clear Trap"
::= 21119

gstPow3ChRealPowBCLEAR TRAP-TYPE
ENTERPRISE geistmfg
VARIABLES { pow3ChRealPowB, pow3ChName, productFriendlyName, alarmTripType }
DESCRIPTION "Real Power B Clear Trap"
::= 21120

gstPow3ChAppPowBCLEAR TRAP-TYPE
ENTERPRISE geistmfg
VARIABLES { pow3ChAppPowB, pow3ChName, productFriendlyName, alarmTripType }
DESCRIPTION "Apparent Power B Clear Trap"
::= 21121

gstPow3ChPwrFactBCLEAR TRAP-TYPE
ENTERPRISE geistmfg
VARIABLES { pow3ChPwrFactB, pow3ChName, productFriendlyName, alarmTripType }
DESCRIPTION "Power Factor B Clear Trap"
::= 21122

gstPow3ChKWattHrsCCLEAR TRAP-TYPE
ENTERPRISE geistmfg
VARIABLES { pow3ChKWattHrsC, pow3ChName, productFriendlyName, alarmTripType }
DESCRIPTION "Kilo Watt Hours C Clear Trap"
::= 21123

gstPow3ChVoltsCCLEAR TRAP-TYPE
ENTERPRISE geistmfg
VARIABLES { pow3ChVoltsC, pow3ChName, productFriendlyName, alarmTripType }
DESCRIPTION "Volts C Clear Trap"
::= 21124

gstPow3ChVoltMaxCCLEAR TRAP-TYPE
ENTERPRISE geistmfg
VARIABLES { pow3ChVoltMaxC, pow3ChName, productFriendlyName, alarmTripType }
DESCRIPTION "Volts Max C Clear Trap"
::= 21125

gstPow3ChVoltMinCCLEAR TRAP-TYPE
ENTERPRISE geistmfg
VARIABLES { pow3ChVoltMinC, pow3ChName, productFriendlyName, alarmTripType }
DESCRIPTION "Volts Min C Clear Trap"
::= 21126

gstPow3ChVoltPkCCLEAR TRAP-TYPE
ENTERPRISE geistmfg
VARIABLES { pow3ChVoltPkC, pow3ChName, productFriendlyName, alarmTripType }
DESCRIPTION "Volt Peak C Clear Trap"
::= 21127

gstPow3ChAmpsX10CCLEAR TRAP-TYPE
ENTERPRISE geistmfg
VARIABLES { pow3ChAmpsX10C, pow3ChName, productFriendlyName, alarmTripType }
DESCRIPTION "Amps x 10 C Clear Trap"
::= 21128

gstPow3ChRealPowCCLEAR TRAP-TYPE
ENTERPRISE geistmfg
VARIABLES { pow3ChRealPowC, pow3ChName, productFriendlyName, alarmTripType }
DESCRIPTION "Real Power C Clear Trap"
::= 21129

gstPow3ChAppPowCCLEAR TRAP-TYPE
ENTERPRISE geistmfg
VARIABLES { pow3ChAppPowC, pow3ChName, productFriendlyName, alarmTripType }
DESCRIPTION "Apparent Power C Clear Trap"
::= 21130

gstPow3ChPwrFactCCLEAR TRAP-TYPE
ENTERPRISE geistmfg
VARIABLES { pow3ChPwrFactC, pow3ChName, productFriendlyName, alarmTripType }
DESCRIPTION "Power Factor C Clear Trap"
::= 21131

gstOutlet1StatusCLEAR TRAP-TYPE
ENTERPRISE geistmfg
VARIABLES { outlet1Status, outletName, productFriendlyName, alarmTripType }
DESCRIPTION "Outlet 1 Status Clear Trap"
::= 21205

gstOutlet2StatusCLEAR TRAP-TYPE
ENTERPRISE geistmfg
VARIABLES { outlet2Status, outletName, productFriendlyName, alarmTripType }
DESCRIPTION "Outlet 2 Status Clear Trap"
::= 21206

gstVsfcSetPointCCLEAR TRAP-TYPE
ENTERPRISE geistmfg
VARIABLES { vsfcSetPointC, vsfcName, productFriendlyName, alarmTripType }
DESCRIPTION "Vsfc Temp Set Point Sensor Clear"
::= 21305

gstVsfcIntTempCCLEAR TRAP-TYPE
ENTERPRISE geistmfg
VARIABLES { vsfcIntTempC, vsfcName, productFriendlyName, alarmTripType }
DESCRIPTION "Vsfc Internal Temp Sensor Clear"
::= 21306

gstVsfcExt1TempCCLEAR TRAP-TYPE
ENTERPRISE geistmfg
VARIABLES { vsfcExt1TempC, vsfcName, productFriendlyName, alarmTripType }
DESCRIPTION "Vsfc External Temp 1 Sensor Clear"
::= 21307

gstVsfcExt2TempCCLEAR TRAP-TYPE
ENTERPRISE geistmfg
VARIABLES { vsfcExt2TempC, vsfcName, productFriendlyName, alarmTripType }
DESCRIPTION "Vsfc External Temp 2 Sensor Clear"
::= 21308

gstVsfcExt3TempCCLEAR TRAP-TYPE
ENTERPRISE geistmfg
VARIABLES { vsfcExt3TempC, vsfcName, productFriendlyName, alarmTripType }
DESCRIPTION "Vsfc External Temp 3 Sensor Clear"
::= 21309

gstVsfcExt4TempCCLEAR TRAP-TYPE
ENTERPRISE geistmfg
VARIABLES { vsfcExt4TempC, vsfcName, productFriendlyName, alarmTripType }
DESCRIPTION "Vsfc External Temp 4 Sensor Clear"
::= 21310

gstVsfcFanSpeedCLEAR TRAP-TYPE
ENTERPRISE geistmfg
VARIABLES { vsfcFanSpeed, vsfcName, productFriendlyName, alarmTripType }
DESCRIPTION "Vsfc Fan Speed Sensor Clear"
::= 21311

gstCtrl3ChVoltsACLEAR TRAP-TYPE
ENTERPRISE geistmfg
VARIABLES { ctrl3ChVoltsA, ctrl3ChName, productFriendlyName, alarmTripType }
DESCRIPTION "Volts A Clear"
::= 21405

gstCtrl3ChVoltPkACLEAR TRAP-TYPE
ENTERPRISE geistmfg
VARIABLES { ctrl3ChVoltPkA, ctrl3ChName, productFriendlyName, alarmTripType }
DESCRIPTION "Volt Peak A Clear"
::= 21406

gstCtrl3ChAmpsACLEAR TRAP-TYPE
ENTERPRISE geistmfg
VARIABLES { ctrl3ChAmpsA, ctrl3ChName, productFriendlyName, alarmTripType }
DESCRIPTION "Amps A Clear"
::= 21407

gstCtrl3ChAmpPkACLEAR TRAP-TYPE
ENTERPRISE geistmfg
VARIABLES { ctrl3ChAmpPkA, ctrl3ChName, productFriendlyName, alarmTripType }
DESCRIPTION "Amps Peak A Clear"
::= 21408

gstCtrl3ChRealPowACLEAR TRAP-TYPE
ENTERPRISE geistmfg
VARIABLES { ctrl3ChRealPowA, ctrl3ChName, productFriendlyName, alarmTripType }
DESCRIPTION "Real Power A Clear"
::= 21409

gstCtrl3ChAppPowACLEAR TRAP-TYPE
ENTERPRISE geistmfg
VARIABLES { ctrl3ChAppPowA, ctrl3ChName, productFriendlyName, alarmTripType }
DESCRIPTION "Apparent Power A Clear"
::= 21410

gstCtrl3ChPwrFactACLEAR TRAP-TYPE
ENTERPRISE geistmfg
VARIABLES { ctrl3ChPwrFactA, ctrl3ChName, productFriendlyName, alarmTripType }
DESCRIPTION "Power Factor A Clear"
::= 21411

gstCtrl3ChVoltsBCLEAR TRAP-TYPE
ENTERPRISE geistmfg
VARIABLES { ctrl3ChVoltsB, ctrl3ChName, productFriendlyName, alarmTripType }
DESCRIPTION "Volts B Clear"
::= 21412

gstCtrl3ChVoltPkBCLEAR TRAP-TYPE
ENTERPRISE geistmfg
VARIABLES { ctrl3ChVoltPkB, ctrl3ChName, productFriendlyName, alarmTripType }
DESCRIPTION "Volt Peak B Clear"
::= 21413

gstCtrl3ChAmpsBCLEAR TRAP-TYPE
ENTERPRISE geistmfg
VARIABLES { ctrl3ChAmpsB, ctrl3ChName, productFriendlyName, alarmTripType }
DESCRIPTION "Amps B Clear"
::= 21414

gstCtrl3ChAmpPkBCLEAR TRAP-TYPE
ENTERPRISE geistmfg
VARIABLES { ctrl3ChAmpPkB, ctrl3ChName, productFriendlyName, alarmTripType }
DESCRIPTION "Amps Peak B Clear"
::= 21415

gstCtrl3ChRealPowBCLEAR TRAP-TYPE
ENTERPRISE geistmfg
VARIABLES { ctrl3ChRealPowB, ctrl3ChName, productFriendlyName, alarmTripType }
DESCRIPTION "Real Power B Clear"
::= 21416

gstCtrl3ChAppPowBCLEAR TRAP-TYPE
ENTERPRISE geistmfg
VARIABLES { ctrl3ChAppPowB, ctrl3ChName, productFriendlyName, alarmTripType }
DESCRIPTION "Apparent Power B Clear"
::= 21417

gstCtrl3ChPwrFactBCLEAR TRAP-TYPE
ENTERPRISE geistmfg
VARIABLES { ctrl3ChPwrFactB, ctrl3ChName, productFriendlyName, alarmTripType }
DESCRIPTION "Power Factor B Clear"
::= 21418

gstCtrl3ChVoltsCCLEAR TRAP-TYPE
ENTERPRISE geistmfg
VARIABLES { ctrl3ChVoltsC, ctrl3ChName, productFriendlyName, alarmTripType }
DESCRIPTION "Volts C Clear"
::= 21419

gstCtrl3ChVoltPkCCLEAR TRAP-TYPE
ENTERPRISE geistmfg
VARIABLES { ctrl3ChVoltPkC, ctrl3ChName, productFriendlyName, alarmTripType }
DESCRIPTION "Volt Peak C Clear"
::= 21420

gstCtrl3ChAmpsCCLEAR TRAP-TYPE
ENTERPRISE geistmfg
VARIABLES { ctrl3ChAmpsC, ctrl3ChName, productFriendlyName, alarmTripType }
DESCRIPTION "Amps C Clear"
::= 21421

gstCtrl3ChAmpPkCCLEAR TRAP-TYPE
ENTERPRISE geistmfg
VARIABLES { ctrl3ChAmpPkC, ctrl3ChName, productFriendlyName, alarmTripType }
DESCRIPTION "Amps Peak C Clear"
::= 21422

gstCtrl3ChRealPowCCLEAR TRAP-TYPE
ENTERPRISE geistmfg
VARIABLES { ctrl3ChRealPowC, ctrl3ChName, productFriendlyName, alarmTripType }
DESCRIPTION "Real Power C Clear"
::= 21423

gstCtrl3ChAppPowCCLEAR TRAP-TYPE
ENTERPRISE geistmfg
VARIABLES { ctrl3ChAppPowC, ctrl3ChName, productFriendlyName, alarmTripType }
DESCRIPTION "Apparent Power C Clear"
::= 21424

gstCtrl3ChPwrFactCCLEAR TRAP-TYPE
ENTERPRISE geistmfg
VARIABLES { ctrl3ChPwrFactC, ctrl3ChName, productFriendlyName, alarmTripType }
DESCRIPTION "Power Factor C Clear"
::= 21425

gstCtrlGrpAmpsACLEAR TRAP-TYPE
ENTERPRISE geistmfg
VARIABLES { ctrlGrpAmpsA, ctrlGrpAmpsName, productFriendlyName, alarmTripType }
DESCRIPTION "Group A Amps Clear Trap"
::= 21505

gstCtrlGrpAmpsBCLEAR TRAP-TYPE
ENTERPRISE geistmfg
VARIABLES { ctrlGrpAmpsB, ctrlGrpAmpsName, productFriendlyName, alarmTripType }
DESCRIPTION "Group B Amps Clear Trap"
::= 21506

gstCtrlGrpAmpsCCLEAR TRAP-TYPE
ENTERPRISE geistmfg
VARIABLES { ctrlGrpAmpsC, ctrlGrpAmpsName, productFriendlyName, alarmTripType }
DESCRIPTION "Group C Amps Clear Trap"
::= 21507

gstCtrlGrpAmpsDCLEAR TRAP-TYPE
ENTERPRISE geistmfg
VARIABLES { ctrlGrpAmpsD, ctrlGrpAmpsName, productFriendlyName, alarmTripType }
DESCRIPTION "Group D Amps Clear Trap"
::= 21508

gstCtrlGrpAmpsECLEAR TRAP-TYPE
ENTERPRISE geistmfg
VARIABLES { ctrlGrpAmpsE, ctrlGrpAmpsName, productFriendlyName, alarmTripType }
DESCRIPTION "Group E Amps Clear Trap"
::= 21509

gstCtrlGrpAmpsFCLEAR TRAP-TYPE
ENTERPRISE geistmfg
VARIABLES { ctrlGrpAmpsF, ctrlGrpAmpsName, productFriendlyName, alarmTripType }
DESCRIPTION "Group F Amps Clear Trap"
::= 21510

gstDewPointSensorDewPointCLEAR TRAP-TYPE
ENTERPRISE geistmfg
VARIABLES { dewPointSensorDewPoint, dewPointSensorName, productFriendlyName, alarmTripType }
DESCRIPTION "Remote Dew Point Sensor - Dew Point Clear Trap"
::= 21705

gstDewPointSensorTempCCLEAR TRAP-TYPE
ENTERPRISE geistmfg
VARIABLES { dewPointSensorTempC, dewPointSensorName, productFriendlyName, alarmTripType }
DESCRIPTION "Remote Dew Point Sensor - Temperature Clear Trap"
::= 21706

gstDewPointSensorHumidityCLEAR TRAP-TYPE
ENTERPRISE geistmfg
VARIABLES { dewPointSensorHumidity, dewPointSensorName, productFriendlyName, alarmTripType }
DESCRIPTION "Remote Dew Point Sensor - Humidity Clear Trap"
::= 21707

END
