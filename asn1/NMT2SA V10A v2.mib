--  Title:    NMT2SA_V10A_V2.MIB
--  Version:  v1.0
--
--  Copyright @ 2008 DPS Inc. All Rights Reserved
--
--  This MIB defines supplemental objects for the DPS NetMediator T2S series remotes.
--
--

DPS-MIB-NMT2SA-V10A-V2 DEFINITIONS ::= BEGIN

IMPORTS
	dpsRTUv2
		FROM DPS-MIB-V38-V2;

dpsRTUv2p10001Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 1 is set"
	::= { dpsRTUv2 10001 }

dpsRTUv2p11001Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 1 is cleared"
	::= { dpsRTUv2 11001 }

dpsRTUv2p10002Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 2 is set"
	::= { dpsRTUv2 10002 }

dpsRTUv2p11002Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 2 is cleared"
	::= { dpsRTUv2 11002 }

dpsRTUv2p10003Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 3 is set"
	::= { dpsRTUv2 10003 }

dpsRTUv2p11003Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 3 is cleared"
	::= { dpsRTUv2 11003 }

dpsRTUv2p10004Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 4 is set"
	::= { dpsRTUv2 10004 }

dpsRTUv2p11004Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 4 is cleared"
	::= { dpsRTUv2 11004 }

dpsRTUv2p10005Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 5 is set"
	::= { dpsRTUv2 10005 }

dpsRTUv2p11005Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 5 is cleared"
	::= { dpsRTUv2 11005 }

dpsRTUv2p10006Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 6 is set"
	::= { dpsRTUv2 10006 }

dpsRTUv2p11006Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 6 is cleared"
	::= { dpsRTUv2 11006 }

dpsRTUv2p10007Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 7 is set"
	::= { dpsRTUv2 10007 }

dpsRTUv2p11007Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 7 is cleared"
	::= { dpsRTUv2 11007 }

dpsRTUv2p10008Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 8 is set"
	::= { dpsRTUv2 10008 }

dpsRTUv2p11008Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 8 is cleared"
	::= { dpsRTUv2 11008 }

dpsRTUv2p10009Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 9 is set"
	::= { dpsRTUv2 10009 }

dpsRTUv2p11009Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 9 is cleared"
	::= { dpsRTUv2 11009 }

dpsRTUv2p10010Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 10 is set"
	::= { dpsRTUv2 10010 }

dpsRTUv2p11010Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 10 is cleared"
	::= { dpsRTUv2 11010 }

dpsRTUv2p10011Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 11 is set"
	::= { dpsRTUv2 10011 }

dpsRTUv2p11011Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 11 is cleared"
	::= { dpsRTUv2 11011 }

dpsRTUv2p10012Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 12 is set"
	::= { dpsRTUv2 10012 }

dpsRTUv2p11012Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 12 is cleared"
	::= { dpsRTUv2 11012 }

dpsRTUv2p10013Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 13 is set"
	::= { dpsRTUv2 10013 }

dpsRTUv2p11013Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 13 is cleared"
	::= { dpsRTUv2 11013 }

dpsRTUv2p10014Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 14 is set"
	::= { dpsRTUv2 10014 }

dpsRTUv2p11014Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 14 is cleared"
	::= { dpsRTUv2 11014 }

dpsRTUv2p10015Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 15 is set"
	::= { dpsRTUv2 10015 }

dpsRTUv2p11015Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 15 is cleared"
	::= { dpsRTUv2 11015 }

dpsRTUv2p10016Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 16 is set"
	::= { dpsRTUv2 10016 }

dpsRTUv2p11016Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 16 is cleared"
	::= { dpsRTUv2 11016 }

dpsRTUv2p10017Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 17 is set"
	::= { dpsRTUv2 10017 }

dpsRTUv2p11017Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 17 is cleared"
	::= { dpsRTUv2 11017 }

dpsRTUv2p10018Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 18 is set"
	::= { dpsRTUv2 10018 }

dpsRTUv2p11018Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 18 is cleared"
	::= { dpsRTUv2 11018 }

dpsRTUv2p10019Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 19 is set"
	::= { dpsRTUv2 10019 }

dpsRTUv2p11019Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 19 is cleared"
	::= { dpsRTUv2 11019 }

dpsRTUv2p10020Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 20 is set"
	::= { dpsRTUv2 10020 }

dpsRTUv2p11020Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 20 is cleared"
	::= { dpsRTUv2 11020 }

dpsRTUv2p10021Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 21 is set"
	::= { dpsRTUv2 10021 }

dpsRTUv2p11021Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 21 is cleared"
	::= { dpsRTUv2 11021 }

dpsRTUv2p10022Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 22 is set"
	::= { dpsRTUv2 10022 }

dpsRTUv2p11022Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 22 is cleared"
	::= { dpsRTUv2 11022 }

dpsRTUv2p10023Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 23 is set"
	::= { dpsRTUv2 10023 }

dpsRTUv2p11023Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 23 is cleared"
	::= { dpsRTUv2 11023 }

dpsRTUv2p10024Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 24 is set"
	::= { dpsRTUv2 10024 }

dpsRTUv2p11024Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 24 is cleared"
	::= { dpsRTUv2 11024 }

dpsRTUv2p10025Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 25 is set"
	::= { dpsRTUv2 10025 }

dpsRTUv2p11025Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 25 is cleared"
	::= { dpsRTUv2 11025 }

dpsRTUv2p10026Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 26 is set"
	::= { dpsRTUv2 10026 }

dpsRTUv2p11026Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 26 is cleared"
	::= { dpsRTUv2 11026 }

dpsRTUv2p10027Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 27 is set"
	::= { dpsRTUv2 10027 }

dpsRTUv2p11027Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 27 is cleared"
	::= { dpsRTUv2 11027 }

dpsRTUv2p10028Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 28 is set"
	::= { dpsRTUv2 10028 }

dpsRTUv2p11028Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 28 is cleared"
	::= { dpsRTUv2 11028 }

dpsRTUv2p10029Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 29 is set"
	::= { dpsRTUv2 10029 }

dpsRTUv2p11029Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 29 is cleared"
	::= { dpsRTUv2 11029 }

dpsRTUv2p10030Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 30 is set"
	::= { dpsRTUv2 10030 }

dpsRTUv2p11030Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 30 is cleared"
	::= { dpsRTUv2 11030 }

dpsRTUv2p10031Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 31 is set"
	::= { dpsRTUv2 10031 }

dpsRTUv2p11031Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 31 is cleared"
	::= { dpsRTUv2 11031 }

dpsRTUv2p10032Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 32 is set"
	::= { dpsRTUv2 10032 }

dpsRTUv2p11032Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 32 is cleared"
	::= { dpsRTUv2 11032 }

dpsRTUv2p10033Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 33 is set"
	::= { dpsRTUv2 10033 }

dpsRTUv2p11033Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 33 is cleared"
	::= { dpsRTUv2 11033 }

dpsRTUv2p10034Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 34 is set"
	::= { dpsRTUv2 10034 }

dpsRTUv2p11034Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 34 is cleared"
	::= { dpsRTUv2 11034 }

dpsRTUv2p10035Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 35 is set"
	::= { dpsRTUv2 10035 }

dpsRTUv2p11035Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 35 is cleared"
	::= { dpsRTUv2 11035 }

dpsRTUv2p10036Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 36 is set"
	::= { dpsRTUv2 10036 }

dpsRTUv2p11036Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 36 is cleared"
	::= { dpsRTUv2 11036 }

dpsRTUv2p10037Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 37 is set"
	::= { dpsRTUv2 10037 }

dpsRTUv2p11037Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 37 is cleared"
	::= { dpsRTUv2 11037 }

dpsRTUv2p10038Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 38 is set"
	::= { dpsRTUv2 10038 }

dpsRTUv2p11038Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 38 is cleared"
	::= { dpsRTUv2 11038 }

dpsRTUv2p10039Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 39 is set"
	::= { dpsRTUv2 10039 }

dpsRTUv2p11039Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 39 is cleared"
	::= { dpsRTUv2 11039 }

dpsRTUv2p10040Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 40 is set"
	::= { dpsRTUv2 10040 }

dpsRTUv2p11040Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 40 is cleared"
	::= { dpsRTUv2 11040 }

dpsRTUv2p10041Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 41 is set"
	::= { dpsRTUv2 10041 }

dpsRTUv2p11041Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 41 is cleared"
	::= { dpsRTUv2 11041 }

dpsRTUv2p10042Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 42 is set"
	::= { dpsRTUv2 10042 }

dpsRTUv2p11042Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 42 is cleared"
	::= { dpsRTUv2 11042 }

dpsRTUv2p10043Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 43 is set"
	::= { dpsRTUv2 10043 }

dpsRTUv2p11043Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 43 is cleared"
	::= { dpsRTUv2 11043 }

dpsRTUv2p10044Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 44 is set"
	::= { dpsRTUv2 10044 }

dpsRTUv2p11044Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 44 is cleared"
	::= { dpsRTUv2 11044 }

dpsRTUv2p10045Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 45 is set"
	::= { dpsRTUv2 10045 }

dpsRTUv2p11045Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 45 is cleared"
	::= { dpsRTUv2 11045 }

dpsRTUv2p10046Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 46 is set"
	::= { dpsRTUv2 10046 }

dpsRTUv2p11046Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 46 is cleared"
	::= { dpsRTUv2 11046 }

dpsRTUv2p10047Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 47 is set"
	::= { dpsRTUv2 10047 }

dpsRTUv2p11047Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 47 is cleared"
	::= { dpsRTUv2 11047 }

dpsRTUv2p10048Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 48 is set"
	::= { dpsRTUv2 10048 }

dpsRTUv2p11048Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 48 is cleared"
	::= { dpsRTUv2 11048 }

dpsRTUv2p10049Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 49 is set"
	::= { dpsRTUv2 10049 }

dpsRTUv2p11049Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 49 is cleared"
	::= { dpsRTUv2 11049 }

dpsRTUv2p10050Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 50 is set"
	::= { dpsRTUv2 10050 }

dpsRTUv2p11050Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 50 is cleared"
	::= { dpsRTUv2 11050 }

dpsRTUv2p10051Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 51 is set"
	::= { dpsRTUv2 10051 }

dpsRTUv2p11051Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 51 is cleared"
	::= { dpsRTUv2 11051 }

dpsRTUv2p10052Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 52 is set"
	::= { dpsRTUv2 10052 }

dpsRTUv2p11052Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 52 is cleared"
	::= { dpsRTUv2 11052 }

dpsRTUv2p10053Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 53 is set"
	::= { dpsRTUv2 10053 }

dpsRTUv2p11053Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 53 is cleared"
	::= { dpsRTUv2 11053 }

dpsRTUv2p10054Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 54 is set"
	::= { dpsRTUv2 10054 }

dpsRTUv2p11054Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 54 is cleared"
	::= { dpsRTUv2 11054 }

dpsRTUv2p10055Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 55 is set"
	::= { dpsRTUv2 10055 }

dpsRTUv2p11055Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 55 is cleared"
	::= { dpsRTUv2 11055 }

dpsRTUv2p10056Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 56 is set"
	::= { dpsRTUv2 10056 }

dpsRTUv2p11056Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 56 is cleared"
	::= { dpsRTUv2 11056 }

dpsRTUv2p10057Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 57 is set"
	::= { dpsRTUv2 10057 }

dpsRTUv2p11057Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 57 is cleared"
	::= { dpsRTUv2 11057 }

dpsRTUv2p10058Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 58 is set"
	::= { dpsRTUv2 10058 }

dpsRTUv2p11058Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 58 is cleared"
	::= { dpsRTUv2 11058 }

dpsRTUv2p10059Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 59 is set"
	::= { dpsRTUv2 10059 }

dpsRTUv2p11059Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 59 is cleared"
	::= { dpsRTUv2 11059 }

dpsRTUv2p10060Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 60 is set"
	::= { dpsRTUv2 10060 }

dpsRTUv2p11060Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 60 is cleared"
	::= { dpsRTUv2 11060 }

dpsRTUv2p10061Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 61 is set"
	::= { dpsRTUv2 10061 }

dpsRTUv2p11061Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 61 is cleared"
	::= { dpsRTUv2 11061 }

dpsRTUv2p10062Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 62 is set"
	::= { dpsRTUv2 10062 }

dpsRTUv2p11062Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 62 is cleared"
	::= { dpsRTUv2 11062 }

dpsRTUv2p10063Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 63 is set"
	::= { dpsRTUv2 10063 }

dpsRTUv2p11063Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 63 is cleared"
	::= { dpsRTUv2 11063 }

dpsRTUv2p10064Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 64 is set"
	::= { dpsRTUv2 10064 }

dpsRTUv2p11064Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 1 point 64 is cleared"
	::= { dpsRTUv2 11064 }

dpsRTUv2p10065Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 1 is set"
	::= { dpsRTUv2 10065 }

dpsRTUv2p11065Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 1 is cleared"
	::= { dpsRTUv2 11065 }

dpsRTUv2p10066Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 2 is set"
	::= { dpsRTUv2 10066 }

dpsRTUv2p11066Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 2 is cleared"
	::= { dpsRTUv2 11066 }

dpsRTUv2p10067Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 3 is set"
	::= { dpsRTUv2 10067 }

dpsRTUv2p11067Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 3 is cleared"
	::= { dpsRTUv2 11067 }

dpsRTUv2p10068Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 4 is set"
	::= { dpsRTUv2 10068 }

dpsRTUv2p11068Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 4 is cleared"
	::= { dpsRTUv2 11068 }

dpsRTUv2p10069Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 5 is set"
	::= { dpsRTUv2 10069 }

dpsRTUv2p11069Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 5 is cleared"
	::= { dpsRTUv2 11069 }

dpsRTUv2p10070Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 6 is set"
	::= { dpsRTUv2 10070 }

dpsRTUv2p11070Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 6 is cleared"
	::= { dpsRTUv2 11070 }

dpsRTUv2p10071Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 7 is set"
	::= { dpsRTUv2 10071 }

dpsRTUv2p11071Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 7 is cleared"
	::= { dpsRTUv2 11071 }

dpsRTUv2p10072Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 8 is set"
	::= { dpsRTUv2 10072 }

dpsRTUv2p11072Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 8 is cleared"
	::= { dpsRTUv2 11072 }

dpsRTUv2p10073Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 9 is set"
	::= { dpsRTUv2 10073 }

dpsRTUv2p11073Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 9 is cleared"
	::= { dpsRTUv2 11073 }

dpsRTUv2p10074Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 10 is set"
	::= { dpsRTUv2 10074 }

dpsRTUv2p11074Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 10 is cleared"
	::= { dpsRTUv2 11074 }

dpsRTUv2p10075Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 11 is set"
	::= { dpsRTUv2 10075 }

dpsRTUv2p11075Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 11 is cleared"
	::= { dpsRTUv2 11075 }

dpsRTUv2p10076Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 12 is set"
	::= { dpsRTUv2 10076 }

dpsRTUv2p11076Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 12 is cleared"
	::= { dpsRTUv2 11076 }

dpsRTUv2p10077Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 13 is set"
	::= { dpsRTUv2 10077 }

dpsRTUv2p11077Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 13 is cleared"
	::= { dpsRTUv2 11077 }

dpsRTUv2p10078Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 14 is set"
	::= { dpsRTUv2 10078 }

dpsRTUv2p11078Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 14 is cleared"
	::= { dpsRTUv2 11078 }

dpsRTUv2p10079Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 15 is set"
	::= { dpsRTUv2 10079 }

dpsRTUv2p11079Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 15 is cleared"
	::= { dpsRTUv2 11079 }

dpsRTUv2p10080Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 16 is set"
	::= { dpsRTUv2 10080 }

dpsRTUv2p11080Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 16 is cleared"
	::= { dpsRTUv2 11080 }

dpsRTUv2p10081Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 17 is set"
	::= { dpsRTUv2 10081 }

dpsRTUv2p11081Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 17 is cleared"
	::= { dpsRTUv2 11081 }

dpsRTUv2p10082Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 18 is set"
	::= { dpsRTUv2 10082 }

dpsRTUv2p11082Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 18 is cleared"
	::= { dpsRTUv2 11082 }

dpsRTUv2p10083Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 19 is set"
	::= { dpsRTUv2 10083 }

dpsRTUv2p11083Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 19 is cleared"
	::= { dpsRTUv2 11083 }

dpsRTUv2p10084Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 20 is set"
	::= { dpsRTUv2 10084 }

dpsRTUv2p11084Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 20 is cleared"
	::= { dpsRTUv2 11084 }

dpsRTUv2p10085Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 21 is set"
	::= { dpsRTUv2 10085 }

dpsRTUv2p11085Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 21 is cleared"
	::= { dpsRTUv2 11085 }

dpsRTUv2p10086Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 22 is set"
	::= { dpsRTUv2 10086 }

dpsRTUv2p11086Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 22 is cleared"
	::= { dpsRTUv2 11086 }

dpsRTUv2p10087Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 23 is set"
	::= { dpsRTUv2 10087 }

dpsRTUv2p11087Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 23 is cleared"
	::= { dpsRTUv2 11087 }

dpsRTUv2p10088Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 24 is set"
	::= { dpsRTUv2 10088 }

dpsRTUv2p11088Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 24 is cleared"
	::= { dpsRTUv2 11088 }

dpsRTUv2p10089Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 25 is set"
	::= { dpsRTUv2 10089 }

dpsRTUv2p11089Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 25 is cleared"
	::= { dpsRTUv2 11089 }

dpsRTUv2p10090Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 26 is set"
	::= { dpsRTUv2 10090 }

dpsRTUv2p11090Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 26 is cleared"
	::= { dpsRTUv2 11090 }

dpsRTUv2p10091Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 27 is set"
	::= { dpsRTUv2 10091 }

dpsRTUv2p11091Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 27 is cleared"
	::= { dpsRTUv2 11091 }

dpsRTUv2p10092Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 28 is set"
	::= { dpsRTUv2 10092 }

dpsRTUv2p11092Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 28 is cleared"
	::= { dpsRTUv2 11092 }

dpsRTUv2p10093Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 29 is set"
	::= { dpsRTUv2 10093 }

dpsRTUv2p11093Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 29 is cleared"
	::= { dpsRTUv2 11093 }

dpsRTUv2p10094Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 30 is set"
	::= { dpsRTUv2 10094 }

dpsRTUv2p11094Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 30 is cleared"
	::= { dpsRTUv2 11094 }

dpsRTUv2p10095Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 31 is set"
	::= { dpsRTUv2 10095 }

dpsRTUv2p11095Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 31 is cleared"
	::= { dpsRTUv2 11095 }

dpsRTUv2p10096Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 32 is set"
	::= { dpsRTUv2 10096 }

dpsRTUv2p11096Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 32 is cleared"
	::= { dpsRTUv2 11096 }

dpsRTUv2p10097Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 33 is set"
	::= { dpsRTUv2 10097 }

dpsRTUv2p11097Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 33 is cleared"
	::= { dpsRTUv2 11097 }

dpsRTUv2p10098Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 34 is set"
	::= { dpsRTUv2 10098 }

dpsRTUv2p11098Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 34 is cleared"
	::= { dpsRTUv2 11098 }

dpsRTUv2p10099Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 35 is set"
	::= { dpsRTUv2 10099 }

dpsRTUv2p11099Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 35 is cleared"
	::= { dpsRTUv2 11099 }

dpsRTUv2p10100Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 36 is set"
	::= { dpsRTUv2 10100 }

dpsRTUv2p11100Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 36 is cleared"
	::= { dpsRTUv2 11100 }

dpsRTUv2p10101Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 37 is set"
	::= { dpsRTUv2 10101 }

dpsRTUv2p11101Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 37 is cleared"
	::= { dpsRTUv2 11101 }

dpsRTUv2p10102Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 38 is set"
	::= { dpsRTUv2 10102 }

dpsRTUv2p11102Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 38 is cleared"
	::= { dpsRTUv2 11102 }

dpsRTUv2p10103Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 39 is set"
	::= { dpsRTUv2 10103 }

dpsRTUv2p11103Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 39 is cleared"
	::= { dpsRTUv2 11103 }

dpsRTUv2p10104Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 40 is set"
	::= { dpsRTUv2 10104 }

dpsRTUv2p11104Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 40 is cleared"
	::= { dpsRTUv2 11104 }

dpsRTUv2p10105Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 41 is set"
	::= { dpsRTUv2 10105 }

dpsRTUv2p11105Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 41 is cleared"
	::= { dpsRTUv2 11105 }

dpsRTUv2p10106Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 42 is set"
	::= { dpsRTUv2 10106 }

dpsRTUv2p11106Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 42 is cleared"
	::= { dpsRTUv2 11106 }

dpsRTUv2p10107Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 43 is set"
	::= { dpsRTUv2 10107 }

dpsRTUv2p11107Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 43 is cleared"
	::= { dpsRTUv2 11107 }

dpsRTUv2p10108Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 44 is set"
	::= { dpsRTUv2 10108 }

dpsRTUv2p11108Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 44 is cleared"
	::= { dpsRTUv2 11108 }

dpsRTUv2p10109Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 45 is set"
	::= { dpsRTUv2 10109 }

dpsRTUv2p11109Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 45 is cleared"
	::= { dpsRTUv2 11109 }

dpsRTUv2p10110Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 46 is set"
	::= { dpsRTUv2 10110 }

dpsRTUv2p11110Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 46 is cleared"
	::= { dpsRTUv2 11110 }

dpsRTUv2p10111Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 47 is set"
	::= { dpsRTUv2 10111 }

dpsRTUv2p11111Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 47 is cleared"
	::= { dpsRTUv2 11111 }

dpsRTUv2p10112Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 48 is set"
	::= { dpsRTUv2 10112 }

dpsRTUv2p11112Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 48 is cleared"
	::= { dpsRTUv2 11112 }

dpsRTUv2p10113Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 49 is set"
	::= { dpsRTUv2 10113 }

dpsRTUv2p11113Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 49 is cleared"
	::= { dpsRTUv2 11113 }

dpsRTUv2p10114Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 50 is set"
	::= { dpsRTUv2 10114 }

dpsRTUv2p11114Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 50 is cleared"
	::= { dpsRTUv2 11114 }

dpsRTUv2p10115Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 51 is set"
	::= { dpsRTUv2 10115 }

dpsRTUv2p11115Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 51 is cleared"
	::= { dpsRTUv2 11115 }

dpsRTUv2p10116Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 52 is set"
	::= { dpsRTUv2 10116 }

dpsRTUv2p11116Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 52 is cleared"
	::= { dpsRTUv2 11116 }

dpsRTUv2p10117Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 53 is set"
	::= { dpsRTUv2 10117 }

dpsRTUv2p11117Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 53 is cleared"
	::= { dpsRTUv2 11117 }

dpsRTUv2p10118Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 54 is set"
	::= { dpsRTUv2 10118 }

dpsRTUv2p11118Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 54 is cleared"
	::= { dpsRTUv2 11118 }

dpsRTUv2p10119Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 55 is set"
	::= { dpsRTUv2 10119 }

dpsRTUv2p11119Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 55 is cleared"
	::= { dpsRTUv2 11119 }

dpsRTUv2p10120Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 56 is set"
	::= { dpsRTUv2 10120 }

dpsRTUv2p11120Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 56 is cleared"
	::= { dpsRTUv2 11120 }

dpsRTUv2p10121Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 57 is set"
	::= { dpsRTUv2 10121 }

dpsRTUv2p11121Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 57 is cleared"
	::= { dpsRTUv2 11121 }

dpsRTUv2p10122Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 58 is set"
	::= { dpsRTUv2 10122 }

dpsRTUv2p11122Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 58 is cleared"
	::= { dpsRTUv2 11122 }

dpsRTUv2p10123Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 59 is set"
	::= { dpsRTUv2 10123 }

dpsRTUv2p11123Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 59 is cleared"
	::= { dpsRTUv2 11123 }

dpsRTUv2p10124Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 60 is set"
	::= { dpsRTUv2 10124 }

dpsRTUv2p11124Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 60 is cleared"
	::= { dpsRTUv2 11124 }

dpsRTUv2p10125Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 61 is set"
	::= { dpsRTUv2 10125 }

dpsRTUv2p11125Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 61 is cleared"
	::= { dpsRTUv2 11125 }

dpsRTUv2p10126Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 62 is set"
	::= { dpsRTUv2 10126 }

dpsRTUv2p11126Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 62 is cleared"
	::= { dpsRTUv2 11126 }

dpsRTUv2p10127Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 63 is set"
	::= { dpsRTUv2 10127 }

dpsRTUv2p11127Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 63 is cleared"
	::= { dpsRTUv2 11127 }

dpsRTUv2p10128Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 64 is set"
	::= { dpsRTUv2 10128 }

dpsRTUv2p11128Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 2 point 64 is cleared"
	::= { dpsRTUv2 11128 }

dpsRTUv2p10129Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 1 is set"
	::= { dpsRTUv2 10129 }

dpsRTUv2p11129Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 1 is cleared"
	::= { dpsRTUv2 11129 }

dpsRTUv2p10130Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 2 is set"
	::= { dpsRTUv2 10130 }

dpsRTUv2p11130Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 2 is cleared"
	::= { dpsRTUv2 11130 }

dpsRTUv2p10131Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 3 is set"
	::= { dpsRTUv2 10131 }

dpsRTUv2p11131Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 3 is cleared"
	::= { dpsRTUv2 11131 }

dpsRTUv2p10132Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 4 is set"
	::= { dpsRTUv2 10132 }

dpsRTUv2p11132Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 4 is cleared"
	::= { dpsRTUv2 11132 }

dpsRTUv2p10133Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 5 is set"
	::= { dpsRTUv2 10133 }

dpsRTUv2p11133Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 5 is cleared"
	::= { dpsRTUv2 11133 }

dpsRTUv2p10134Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 6 is set"
	::= { dpsRTUv2 10134 }

dpsRTUv2p11134Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 6 is cleared"
	::= { dpsRTUv2 11134 }

dpsRTUv2p10135Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 7 is set"
	::= { dpsRTUv2 10135 }

dpsRTUv2p11135Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 7 is cleared"
	::= { dpsRTUv2 11135 }

dpsRTUv2p10136Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 8 is set"
	::= { dpsRTUv2 10136 }

dpsRTUv2p11136Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 8 is cleared"
	::= { dpsRTUv2 11136 }

dpsRTUv2p10137Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 9 is set"
	::= { dpsRTUv2 10137 }

dpsRTUv2p11137Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 9 is cleared"
	::= { dpsRTUv2 11137 }

dpsRTUv2p10138Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 10 is set"
	::= { dpsRTUv2 10138 }

dpsRTUv2p11138Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 10 is cleared"
	::= { dpsRTUv2 11138 }

dpsRTUv2p10139Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 11 is set"
	::= { dpsRTUv2 10139 }

dpsRTUv2p11139Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 11 is cleared"
	::= { dpsRTUv2 11139 }

dpsRTUv2p10140Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 12 is set"
	::= { dpsRTUv2 10140 }

dpsRTUv2p11140Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 12 is cleared"
	::= { dpsRTUv2 11140 }

dpsRTUv2p10141Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 13 is set"
	::= { dpsRTUv2 10141 }

dpsRTUv2p11141Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 13 is cleared"
	::= { dpsRTUv2 11141 }

dpsRTUv2p10142Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 14 is set"
	::= { dpsRTUv2 10142 }

dpsRTUv2p11142Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 14 is cleared"
	::= { dpsRTUv2 11142 }

dpsRTUv2p10143Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 15 is set"
	::= { dpsRTUv2 10143 }

dpsRTUv2p11143Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 15 is cleared"
	::= { dpsRTUv2 11143 }

dpsRTUv2p10144Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 16 is set"
	::= { dpsRTUv2 10144 }

dpsRTUv2p11144Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 16 is cleared"
	::= { dpsRTUv2 11144 }

dpsRTUv2p10145Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 17 is set"
	::= { dpsRTUv2 10145 }

dpsRTUv2p11145Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 17 is cleared"
	::= { dpsRTUv2 11145 }

dpsRTUv2p10146Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 18 is set"
	::= { dpsRTUv2 10146 }

dpsRTUv2p11146Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 18 is cleared"
	::= { dpsRTUv2 11146 }

dpsRTUv2p10147Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 19 is set"
	::= { dpsRTUv2 10147 }

dpsRTUv2p11147Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 19 is cleared"
	::= { dpsRTUv2 11147 }

dpsRTUv2p10148Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 20 is set"
	::= { dpsRTUv2 10148 }

dpsRTUv2p11148Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 20 is cleared"
	::= { dpsRTUv2 11148 }

dpsRTUv2p10149Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 21 is set"
	::= { dpsRTUv2 10149 }

dpsRTUv2p11149Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 21 is cleared"
	::= { dpsRTUv2 11149 }

dpsRTUv2p10150Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 22 is set"
	::= { dpsRTUv2 10150 }

dpsRTUv2p11150Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 22 is cleared"
	::= { dpsRTUv2 11150 }

dpsRTUv2p10151Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 23 is set"
	::= { dpsRTUv2 10151 }

dpsRTUv2p11151Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 23 is cleared"
	::= { dpsRTUv2 11151 }

dpsRTUv2p10152Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 24 is set"
	::= { dpsRTUv2 10152 }

dpsRTUv2p11152Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 24 is cleared"
	::= { dpsRTUv2 11152 }

dpsRTUv2p10153Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 25 is set"
	::= { dpsRTUv2 10153 }

dpsRTUv2p11153Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 25 is cleared"
	::= { dpsRTUv2 11153 }

dpsRTUv2p10154Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 26 is set"
	::= { dpsRTUv2 10154 }

dpsRTUv2p11154Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 26 is cleared"
	::= { dpsRTUv2 11154 }

dpsRTUv2p10155Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 27 is set"
	::= { dpsRTUv2 10155 }

dpsRTUv2p11155Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 27 is cleared"
	::= { dpsRTUv2 11155 }

dpsRTUv2p10156Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 28 is set"
	::= { dpsRTUv2 10156 }

dpsRTUv2p11156Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 28 is cleared"
	::= { dpsRTUv2 11156 }

dpsRTUv2p10157Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 29 is set"
	::= { dpsRTUv2 10157 }

dpsRTUv2p11157Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 29 is cleared"
	::= { dpsRTUv2 11157 }

dpsRTUv2p10158Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 30 is set"
	::= { dpsRTUv2 10158 }

dpsRTUv2p11158Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 30 is cleared"
	::= { dpsRTUv2 11158 }

dpsRTUv2p10159Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 31 is set"
	::= { dpsRTUv2 10159 }

dpsRTUv2p11159Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 31 is cleared"
	::= { dpsRTUv2 11159 }

dpsRTUv2p10160Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 32 is set"
	::= { dpsRTUv2 10160 }

dpsRTUv2p11160Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 32 is cleared"
	::= { dpsRTUv2 11160 }

dpsRTUv2p10161Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 33 is set"
	::= { dpsRTUv2 10161 }

dpsRTUv2p11161Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 33 is cleared"
	::= { dpsRTUv2 11161 }

dpsRTUv2p10162Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 34 is set"
	::= { dpsRTUv2 10162 }

dpsRTUv2p11162Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 34 is cleared"
	::= { dpsRTUv2 11162 }

dpsRTUv2p10163Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 35 is set"
	::= { dpsRTUv2 10163 }

dpsRTUv2p11163Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 35 is cleared"
	::= { dpsRTUv2 11163 }

dpsRTUv2p10164Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 36 is set"
	::= { dpsRTUv2 10164 }

dpsRTUv2p11164Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 36 is cleared"
	::= { dpsRTUv2 11164 }

dpsRTUv2p10165Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 37 is set"
	::= { dpsRTUv2 10165 }

dpsRTUv2p11165Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 37 is cleared"
	::= { dpsRTUv2 11165 }

dpsRTUv2p10166Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 38 is set"
	::= { dpsRTUv2 10166 }

dpsRTUv2p11166Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 38 is cleared"
	::= { dpsRTUv2 11166 }

dpsRTUv2p10167Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 39 is set"
	::= { dpsRTUv2 10167 }

dpsRTUv2p11167Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 39 is cleared"
	::= { dpsRTUv2 11167 }

dpsRTUv2p10168Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 40 is set"
	::= { dpsRTUv2 10168 }

dpsRTUv2p11168Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 40 is cleared"
	::= { dpsRTUv2 11168 }

dpsRTUv2p10169Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 41 is set"
	::= { dpsRTUv2 10169 }

dpsRTUv2p11169Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 41 is cleared"
	::= { dpsRTUv2 11169 }

dpsRTUv2p10170Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 42 is set"
	::= { dpsRTUv2 10170 }

dpsRTUv2p11170Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 42 is cleared"
	::= { dpsRTUv2 11170 }

dpsRTUv2p10171Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 43 is set"
	::= { dpsRTUv2 10171 }

dpsRTUv2p11171Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 43 is cleared"
	::= { dpsRTUv2 11171 }

dpsRTUv2p10172Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 44 is set"
	::= { dpsRTUv2 10172 }

dpsRTUv2p11172Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 44 is cleared"
	::= { dpsRTUv2 11172 }

dpsRTUv2p10173Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 45 is set"
	::= { dpsRTUv2 10173 }

dpsRTUv2p11173Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 45 is cleared"
	::= { dpsRTUv2 11173 }

dpsRTUv2p10174Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 46 is set"
	::= { dpsRTUv2 10174 }

dpsRTUv2p11174Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 46 is cleared"
	::= { dpsRTUv2 11174 }

dpsRTUv2p10175Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 47 is set"
	::= { dpsRTUv2 10175 }

dpsRTUv2p11175Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 47 is cleared"
	::= { dpsRTUv2 11175 }

dpsRTUv2p10176Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 48 is set"
	::= { dpsRTUv2 10176 }

dpsRTUv2p11176Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 48 is cleared"
	::= { dpsRTUv2 11176 }

dpsRTUv2p10177Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 49 is set"
	::= { dpsRTUv2 10177 }

dpsRTUv2p11177Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 49 is cleared"
	::= { dpsRTUv2 11177 }

dpsRTUv2p10178Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 50 is set"
	::= { dpsRTUv2 10178 }

dpsRTUv2p11178Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 50 is cleared"
	::= { dpsRTUv2 11178 }

dpsRTUv2p10179Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 51 is set"
	::= { dpsRTUv2 10179 }

dpsRTUv2p11179Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 51 is cleared"
	::= { dpsRTUv2 11179 }

dpsRTUv2p10180Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 52 is set"
	::= { dpsRTUv2 10180 }

dpsRTUv2p11180Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 52 is cleared"
	::= { dpsRTUv2 11180 }

dpsRTUv2p10181Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 53 is set"
	::= { dpsRTUv2 10181 }

dpsRTUv2p11181Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 53 is cleared"
	::= { dpsRTUv2 11181 }

dpsRTUv2p10182Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 54 is set"
	::= { dpsRTUv2 10182 }

dpsRTUv2p11182Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 54 is cleared"
	::= { dpsRTUv2 11182 }

dpsRTUv2p10183Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 55 is set"
	::= { dpsRTUv2 10183 }

dpsRTUv2p11183Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 55 is cleared"
	::= { dpsRTUv2 11183 }

dpsRTUv2p10184Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 56 is set"
	::= { dpsRTUv2 10184 }

dpsRTUv2p11184Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 56 is cleared"
	::= { dpsRTUv2 11184 }

dpsRTUv2p10185Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 57 is set"
	::= { dpsRTUv2 10185 }

dpsRTUv2p11185Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 57 is cleared"
	::= { dpsRTUv2 11185 }

dpsRTUv2p10186Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 58 is set"
	::= { dpsRTUv2 10186 }

dpsRTUv2p11186Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 58 is cleared"
	::= { dpsRTUv2 11186 }

dpsRTUv2p10187Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 59 is set"
	::= { dpsRTUv2 10187 }

dpsRTUv2p11187Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 59 is cleared"
	::= { dpsRTUv2 11187 }

dpsRTUv2p10188Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 60 is set"
	::= { dpsRTUv2 10188 }

dpsRTUv2p11188Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 60 is cleared"
	::= { dpsRTUv2 11188 }

dpsRTUv2p10189Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 61 is set"
	::= { dpsRTUv2 10189 }

dpsRTUv2p11189Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 61 is cleared"
	::= { dpsRTUv2 11189 }

dpsRTUv2p10190Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 62 is set"
	::= { dpsRTUv2 10190 }

dpsRTUv2p11190Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 62 is cleared"
	::= { dpsRTUv2 11190 }

dpsRTUv2p10191Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 63 is set"
	::= { dpsRTUv2 10191 }

dpsRTUv2p11191Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 63 is cleared"
	::= { dpsRTUv2 11191 }

dpsRTUv2p10192Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 64 is set"
	::= { dpsRTUv2 10192 }

dpsRTUv2p11192Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 3 point 64 is cleared"
	::= { dpsRTUv2 11192 }

dpsRTUv2p10193Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 1 is set"
	::= { dpsRTUv2 10193 }

dpsRTUv2p11193Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 1 is cleared"
	::= { dpsRTUv2 11193 }

dpsRTUv2p10194Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 2 is set"
	::= { dpsRTUv2 10194 }

dpsRTUv2p11194Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 2 is cleared"
	::= { dpsRTUv2 11194 }

dpsRTUv2p10195Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 3 is set"
	::= { dpsRTUv2 10195 }

dpsRTUv2p11195Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 3 is cleared"
	::= { dpsRTUv2 11195 }

dpsRTUv2p10196Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 4 is set"
	::= { dpsRTUv2 10196 }

dpsRTUv2p11196Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 4 is cleared"
	::= { dpsRTUv2 11196 }

dpsRTUv2p10197Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 5 is set"
	::= { dpsRTUv2 10197 }

dpsRTUv2p11197Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 5 is cleared"
	::= { dpsRTUv2 11197 }

dpsRTUv2p10198Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 6 is set"
	::= { dpsRTUv2 10198 }

dpsRTUv2p11198Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 6 is cleared"
	::= { dpsRTUv2 11198 }

dpsRTUv2p10199Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 7 is set"
	::= { dpsRTUv2 10199 }

dpsRTUv2p11199Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 7 is cleared"
	::= { dpsRTUv2 11199 }

dpsRTUv2p10200Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 8 is set"
	::= { dpsRTUv2 10200 }

dpsRTUv2p11200Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 8 is cleared"
	::= { dpsRTUv2 11200 }

dpsRTUv2p10201Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 9 is set"
	::= { dpsRTUv2 10201 }

dpsRTUv2p11201Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 9 is cleared"
	::= { dpsRTUv2 11201 }

dpsRTUv2p10202Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 10 is set"
	::= { dpsRTUv2 10202 }

dpsRTUv2p11202Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 10 is cleared"
	::= { dpsRTUv2 11202 }

dpsRTUv2p10203Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 11 is set"
	::= { dpsRTUv2 10203 }

dpsRTUv2p11203Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 11 is cleared"
	::= { dpsRTUv2 11203 }

dpsRTUv2p10204Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 12 is set"
	::= { dpsRTUv2 10204 }

dpsRTUv2p11204Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 12 is cleared"
	::= { dpsRTUv2 11204 }

dpsRTUv2p10205Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 13 is set"
	::= { dpsRTUv2 10205 }

dpsRTUv2p11205Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 13 is cleared"
	::= { dpsRTUv2 11205 }

dpsRTUv2p10206Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 14 is set"
	::= { dpsRTUv2 10206 }

dpsRTUv2p11206Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 14 is cleared"
	::= { dpsRTUv2 11206 }

dpsRTUv2p10207Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 15 is set"
	::= { dpsRTUv2 10207 }

dpsRTUv2p11207Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 15 is cleared"
	::= { dpsRTUv2 11207 }

dpsRTUv2p10208Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 16 is set"
	::= { dpsRTUv2 10208 }

dpsRTUv2p11208Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 16 is cleared"
	::= { dpsRTUv2 11208 }

dpsRTUv2p10209Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 17 is set"
	::= { dpsRTUv2 10209 }

dpsRTUv2p11209Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 17 is cleared"
	::= { dpsRTUv2 11209 }

dpsRTUv2p10210Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 18 is set"
	::= { dpsRTUv2 10210 }

dpsRTUv2p11210Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 18 is cleared"
	::= { dpsRTUv2 11210 }

dpsRTUv2p10211Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 19 is set"
	::= { dpsRTUv2 10211 }

dpsRTUv2p11211Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 19 is cleared"
	::= { dpsRTUv2 11211 }

dpsRTUv2p10212Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 20 is set"
	::= { dpsRTUv2 10212 }

dpsRTUv2p11212Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 20 is cleared"
	::= { dpsRTUv2 11212 }

dpsRTUv2p10213Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 21 is set"
	::= { dpsRTUv2 10213 }

dpsRTUv2p11213Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 21 is cleared"
	::= { dpsRTUv2 11213 }

dpsRTUv2p10214Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 22 is set"
	::= { dpsRTUv2 10214 }

dpsRTUv2p11214Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 22 is cleared"
	::= { dpsRTUv2 11214 }

dpsRTUv2p10215Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 23 is set"
	::= { dpsRTUv2 10215 }

dpsRTUv2p11215Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 23 is cleared"
	::= { dpsRTUv2 11215 }

dpsRTUv2p10216Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 24 is set"
	::= { dpsRTUv2 10216 }

dpsRTUv2p11216Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 24 is cleared"
	::= { dpsRTUv2 11216 }

dpsRTUv2p10217Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 25 is set"
	::= { dpsRTUv2 10217 }

dpsRTUv2p11217Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 25 is cleared"
	::= { dpsRTUv2 11217 }

dpsRTUv2p10218Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 26 is set"
	::= { dpsRTUv2 10218 }

dpsRTUv2p11218Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 26 is cleared"
	::= { dpsRTUv2 11218 }

dpsRTUv2p10219Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 27 is set"
	::= { dpsRTUv2 10219 }

dpsRTUv2p11219Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 27 is cleared"
	::= { dpsRTUv2 11219 }

dpsRTUv2p10220Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 28 is set"
	::= { dpsRTUv2 10220 }

dpsRTUv2p11220Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 28 is cleared"
	::= { dpsRTUv2 11220 }

dpsRTUv2p10221Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 29 is set"
	::= { dpsRTUv2 10221 }

dpsRTUv2p11221Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 29 is cleared"
	::= { dpsRTUv2 11221 }

dpsRTUv2p10222Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 30 is set"
	::= { dpsRTUv2 10222 }

dpsRTUv2p11222Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 30 is cleared"
	::= { dpsRTUv2 11222 }

dpsRTUv2p10223Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 31 is set"
	::= { dpsRTUv2 10223 }

dpsRTUv2p11223Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 31 is cleared"
	::= { dpsRTUv2 11223 }

dpsRTUv2p10224Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 32 is set"
	::= { dpsRTUv2 10224 }

dpsRTUv2p11224Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 32 is cleared"
	::= { dpsRTUv2 11224 }

dpsRTUv2p10225Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 33 is set"
	::= { dpsRTUv2 10225 }

dpsRTUv2p11225Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 33 is cleared"
	::= { dpsRTUv2 11225 }

dpsRTUv2p10226Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 34 is set"
	::= { dpsRTUv2 10226 }

dpsRTUv2p11226Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 34 is cleared"
	::= { dpsRTUv2 11226 }

dpsRTUv2p10227Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 35 is set"
	::= { dpsRTUv2 10227 }

dpsRTUv2p11227Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 35 is cleared"
	::= { dpsRTUv2 11227 }

dpsRTUv2p10228Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 36 is set"
	::= { dpsRTUv2 10228 }

dpsRTUv2p11228Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 36 is cleared"
	::= { dpsRTUv2 11228 }

dpsRTUv2p10229Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 37 is set"
	::= { dpsRTUv2 10229 }

dpsRTUv2p11229Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 37 is cleared"
	::= { dpsRTUv2 11229 }

dpsRTUv2p10230Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 38 is set"
	::= { dpsRTUv2 10230 }

dpsRTUv2p11230Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 38 is cleared"
	::= { dpsRTUv2 11230 }

dpsRTUv2p10231Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 39 is set"
	::= { dpsRTUv2 10231 }

dpsRTUv2p11231Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 39 is cleared"
	::= { dpsRTUv2 11231 }

dpsRTUv2p10232Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 40 is set"
	::= { dpsRTUv2 10232 }

dpsRTUv2p11232Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 40 is cleared"
	::= { dpsRTUv2 11232 }

dpsRTUv2p10233Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 41 is set"
	::= { dpsRTUv2 10233 }

dpsRTUv2p11233Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 41 is cleared"
	::= { dpsRTUv2 11233 }

dpsRTUv2p10234Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 42 is set"
	::= { dpsRTUv2 10234 }

dpsRTUv2p11234Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 42 is cleared"
	::= { dpsRTUv2 11234 }

dpsRTUv2p10235Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 43 is set"
	::= { dpsRTUv2 10235 }

dpsRTUv2p11235Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 43 is cleared"
	::= { dpsRTUv2 11235 }

dpsRTUv2p10236Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 44 is set"
	::= { dpsRTUv2 10236 }

dpsRTUv2p11236Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 44 is cleared"
	::= { dpsRTUv2 11236 }

dpsRTUv2p10237Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 45 is set"
	::= { dpsRTUv2 10237 }

dpsRTUv2p11237Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 45 is cleared"
	::= { dpsRTUv2 11237 }

dpsRTUv2p10238Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 46 is set"
	::= { dpsRTUv2 10238 }

dpsRTUv2p11238Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 46 is cleared"
	::= { dpsRTUv2 11238 }

dpsRTUv2p10239Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 47 is set"
	::= { dpsRTUv2 10239 }

dpsRTUv2p11239Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 47 is cleared"
	::= { dpsRTUv2 11239 }

dpsRTUv2p10240Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 48 is set"
	::= { dpsRTUv2 10240 }

dpsRTUv2p11240Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 48 is cleared"
	::= { dpsRTUv2 11240 }

dpsRTUv2p10241Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 49 is set"
	::= { dpsRTUv2 10241 }

dpsRTUv2p11241Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 49 is cleared"
	::= { dpsRTUv2 11241 }

dpsRTUv2p10242Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 50 is set"
	::= { dpsRTUv2 10242 }

dpsRTUv2p11242Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 50 is cleared"
	::= { dpsRTUv2 11242 }

dpsRTUv2p10243Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 51 is set"
	::= { dpsRTUv2 10243 }

dpsRTUv2p11243Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 51 is cleared"
	::= { dpsRTUv2 11243 }

dpsRTUv2p10244Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 52 is set"
	::= { dpsRTUv2 10244 }

dpsRTUv2p11244Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 52 is cleared"
	::= { dpsRTUv2 11244 }

dpsRTUv2p10245Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 53 is set"
	::= { dpsRTUv2 10245 }

dpsRTUv2p11245Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 53 is cleared"
	::= { dpsRTUv2 11245 }

dpsRTUv2p10246Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 54 is set"
	::= { dpsRTUv2 10246 }

dpsRTUv2p11246Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 54 is cleared"
	::= { dpsRTUv2 11246 }

dpsRTUv2p10247Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 55 is set"
	::= { dpsRTUv2 10247 }

dpsRTUv2p11247Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 55 is cleared"
	::= { dpsRTUv2 11247 }

dpsRTUv2p10248Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 56 is set"
	::= { dpsRTUv2 10248 }

dpsRTUv2p11248Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 56 is cleared"
	::= { dpsRTUv2 11248 }

dpsRTUv2p10249Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 57 is set"
	::= { dpsRTUv2 10249 }

dpsRTUv2p11249Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 57 is cleared"
	::= { dpsRTUv2 11249 }

dpsRTUv2p10250Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 58 is set"
	::= { dpsRTUv2 10250 }

dpsRTUv2p11250Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 58 is cleared"
	::= { dpsRTUv2 11250 }

dpsRTUv2p10251Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 59 is set"
	::= { dpsRTUv2 10251 }

dpsRTUv2p11251Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 59 is cleared"
	::= { dpsRTUv2 11251 }

dpsRTUv2p10252Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 60 is set"
	::= { dpsRTUv2 10252 }

dpsRTUv2p11252Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 60 is cleared"
	::= { dpsRTUv2 11252 }

dpsRTUv2p10253Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 61 is set"
	::= { dpsRTUv2 10253 }

dpsRTUv2p11253Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 61 is cleared"
	::= { dpsRTUv2 11253 }

dpsRTUv2p10254Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 62 is set"
	::= { dpsRTUv2 10254 }

dpsRTUv2p11254Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 62 is cleared"
	::= { dpsRTUv2 11254 }

dpsRTUv2p10255Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 63 is set"
	::= { dpsRTUv2 10255 }

dpsRTUv2p11255Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 63 is cleared"
	::= { dpsRTUv2 11255 }

dpsRTUv2p10256Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 64 is set"
	::= { dpsRTUv2 10256 }

dpsRTUv2p11256Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 4 point 64 is cleared"
	::= { dpsRTUv2 11256 }

dpsRTUv2p10257Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 1 is set"
	::= { dpsRTUv2 10257 }

dpsRTUv2p11257Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 1 is cleared"
	::= { dpsRTUv2 11257 }

dpsRTUv2p10258Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 2 is set"
	::= { dpsRTUv2 10258 }

dpsRTUv2p11258Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 2 is cleared"
	::= { dpsRTUv2 11258 }

dpsRTUv2p10259Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 3 is set"
	::= { dpsRTUv2 10259 }

dpsRTUv2p11259Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 3 is cleared"
	::= { dpsRTUv2 11259 }

dpsRTUv2p10260Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 4 is set"
	::= { dpsRTUv2 10260 }

dpsRTUv2p11260Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 4 is cleared"
	::= { dpsRTUv2 11260 }

dpsRTUv2p10261Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 5 is set"
	::= { dpsRTUv2 10261 }

dpsRTUv2p11261Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 5 is cleared"
	::= { dpsRTUv2 11261 }

dpsRTUv2p10262Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 6 is set"
	::= { dpsRTUv2 10262 }

dpsRTUv2p11262Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 6 is cleared"
	::= { dpsRTUv2 11262 }

dpsRTUv2p10263Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 7 is set"
	::= { dpsRTUv2 10263 }

dpsRTUv2p11263Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 7 is cleared"
	::= { dpsRTUv2 11263 }

dpsRTUv2p10264Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 8 is set"
	::= { dpsRTUv2 10264 }

dpsRTUv2p11264Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 8 is cleared"
	::= { dpsRTUv2 11264 }

dpsRTUv2p10265Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 9 is set"
	::= { dpsRTUv2 10265 }

dpsRTUv2p11265Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 9 is cleared"
	::= { dpsRTUv2 11265 }

dpsRTUv2p10266Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 10 is set"
	::= { dpsRTUv2 10266 }

dpsRTUv2p11266Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 10 is cleared"
	::= { dpsRTUv2 11266 }

dpsRTUv2p10267Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 11 is set"
	::= { dpsRTUv2 10267 }

dpsRTUv2p11267Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 11 is cleared"
	::= { dpsRTUv2 11267 }

dpsRTUv2p10268Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 12 is set"
	::= { dpsRTUv2 10268 }

dpsRTUv2p11268Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 12 is cleared"
	::= { dpsRTUv2 11268 }

dpsRTUv2p10269Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 13 is set"
	::= { dpsRTUv2 10269 }

dpsRTUv2p11269Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 13 is cleared"
	::= { dpsRTUv2 11269 }

dpsRTUv2p10270Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 14 is set"
	::= { dpsRTUv2 10270 }

dpsRTUv2p11270Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 14 is cleared"
	::= { dpsRTUv2 11270 }

dpsRTUv2p10271Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 15 is set"
	::= { dpsRTUv2 10271 }

dpsRTUv2p11271Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 15 is cleared"
	::= { dpsRTUv2 11271 }

dpsRTUv2p10272Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 16 is set"
	::= { dpsRTUv2 10272 }

dpsRTUv2p11272Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 16 is cleared"
	::= { dpsRTUv2 11272 }

dpsRTUv2p10273Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 17 is set"
	::= { dpsRTUv2 10273 }

dpsRTUv2p11273Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 17 is cleared"
	::= { dpsRTUv2 11273 }

dpsRTUv2p10274Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 18 is set"
	::= { dpsRTUv2 10274 }

dpsRTUv2p11274Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 18 is cleared"
	::= { dpsRTUv2 11274 }

dpsRTUv2p10275Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 19 is set"
	::= { dpsRTUv2 10275 }

dpsRTUv2p11275Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 19 is cleared"
	::= { dpsRTUv2 11275 }

dpsRTUv2p10276Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 20 is set"
	::= { dpsRTUv2 10276 }

dpsRTUv2p11276Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 20 is cleared"
	::= { dpsRTUv2 11276 }

dpsRTUv2p10277Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 21 is set"
	::= { dpsRTUv2 10277 }

dpsRTUv2p11277Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 21 is cleared"
	::= { dpsRTUv2 11277 }

dpsRTUv2p10278Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 22 is set"
	::= { dpsRTUv2 10278 }

dpsRTUv2p11278Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 22 is cleared"
	::= { dpsRTUv2 11278 }

dpsRTUv2p10279Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 23 is set"
	::= { dpsRTUv2 10279 }

dpsRTUv2p11279Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 23 is cleared"
	::= { dpsRTUv2 11279 }

dpsRTUv2p10280Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 24 is set"
	::= { dpsRTUv2 10280 }

dpsRTUv2p11280Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 24 is cleared"
	::= { dpsRTUv2 11280 }

dpsRTUv2p10281Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 25 is set"
	::= { dpsRTUv2 10281 }

dpsRTUv2p11281Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 25 is cleared"
	::= { dpsRTUv2 11281 }

dpsRTUv2p10282Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 26 is set"
	::= { dpsRTUv2 10282 }

dpsRTUv2p11282Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 26 is cleared"
	::= { dpsRTUv2 11282 }

dpsRTUv2p10283Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 27 is set"
	::= { dpsRTUv2 10283 }

dpsRTUv2p11283Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 27 is cleared"
	::= { dpsRTUv2 11283 }

dpsRTUv2p10284Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 28 is set"
	::= { dpsRTUv2 10284 }

dpsRTUv2p11284Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 28 is cleared"
	::= { dpsRTUv2 11284 }

dpsRTUv2p10285Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 29 is set"
	::= { dpsRTUv2 10285 }

dpsRTUv2p11285Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 29 is cleared"
	::= { dpsRTUv2 11285 }

dpsRTUv2p10286Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 30 is set"
	::= { dpsRTUv2 10286 }

dpsRTUv2p11286Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 30 is cleared"
	::= { dpsRTUv2 11286 }

dpsRTUv2p10287Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 31 is set"
	::= { dpsRTUv2 10287 }

dpsRTUv2p11287Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 31 is cleared"
	::= { dpsRTUv2 11287 }

dpsRTUv2p10288Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 32 is set"
	::= { dpsRTUv2 10288 }

dpsRTUv2p11288Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 32 is cleared"
	::= { dpsRTUv2 11288 }

dpsRTUv2p10289Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 33 is set"
	::= { dpsRTUv2 10289 }

dpsRTUv2p11289Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 33 is cleared"
	::= { dpsRTUv2 11289 }

dpsRTUv2p10290Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 34 is set"
	::= { dpsRTUv2 10290 }

dpsRTUv2p11290Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 34 is cleared"
	::= { dpsRTUv2 11290 }

dpsRTUv2p10291Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 35 is set"
	::= { dpsRTUv2 10291 }

dpsRTUv2p11291Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 35 is cleared"
	::= { dpsRTUv2 11291 }

dpsRTUv2p10292Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 36 is set"
	::= { dpsRTUv2 10292 }

dpsRTUv2p11292Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 36 is cleared"
	::= { dpsRTUv2 11292 }

dpsRTUv2p10293Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 37 is set"
	::= { dpsRTUv2 10293 }

dpsRTUv2p11293Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 37 is cleared"
	::= { dpsRTUv2 11293 }

dpsRTUv2p10294Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 38 is set"
	::= { dpsRTUv2 10294 }

dpsRTUv2p11294Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 38 is cleared"
	::= { dpsRTUv2 11294 }

dpsRTUv2p10295Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 39 is set"
	::= { dpsRTUv2 10295 }

dpsRTUv2p11295Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 39 is cleared"
	::= { dpsRTUv2 11295 }

dpsRTUv2p10296Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 40 is set"
	::= { dpsRTUv2 10296 }

dpsRTUv2p11296Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 40 is cleared"
	::= { dpsRTUv2 11296 }

dpsRTUv2p10297Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 41 is set"
	::= { dpsRTUv2 10297 }

dpsRTUv2p11297Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 41 is cleared"
	::= { dpsRTUv2 11297 }

dpsRTUv2p10298Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 42 is set"
	::= { dpsRTUv2 10298 }

dpsRTUv2p11298Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 42 is cleared"
	::= { dpsRTUv2 11298 }

dpsRTUv2p10299Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 43 is set"
	::= { dpsRTUv2 10299 }

dpsRTUv2p11299Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 43 is cleared"
	::= { dpsRTUv2 11299 }

dpsRTUv2p10300Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 44 is set"
	::= { dpsRTUv2 10300 }

dpsRTUv2p11300Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 44 is cleared"
	::= { dpsRTUv2 11300 }

dpsRTUv2p10301Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 45 is set"
	::= { dpsRTUv2 10301 }

dpsRTUv2p11301Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 45 is cleared"
	::= { dpsRTUv2 11301 }

dpsRTUv2p10302Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 46 is set"
	::= { dpsRTUv2 10302 }

dpsRTUv2p11302Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 46 is cleared"
	::= { dpsRTUv2 11302 }

dpsRTUv2p10303Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 47 is set"
	::= { dpsRTUv2 10303 }

dpsRTUv2p11303Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 47 is cleared"
	::= { dpsRTUv2 11303 }

dpsRTUv2p10304Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 48 is set"
	::= { dpsRTUv2 10304 }

dpsRTUv2p11304Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 48 is cleared"
	::= { dpsRTUv2 11304 }

dpsRTUv2p10305Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 49 is set"
	::= { dpsRTUv2 10305 }

dpsRTUv2p11305Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 49 is cleared"
	::= { dpsRTUv2 11305 }

dpsRTUv2p10306Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 50 is set"
	::= { dpsRTUv2 10306 }

dpsRTUv2p11306Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 50 is cleared"
	::= { dpsRTUv2 11306 }

dpsRTUv2p10307Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 51 is set"
	::= { dpsRTUv2 10307 }

dpsRTUv2p11307Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 51 is cleared"
	::= { dpsRTUv2 11307 }

dpsRTUv2p10308Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 52 is set"
	::= { dpsRTUv2 10308 }

dpsRTUv2p11308Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 52 is cleared"
	::= { dpsRTUv2 11308 }

dpsRTUv2p10309Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 53 is set"
	::= { dpsRTUv2 10309 }

dpsRTUv2p11309Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 53 is cleared"
	::= { dpsRTUv2 11309 }

dpsRTUv2p10310Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 54 is set"
	::= { dpsRTUv2 10310 }

dpsRTUv2p11310Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 54 is cleared"
	::= { dpsRTUv2 11310 }

dpsRTUv2p10311Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 55 is set"
	::= { dpsRTUv2 10311 }

dpsRTUv2p11311Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 55 is cleared"
	::= { dpsRTUv2 11311 }

dpsRTUv2p10312Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 56 is set"
	::= { dpsRTUv2 10312 }

dpsRTUv2p11312Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 56 is cleared"
	::= { dpsRTUv2 11312 }

dpsRTUv2p10313Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 57 is set"
	::= { dpsRTUv2 10313 }

dpsRTUv2p11313Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 57 is cleared"
	::= { dpsRTUv2 11313 }

dpsRTUv2p10314Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 58 is set"
	::= { dpsRTUv2 10314 }

dpsRTUv2p11314Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 58 is cleared"
	::= { dpsRTUv2 11314 }

dpsRTUv2p10315Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 59 is set"
	::= { dpsRTUv2 10315 }

dpsRTUv2p11315Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 59 is cleared"
	::= { dpsRTUv2 11315 }

dpsRTUv2p10316Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 60 is set"
	::= { dpsRTUv2 10316 }

dpsRTUv2p11316Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 60 is cleared"
	::= { dpsRTUv2 11316 }

dpsRTUv2p10317Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 61 is set"
	::= { dpsRTUv2 10317 }

dpsRTUv2p11317Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 61 is cleared"
	::= { dpsRTUv2 11317 }

dpsRTUv2p10318Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 62 is set"
	::= { dpsRTUv2 10318 }

dpsRTUv2p11318Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 62 is cleared"
	::= { dpsRTUv2 11318 }

dpsRTUv2p10319Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 63 is set"
	::= { dpsRTUv2 10319 }

dpsRTUv2p11319Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 63 is cleared"
	::= { dpsRTUv2 11319 }

dpsRTUv2p10320Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 64 is set"
	::= { dpsRTUv2 10320 }

dpsRTUv2p11320Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 5 point 64 is cleared"
	::= { dpsRTUv2 11320 }

dpsRTUv2p10321Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 1 is set"
	::= { dpsRTUv2 10321 }

dpsRTUv2p11321Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 1 is cleared"
	::= { dpsRTUv2 11321 }

dpsRTUv2p10322Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 2 is set"
	::= { dpsRTUv2 10322 }

dpsRTUv2p11322Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 2 is cleared"
	::= { dpsRTUv2 11322 }

dpsRTUv2p10323Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 3 is set"
	::= { dpsRTUv2 10323 }

dpsRTUv2p11323Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 3 is cleared"
	::= { dpsRTUv2 11323 }

dpsRTUv2p10324Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 4 is set"
	::= { dpsRTUv2 10324 }

dpsRTUv2p11324Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 4 is cleared"
	::= { dpsRTUv2 11324 }

dpsRTUv2p10325Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 5 is set"
	::= { dpsRTUv2 10325 }

dpsRTUv2p11325Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 5 is cleared"
	::= { dpsRTUv2 11325 }

dpsRTUv2p10326Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 6 is set"
	::= { dpsRTUv2 10326 }

dpsRTUv2p11326Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 6 is cleared"
	::= { dpsRTUv2 11326 }

dpsRTUv2p10327Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 7 is set"
	::= { dpsRTUv2 10327 }

dpsRTUv2p11327Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 7 is cleared"
	::= { dpsRTUv2 11327 }

dpsRTUv2p10328Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 8 is set"
	::= { dpsRTUv2 10328 }

dpsRTUv2p11328Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 8 is cleared"
	::= { dpsRTUv2 11328 }

dpsRTUv2p10329Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 9 is set"
	::= { dpsRTUv2 10329 }

dpsRTUv2p11329Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 9 is cleared"
	::= { dpsRTUv2 11329 }

dpsRTUv2p10330Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 10 is set"
	::= { dpsRTUv2 10330 }

dpsRTUv2p11330Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 10 is cleared"
	::= { dpsRTUv2 11330 }

dpsRTUv2p10331Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 11 is set"
	::= { dpsRTUv2 10331 }

dpsRTUv2p11331Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 11 is cleared"
	::= { dpsRTUv2 11331 }

dpsRTUv2p10332Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 12 is set"
	::= { dpsRTUv2 10332 }

dpsRTUv2p11332Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 12 is cleared"
	::= { dpsRTUv2 11332 }

dpsRTUv2p10333Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 13 is set"
	::= { dpsRTUv2 10333 }

dpsRTUv2p11333Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 13 is cleared"
	::= { dpsRTUv2 11333 }

dpsRTUv2p10334Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 14 is set"
	::= { dpsRTUv2 10334 }

dpsRTUv2p11334Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 14 is cleared"
	::= { dpsRTUv2 11334 }

dpsRTUv2p10335Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 15 is set"
	::= { dpsRTUv2 10335 }

dpsRTUv2p11335Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 15 is cleared"
	::= { dpsRTUv2 11335 }

dpsRTUv2p10336Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 16 is set"
	::= { dpsRTUv2 10336 }

dpsRTUv2p11336Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 16 is cleared"
	::= { dpsRTUv2 11336 }

dpsRTUv2p10337Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 17 is set"
	::= { dpsRTUv2 10337 }

dpsRTUv2p11337Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 17 is cleared"
	::= { dpsRTUv2 11337 }

dpsRTUv2p10338Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 18 is set"
	::= { dpsRTUv2 10338 }

dpsRTUv2p11338Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 18 is cleared"
	::= { dpsRTUv2 11338 }

dpsRTUv2p10339Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 19 is set"
	::= { dpsRTUv2 10339 }

dpsRTUv2p11339Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 19 is cleared"
	::= { dpsRTUv2 11339 }

dpsRTUv2p10340Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 20 is set"
	::= { dpsRTUv2 10340 }

dpsRTUv2p11340Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 20 is cleared"
	::= { dpsRTUv2 11340 }

dpsRTUv2p10341Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 21 is set"
	::= { dpsRTUv2 10341 }

dpsRTUv2p11341Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 21 is cleared"
	::= { dpsRTUv2 11341 }

dpsRTUv2p10342Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 22 is set"
	::= { dpsRTUv2 10342 }

dpsRTUv2p11342Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 22 is cleared"
	::= { dpsRTUv2 11342 }

dpsRTUv2p10343Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 23 is set"
	::= { dpsRTUv2 10343 }

dpsRTUv2p11343Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 23 is cleared"
	::= { dpsRTUv2 11343 }

dpsRTUv2p10344Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 24 is set"
	::= { dpsRTUv2 10344 }

dpsRTUv2p11344Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 24 is cleared"
	::= { dpsRTUv2 11344 }

dpsRTUv2p10345Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 25 is set"
	::= { dpsRTUv2 10345 }

dpsRTUv2p11345Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 25 is cleared"
	::= { dpsRTUv2 11345 }

dpsRTUv2p10346Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 26 is set"
	::= { dpsRTUv2 10346 }

dpsRTUv2p11346Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 26 is cleared"
	::= { dpsRTUv2 11346 }

dpsRTUv2p10347Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 27 is set"
	::= { dpsRTUv2 10347 }

dpsRTUv2p11347Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 27 is cleared"
	::= { dpsRTUv2 11347 }

dpsRTUv2p10348Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 28 is set"
	::= { dpsRTUv2 10348 }

dpsRTUv2p11348Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 28 is cleared"
	::= { dpsRTUv2 11348 }

dpsRTUv2p10349Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 29 is set"
	::= { dpsRTUv2 10349 }

dpsRTUv2p11349Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 29 is cleared"
	::= { dpsRTUv2 11349 }

dpsRTUv2p10350Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 30 is set"
	::= { dpsRTUv2 10350 }

dpsRTUv2p11350Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 30 is cleared"
	::= { dpsRTUv2 11350 }

dpsRTUv2p10351Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 31 is set"
	::= { dpsRTUv2 10351 }

dpsRTUv2p11351Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 31 is cleared"
	::= { dpsRTUv2 11351 }

dpsRTUv2p10352Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 32 is set"
	::= { dpsRTUv2 10352 }

dpsRTUv2p11352Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 32 is cleared"
	::= { dpsRTUv2 11352 }

dpsRTUv2p10353Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 33 is set"
	::= { dpsRTUv2 10353 }

dpsRTUv2p11353Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 33 is cleared"
	::= { dpsRTUv2 11353 }

dpsRTUv2p10354Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 34 is set"
	::= { dpsRTUv2 10354 }

dpsRTUv2p11354Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 34 is cleared"
	::= { dpsRTUv2 11354 }

dpsRTUv2p10355Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 35 is set"
	::= { dpsRTUv2 10355 }

dpsRTUv2p11355Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 35 is cleared"
	::= { dpsRTUv2 11355 }

dpsRTUv2p10356Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 36 is set"
	::= { dpsRTUv2 10356 }

dpsRTUv2p11356Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 36 is cleared"
	::= { dpsRTUv2 11356 }

dpsRTUv2p10357Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 37 is set"
	::= { dpsRTUv2 10357 }

dpsRTUv2p11357Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 37 is cleared"
	::= { dpsRTUv2 11357 }

dpsRTUv2p10358Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 38 is set"
	::= { dpsRTUv2 10358 }

dpsRTUv2p11358Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 38 is cleared"
	::= { dpsRTUv2 11358 }

dpsRTUv2p10359Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 39 is set"
	::= { dpsRTUv2 10359 }

dpsRTUv2p11359Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 39 is cleared"
	::= { dpsRTUv2 11359 }

dpsRTUv2p10360Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 40 is set"
	::= { dpsRTUv2 10360 }

dpsRTUv2p11360Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 40 is cleared"
	::= { dpsRTUv2 11360 }

dpsRTUv2p10361Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 41 is set"
	::= { dpsRTUv2 10361 }

dpsRTUv2p11361Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 41 is cleared"
	::= { dpsRTUv2 11361 }

dpsRTUv2p10362Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 42 is set"
	::= { dpsRTUv2 10362 }

dpsRTUv2p11362Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 42 is cleared"
	::= { dpsRTUv2 11362 }

dpsRTUv2p10363Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 43 is set"
	::= { dpsRTUv2 10363 }

dpsRTUv2p11363Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 43 is cleared"
	::= { dpsRTUv2 11363 }

dpsRTUv2p10364Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 44 is set"
	::= { dpsRTUv2 10364 }

dpsRTUv2p11364Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 44 is cleared"
	::= { dpsRTUv2 11364 }

dpsRTUv2p10365Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 45 is set"
	::= { dpsRTUv2 10365 }

dpsRTUv2p11365Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 45 is cleared"
	::= { dpsRTUv2 11365 }

dpsRTUv2p10366Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 46 is set"
	::= { dpsRTUv2 10366 }

dpsRTUv2p11366Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 46 is cleared"
	::= { dpsRTUv2 11366 }

dpsRTUv2p10367Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 47 is set"
	::= { dpsRTUv2 10367 }

dpsRTUv2p11367Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 47 is cleared"
	::= { dpsRTUv2 11367 }

dpsRTUv2p10368Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 48 is set"
	::= { dpsRTUv2 10368 }

dpsRTUv2p11368Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 48 is cleared"
	::= { dpsRTUv2 11368 }

dpsRTUv2p10369Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 49 is set"
	::= { dpsRTUv2 10369 }

dpsRTUv2p11369Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 49 is cleared"
	::= { dpsRTUv2 11369 }

dpsRTUv2p10370Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 50 is set"
	::= { dpsRTUv2 10370 }

dpsRTUv2p11370Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 50 is cleared"
	::= { dpsRTUv2 11370 }

dpsRTUv2p10371Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 51 is set"
	::= { dpsRTUv2 10371 }

dpsRTUv2p11371Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 51 is cleared"
	::= { dpsRTUv2 11371 }

dpsRTUv2p10372Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 52 is set"
	::= { dpsRTUv2 10372 }

dpsRTUv2p11372Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 52 is cleared"
	::= { dpsRTUv2 11372 }

dpsRTUv2p10373Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 53 is set"
	::= { dpsRTUv2 10373 }

dpsRTUv2p11373Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 53 is cleared"
	::= { dpsRTUv2 11373 }

dpsRTUv2p10374Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 54 is set"
	::= { dpsRTUv2 10374 }

dpsRTUv2p11374Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 54 is cleared"
	::= { dpsRTUv2 11374 }

dpsRTUv2p10375Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 55 is set"
	::= { dpsRTUv2 10375 }

dpsRTUv2p11375Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 55 is cleared"
	::= { dpsRTUv2 11375 }

dpsRTUv2p10376Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 56 is set"
	::= { dpsRTUv2 10376 }

dpsRTUv2p11376Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 56 is cleared"
	::= { dpsRTUv2 11376 }

dpsRTUv2p10377Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 57 is set"
	::= { dpsRTUv2 10377 }

dpsRTUv2p11377Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 57 is cleared"
	::= { dpsRTUv2 11377 }

dpsRTUv2p10378Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 58 is set"
	::= { dpsRTUv2 10378 }

dpsRTUv2p11378Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 58 is cleared"
	::= { dpsRTUv2 11378 }

dpsRTUv2p10379Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 59 is set"
	::= { dpsRTUv2 10379 }

dpsRTUv2p11379Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 59 is cleared"
	::= { dpsRTUv2 11379 }

dpsRTUv2p10380Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 60 is set"
	::= { dpsRTUv2 10380 }

dpsRTUv2p11380Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 60 is cleared"
	::= { dpsRTUv2 11380 }

dpsRTUv2p10381Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 61 is set"
	::= { dpsRTUv2 10381 }

dpsRTUv2p11381Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 61 is cleared"
	::= { dpsRTUv2 11381 }

dpsRTUv2p10382Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 62 is set"
	::= { dpsRTUv2 10382 }

dpsRTUv2p11382Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 62 is cleared"
	::= { dpsRTUv2 11382 }

dpsRTUv2p10383Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 63 is set"
	::= { dpsRTUv2 10383 }

dpsRTUv2p11383Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 63 is cleared"
	::= { dpsRTUv2 11383 }

dpsRTUv2p10384Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 64 is set"
	::= { dpsRTUv2 10384 }

dpsRTUv2p11384Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 6 point 64 is cleared"
	::= { dpsRTUv2 11384 }

dpsRTUv2p10385Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 1 is set"
	::= { dpsRTUv2 10385 }

dpsRTUv2p11385Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 1 is cleared"
	::= { dpsRTUv2 11385 }

dpsRTUv2p10386Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 2 is set"
	::= { dpsRTUv2 10386 }

dpsRTUv2p11386Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 2 is cleared"
	::= { dpsRTUv2 11386 }

dpsRTUv2p10387Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 3 is set"
	::= { dpsRTUv2 10387 }

dpsRTUv2p11387Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 3 is cleared"
	::= { dpsRTUv2 11387 }

dpsRTUv2p10388Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 4 is set"
	::= { dpsRTUv2 10388 }

dpsRTUv2p11388Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 4 is cleared"
	::= { dpsRTUv2 11388 }

dpsRTUv2p10389Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 5 is set"
	::= { dpsRTUv2 10389 }

dpsRTUv2p11389Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 5 is cleared"
	::= { dpsRTUv2 11389 }

dpsRTUv2p10390Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 6 is set"
	::= { dpsRTUv2 10390 }

dpsRTUv2p11390Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 6 is cleared"
	::= { dpsRTUv2 11390 }

dpsRTUv2p10391Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 7 is set"
	::= { dpsRTUv2 10391 }

dpsRTUv2p11391Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 7 is cleared"
	::= { dpsRTUv2 11391 }

dpsRTUv2p10392Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 8 is set"
	::= { dpsRTUv2 10392 }

dpsRTUv2p11392Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 8 is cleared"
	::= { dpsRTUv2 11392 }

dpsRTUv2p10393Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 9 is set"
	::= { dpsRTUv2 10393 }

dpsRTUv2p11393Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 9 is cleared"
	::= { dpsRTUv2 11393 }

dpsRTUv2p10394Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 10 is set"
	::= { dpsRTUv2 10394 }

dpsRTUv2p11394Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 10 is cleared"
	::= { dpsRTUv2 11394 }

dpsRTUv2p10395Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 11 is set"
	::= { dpsRTUv2 10395 }

dpsRTUv2p11395Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 11 is cleared"
	::= { dpsRTUv2 11395 }

dpsRTUv2p10396Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 12 is set"
	::= { dpsRTUv2 10396 }

dpsRTUv2p11396Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 12 is cleared"
	::= { dpsRTUv2 11396 }

dpsRTUv2p10397Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 13 is set"
	::= { dpsRTUv2 10397 }

dpsRTUv2p11397Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 13 is cleared"
	::= { dpsRTUv2 11397 }

dpsRTUv2p10398Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 14 is set"
	::= { dpsRTUv2 10398 }

dpsRTUv2p11398Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 14 is cleared"
	::= { dpsRTUv2 11398 }

dpsRTUv2p10399Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 15 is set"
	::= { dpsRTUv2 10399 }

dpsRTUv2p11399Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 15 is cleared"
	::= { dpsRTUv2 11399 }

dpsRTUv2p10400Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 16 is set"
	::= { dpsRTUv2 10400 }

dpsRTUv2p11400Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 16 is cleared"
	::= { dpsRTUv2 11400 }

dpsRTUv2p10401Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 17 is set"
	::= { dpsRTUv2 10401 }

dpsRTUv2p11401Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 17 is cleared"
	::= { dpsRTUv2 11401 }

dpsRTUv2p10402Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 18 is set"
	::= { dpsRTUv2 10402 }

dpsRTUv2p11402Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 18 is cleared"
	::= { dpsRTUv2 11402 }

dpsRTUv2p10403Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 19 is set"
	::= { dpsRTUv2 10403 }

dpsRTUv2p11403Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 19 is cleared"
	::= { dpsRTUv2 11403 }

dpsRTUv2p10404Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 20 is set"
	::= { dpsRTUv2 10404 }

dpsRTUv2p11404Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 20 is cleared"
	::= { dpsRTUv2 11404 }

dpsRTUv2p10405Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 21 is set"
	::= { dpsRTUv2 10405 }

dpsRTUv2p11405Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 21 is cleared"
	::= { dpsRTUv2 11405 }

dpsRTUv2p10406Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 22 is set"
	::= { dpsRTUv2 10406 }

dpsRTUv2p11406Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 22 is cleared"
	::= { dpsRTUv2 11406 }

dpsRTUv2p10407Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 23 is set"
	::= { dpsRTUv2 10407 }

dpsRTUv2p11407Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 23 is cleared"
	::= { dpsRTUv2 11407 }

dpsRTUv2p10408Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 24 is set"
	::= { dpsRTUv2 10408 }

dpsRTUv2p11408Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 24 is cleared"
	::= { dpsRTUv2 11408 }

dpsRTUv2p10409Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 25 is set"
	::= { dpsRTUv2 10409 }

dpsRTUv2p11409Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 25 is cleared"
	::= { dpsRTUv2 11409 }

dpsRTUv2p10410Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 26 is set"
	::= { dpsRTUv2 10410 }

dpsRTUv2p11410Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 26 is cleared"
	::= { dpsRTUv2 11410 }

dpsRTUv2p10411Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 27 is set"
	::= { dpsRTUv2 10411 }

dpsRTUv2p11411Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 27 is cleared"
	::= { dpsRTUv2 11411 }

dpsRTUv2p10412Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 28 is set"
	::= { dpsRTUv2 10412 }

dpsRTUv2p11412Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 28 is cleared"
	::= { dpsRTUv2 11412 }

dpsRTUv2p10413Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 29 is set"
	::= { dpsRTUv2 10413 }

dpsRTUv2p11413Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 29 is cleared"
	::= { dpsRTUv2 11413 }

dpsRTUv2p10414Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 30 is set"
	::= { dpsRTUv2 10414 }

dpsRTUv2p11414Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 30 is cleared"
	::= { dpsRTUv2 11414 }

dpsRTUv2p10415Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 31 is set"
	::= { dpsRTUv2 10415 }

dpsRTUv2p11415Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 31 is cleared"
	::= { dpsRTUv2 11415 }

dpsRTUv2p10416Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 32 is set"
	::= { dpsRTUv2 10416 }

dpsRTUv2p11416Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 32 is cleared"
	::= { dpsRTUv2 11416 }

dpsRTUv2p10417Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 33 is set"
	::= { dpsRTUv2 10417 }

dpsRTUv2p11417Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 33 is cleared"
	::= { dpsRTUv2 11417 }

dpsRTUv2p10418Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 34 is set"
	::= { dpsRTUv2 10418 }

dpsRTUv2p11418Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 34 is cleared"
	::= { dpsRTUv2 11418 }

dpsRTUv2p10419Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 35 is set"
	::= { dpsRTUv2 10419 }

dpsRTUv2p11419Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 35 is cleared"
	::= { dpsRTUv2 11419 }

dpsRTUv2p10420Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 36 is set"
	::= { dpsRTUv2 10420 }

dpsRTUv2p11420Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 36 is cleared"
	::= { dpsRTUv2 11420 }

dpsRTUv2p10421Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 37 is set"
	::= { dpsRTUv2 10421 }

dpsRTUv2p11421Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 37 is cleared"
	::= { dpsRTUv2 11421 }

dpsRTUv2p10422Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 38 is set"
	::= { dpsRTUv2 10422 }

dpsRTUv2p11422Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 38 is cleared"
	::= { dpsRTUv2 11422 }

dpsRTUv2p10423Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 39 is set"
	::= { dpsRTUv2 10423 }

dpsRTUv2p11423Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 39 is cleared"
	::= { dpsRTUv2 11423 }

dpsRTUv2p10424Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 40 is set"
	::= { dpsRTUv2 10424 }

dpsRTUv2p11424Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 40 is cleared"
	::= { dpsRTUv2 11424 }

dpsRTUv2p10425Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 41 is set"
	::= { dpsRTUv2 10425 }

dpsRTUv2p11425Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 41 is cleared"
	::= { dpsRTUv2 11425 }

dpsRTUv2p10426Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 42 is set"
	::= { dpsRTUv2 10426 }

dpsRTUv2p11426Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 42 is cleared"
	::= { dpsRTUv2 11426 }

dpsRTUv2p10427Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 43 is set"
	::= { dpsRTUv2 10427 }

dpsRTUv2p11427Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 43 is cleared"
	::= { dpsRTUv2 11427 }

dpsRTUv2p10428Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 44 is set"
	::= { dpsRTUv2 10428 }

dpsRTUv2p11428Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 44 is cleared"
	::= { dpsRTUv2 11428 }

dpsRTUv2p10429Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 45 is set"
	::= { dpsRTUv2 10429 }

dpsRTUv2p11429Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 45 is cleared"
	::= { dpsRTUv2 11429 }

dpsRTUv2p10430Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 46 is set"
	::= { dpsRTUv2 10430 }

dpsRTUv2p11430Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 46 is cleared"
	::= { dpsRTUv2 11430 }

dpsRTUv2p10431Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 47 is set"
	::= { dpsRTUv2 10431 }

dpsRTUv2p11431Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 47 is cleared"
	::= { dpsRTUv2 11431 }

dpsRTUv2p10432Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 48 is set"
	::= { dpsRTUv2 10432 }

dpsRTUv2p11432Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 48 is cleared"
	::= { dpsRTUv2 11432 }

dpsRTUv2p10433Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 49 is set"
	::= { dpsRTUv2 10433 }

dpsRTUv2p11433Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 49 is cleared"
	::= { dpsRTUv2 11433 }

dpsRTUv2p10434Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 50 is set"
	::= { dpsRTUv2 10434 }

dpsRTUv2p11434Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 50 is cleared"
	::= { dpsRTUv2 11434 }

dpsRTUv2p10435Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 51 is set"
	::= { dpsRTUv2 10435 }

dpsRTUv2p11435Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 51 is cleared"
	::= { dpsRTUv2 11435 }

dpsRTUv2p10436Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 52 is set"
	::= { dpsRTUv2 10436 }

dpsRTUv2p11436Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 52 is cleared"
	::= { dpsRTUv2 11436 }

dpsRTUv2p10437Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 53 is set"
	::= { dpsRTUv2 10437 }

dpsRTUv2p11437Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 53 is cleared"
	::= { dpsRTUv2 11437 }

dpsRTUv2p10438Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 54 is set"
	::= { dpsRTUv2 10438 }

dpsRTUv2p11438Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 54 is cleared"
	::= { dpsRTUv2 11438 }

dpsRTUv2p10439Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 55 is set"
	::= { dpsRTUv2 10439 }

dpsRTUv2p11439Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 55 is cleared"
	::= { dpsRTUv2 11439 }

dpsRTUv2p10440Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 56 is set"
	::= { dpsRTUv2 10440 }

dpsRTUv2p11440Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 56 is cleared"
	::= { dpsRTUv2 11440 }

dpsRTUv2p10441Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 57 is set"
	::= { dpsRTUv2 10441 }

dpsRTUv2p11441Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 57 is cleared"
	::= { dpsRTUv2 11441 }

dpsRTUv2p10442Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 58 is set"
	::= { dpsRTUv2 10442 }

dpsRTUv2p11442Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 58 is cleared"
	::= { dpsRTUv2 11442 }

dpsRTUv2p10443Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 59 is set"
	::= { dpsRTUv2 10443 }

dpsRTUv2p11443Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 59 is cleared"
	::= { dpsRTUv2 11443 }

dpsRTUv2p10444Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 60 is set"
	::= { dpsRTUv2 10444 }

dpsRTUv2p11444Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 60 is cleared"
	::= { dpsRTUv2 11444 }

dpsRTUv2p10445Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 61 is set"
	::= { dpsRTUv2 10445 }

dpsRTUv2p11445Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 61 is cleared"
	::= { dpsRTUv2 11445 }

dpsRTUv2p10446Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 62 is set"
	::= { dpsRTUv2 10446 }

dpsRTUv2p11446Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 62 is cleared"
	::= { dpsRTUv2 11446 }

dpsRTUv2p10447Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 63 is set"
	::= { dpsRTUv2 10447 }

dpsRTUv2p11447Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 63 is cleared"
	::= { dpsRTUv2 11447 }

dpsRTUv2p10448Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 64 is set"
	::= { dpsRTUv2 10448 }

dpsRTUv2p11448Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 7 point 64 is cleared"
	::= { dpsRTUv2 11448 }

dpsRTUv2p10449Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 1 is set"
	::= { dpsRTUv2 10449 }

dpsRTUv2p11449Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 1 is cleared"
	::= { dpsRTUv2 11449 }

dpsRTUv2p10450Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 2 is set"
	::= { dpsRTUv2 10450 }

dpsRTUv2p11450Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 2 is cleared"
	::= { dpsRTUv2 11450 }

dpsRTUv2p10451Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 3 is set"
	::= { dpsRTUv2 10451 }

dpsRTUv2p11451Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 3 is cleared"
	::= { dpsRTUv2 11451 }

dpsRTUv2p10452Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 4 is set"
	::= { dpsRTUv2 10452 }

dpsRTUv2p11452Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 4 is cleared"
	::= { dpsRTUv2 11452 }

dpsRTUv2p10453Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 5 is set"
	::= { dpsRTUv2 10453 }

dpsRTUv2p11453Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 5 is cleared"
	::= { dpsRTUv2 11453 }

dpsRTUv2p10454Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 6 is set"
	::= { dpsRTUv2 10454 }

dpsRTUv2p11454Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 6 is cleared"
	::= { dpsRTUv2 11454 }

dpsRTUv2p10455Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 7 is set"
	::= { dpsRTUv2 10455 }

dpsRTUv2p11455Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 7 is cleared"
	::= { dpsRTUv2 11455 }

dpsRTUv2p10456Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 8 is set"
	::= { dpsRTUv2 10456 }

dpsRTUv2p11456Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 8 is cleared"
	::= { dpsRTUv2 11456 }

dpsRTUv2p10457Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 9 is set"
	::= { dpsRTUv2 10457 }

dpsRTUv2p11457Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 9 is cleared"
	::= { dpsRTUv2 11457 }

dpsRTUv2p10458Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 10 is set"
	::= { dpsRTUv2 10458 }

dpsRTUv2p11458Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 10 is cleared"
	::= { dpsRTUv2 11458 }

dpsRTUv2p10459Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 11 is set"
	::= { dpsRTUv2 10459 }

dpsRTUv2p11459Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 11 is cleared"
	::= { dpsRTUv2 11459 }

dpsRTUv2p10460Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 12 is set"
	::= { dpsRTUv2 10460 }

dpsRTUv2p11460Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 12 is cleared"
	::= { dpsRTUv2 11460 }

dpsRTUv2p10461Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 13 is set"
	::= { dpsRTUv2 10461 }

dpsRTUv2p11461Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 13 is cleared"
	::= { dpsRTUv2 11461 }

dpsRTUv2p10462Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 14 is set"
	::= { dpsRTUv2 10462 }

dpsRTUv2p11462Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 14 is cleared"
	::= { dpsRTUv2 11462 }

dpsRTUv2p10463Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 15 is set"
	::= { dpsRTUv2 10463 }

dpsRTUv2p11463Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 15 is cleared"
	::= { dpsRTUv2 11463 }

dpsRTUv2p10464Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 16 is set"
	::= { dpsRTUv2 10464 }

dpsRTUv2p11464Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 16 is cleared"
	::= { dpsRTUv2 11464 }

dpsRTUv2p10465Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 17 is set"
	::= { dpsRTUv2 10465 }

dpsRTUv2p11465Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 17 is cleared"
	::= { dpsRTUv2 11465 }

dpsRTUv2p10466Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 18 is set"
	::= { dpsRTUv2 10466 }

dpsRTUv2p11466Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 18 is cleared"
	::= { dpsRTUv2 11466 }

dpsRTUv2p10467Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 19 is set"
	::= { dpsRTUv2 10467 }

dpsRTUv2p11467Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 19 is cleared"
	::= { dpsRTUv2 11467 }

dpsRTUv2p10468Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 20 is set"
	::= { dpsRTUv2 10468 }

dpsRTUv2p11468Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 20 is cleared"
	::= { dpsRTUv2 11468 }

dpsRTUv2p10469Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 21 is set"
	::= { dpsRTUv2 10469 }

dpsRTUv2p11469Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 21 is cleared"
	::= { dpsRTUv2 11469 }

dpsRTUv2p10470Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 22 is set"
	::= { dpsRTUv2 10470 }

dpsRTUv2p11470Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 22 is cleared"
	::= { dpsRTUv2 11470 }

dpsRTUv2p10471Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 23 is set"
	::= { dpsRTUv2 10471 }

dpsRTUv2p11471Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 23 is cleared"
	::= { dpsRTUv2 11471 }

dpsRTUv2p10472Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 24 is set"
	::= { dpsRTUv2 10472 }

dpsRTUv2p11472Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 24 is cleared"
	::= { dpsRTUv2 11472 }

dpsRTUv2p10473Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 25 is set"
	::= { dpsRTUv2 10473 }

dpsRTUv2p11473Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 25 is cleared"
	::= { dpsRTUv2 11473 }

dpsRTUv2p10474Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 26 is set"
	::= { dpsRTUv2 10474 }

dpsRTUv2p11474Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 26 is cleared"
	::= { dpsRTUv2 11474 }

dpsRTUv2p10475Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 27 is set"
	::= { dpsRTUv2 10475 }

dpsRTUv2p11475Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 27 is cleared"
	::= { dpsRTUv2 11475 }

dpsRTUv2p10476Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 28 is set"
	::= { dpsRTUv2 10476 }

dpsRTUv2p11476Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 28 is cleared"
	::= { dpsRTUv2 11476 }

dpsRTUv2p10477Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 29 is set"
	::= { dpsRTUv2 10477 }

dpsRTUv2p11477Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 29 is cleared"
	::= { dpsRTUv2 11477 }

dpsRTUv2p10478Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 30 is set"
	::= { dpsRTUv2 10478 }

dpsRTUv2p11478Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 30 is cleared"
	::= { dpsRTUv2 11478 }

dpsRTUv2p10479Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 31 is set"
	::= { dpsRTUv2 10479 }

dpsRTUv2p11479Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 31 is cleared"
	::= { dpsRTUv2 11479 }

dpsRTUv2p10480Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 32 is set"
	::= { dpsRTUv2 10480 }

dpsRTUv2p11480Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 32 is cleared"
	::= { dpsRTUv2 11480 }

dpsRTUv2p10481Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 33 is set"
	::= { dpsRTUv2 10481 }

dpsRTUv2p11481Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 33 is cleared"
	::= { dpsRTUv2 11481 }

dpsRTUv2p10482Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 34 is set"
	::= { dpsRTUv2 10482 }

dpsRTUv2p11482Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 34 is cleared"
	::= { dpsRTUv2 11482 }

dpsRTUv2p10483Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 35 is set"
	::= { dpsRTUv2 10483 }

dpsRTUv2p11483Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 35 is cleared"
	::= { dpsRTUv2 11483 }

dpsRTUv2p10484Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 36 is set"
	::= { dpsRTUv2 10484 }

dpsRTUv2p11484Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 36 is cleared"
	::= { dpsRTUv2 11484 }

dpsRTUv2p10485Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 37 is set"
	::= { dpsRTUv2 10485 }

dpsRTUv2p11485Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 37 is cleared"
	::= { dpsRTUv2 11485 }

dpsRTUv2p10486Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 38 is set"
	::= { dpsRTUv2 10486 }

dpsRTUv2p11486Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 38 is cleared"
	::= { dpsRTUv2 11486 }

dpsRTUv2p10487Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 39 is set"
	::= { dpsRTUv2 10487 }

dpsRTUv2p11487Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 39 is cleared"
	::= { dpsRTUv2 11487 }

dpsRTUv2p10488Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 40 is set"
	::= { dpsRTUv2 10488 }

dpsRTUv2p11488Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 40 is cleared"
	::= { dpsRTUv2 11488 }

dpsRTUv2p10489Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 41 is set"
	::= { dpsRTUv2 10489 }

dpsRTUv2p11489Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 41 is cleared"
	::= { dpsRTUv2 11489 }

dpsRTUv2p10490Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 42 is set"
	::= { dpsRTUv2 10490 }

dpsRTUv2p11490Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 42 is cleared"
	::= { dpsRTUv2 11490 }

dpsRTUv2p10491Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 43 is set"
	::= { dpsRTUv2 10491 }

dpsRTUv2p11491Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 43 is cleared"
	::= { dpsRTUv2 11491 }

dpsRTUv2p10492Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 44 is set"
	::= { dpsRTUv2 10492 }

dpsRTUv2p11492Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 44 is cleared"
	::= { dpsRTUv2 11492 }

dpsRTUv2p10493Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 45 is set"
	::= { dpsRTUv2 10493 }

dpsRTUv2p11493Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 45 is cleared"
	::= { dpsRTUv2 11493 }

dpsRTUv2p10494Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 46 is set"
	::= { dpsRTUv2 10494 }

dpsRTUv2p11494Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 46 is cleared"
	::= { dpsRTUv2 11494 }

dpsRTUv2p10495Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 47 is set"
	::= { dpsRTUv2 10495 }

dpsRTUv2p11495Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 47 is cleared"
	::= { dpsRTUv2 11495 }

dpsRTUv2p10496Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 48 is set"
	::= { dpsRTUv2 10496 }

dpsRTUv2p11496Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 48 is cleared"
	::= { dpsRTUv2 11496 }

dpsRTUv2p10497Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 49 is set"
	::= { dpsRTUv2 10497 }

dpsRTUv2p11497Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 49 is cleared"
	::= { dpsRTUv2 11497 }

dpsRTUv2p10498Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 50 is set"
	::= { dpsRTUv2 10498 }

dpsRTUv2p11498Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 50 is cleared"
	::= { dpsRTUv2 11498 }

dpsRTUv2p10499Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 51 is set"
	::= { dpsRTUv2 10499 }

dpsRTUv2p11499Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 51 is cleared"
	::= { dpsRTUv2 11499 }

dpsRTUv2p10500Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 52 is set"
	::= { dpsRTUv2 10500 }

dpsRTUv2p11500Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 52 is cleared"
	::= { dpsRTUv2 11500 }

dpsRTUv2p10501Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 53 is set"
	::= { dpsRTUv2 10501 }

dpsRTUv2p11501Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 53 is cleared"
	::= { dpsRTUv2 11501 }

dpsRTUv2p10502Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 54 is set"
	::= { dpsRTUv2 10502 }

dpsRTUv2p11502Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 54 is cleared"
	::= { dpsRTUv2 11502 }

dpsRTUv2p10503Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 55 is set"
	::= { dpsRTUv2 10503 }

dpsRTUv2p11503Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 55 is cleared"
	::= { dpsRTUv2 11503 }

dpsRTUv2p10504Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 56 is set"
	::= { dpsRTUv2 10504 }

dpsRTUv2p11504Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 56 is cleared"
	::= { dpsRTUv2 11504 }

dpsRTUv2p10505Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 57 is set"
	::= { dpsRTUv2 10505 }

dpsRTUv2p11505Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 57 is cleared"
	::= { dpsRTUv2 11505 }

dpsRTUv2p10506Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 58 is set"
	::= { dpsRTUv2 10506 }

dpsRTUv2p11506Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 58 is cleared"
	::= { dpsRTUv2 11506 }

dpsRTUv2p10507Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 59 is set"
	::= { dpsRTUv2 10507 }

dpsRTUv2p11507Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 59 is cleared"
	::= { dpsRTUv2 11507 }

dpsRTUv2p10508Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 60 is set"
	::= { dpsRTUv2 10508 }

dpsRTUv2p11508Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 60 is cleared"
	::= { dpsRTUv2 11508 }

dpsRTUv2p10509Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 61 is set"
	::= { dpsRTUv2 10509 }

dpsRTUv2p11509Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 61 is cleared"
	::= { dpsRTUv2 11509 }

dpsRTUv2p10510Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 62 is set"
	::= { dpsRTUv2 10510 }

dpsRTUv2p11510Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 62 is cleared"
	::= { dpsRTUv2 11510 }

dpsRTUv2p10511Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 63 is set"
	::= { dpsRTUv2 10511 }

dpsRTUv2p11511Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 63 is cleared"
	::= { dpsRTUv2 11511 }

dpsRTUv2p10512Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 64 is set"
	::= { dpsRTUv2 10512 }

dpsRTUv2p11512Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 1 display 8 point 64 is cleared"
	::= { dpsRTUv2 11512 }
dpsRTUv2p12001Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 1 is set"
	::= { dpsRTUv2 12001 }

dpsRTUv2p13001Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 1 is cleared"
	::= { dpsRTUv2 13001 }

dpsRTUv2p12002Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 2 is set"
	::= { dpsRTUv2 12002 }

dpsRTUv2p13002Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 2 is cleared"
	::= { dpsRTUv2 13002 }

dpsRTUv2p12003Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 3 is set"
	::= { dpsRTUv2 12003 }

dpsRTUv2p13003Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 3 is cleared"
	::= { dpsRTUv2 13003 }

dpsRTUv2p12004Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 4 is set"
	::= { dpsRTUv2 12004 }

dpsRTUv2p13004Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 4 is cleared"
	::= { dpsRTUv2 13004 }

dpsRTUv2p12005Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 5 is set"
	::= { dpsRTUv2 12005 }

dpsRTUv2p13005Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 5 is cleared"
	::= { dpsRTUv2 13005 }

dpsRTUv2p12006Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 6 is set"
	::= { dpsRTUv2 12006 }

dpsRTUv2p13006Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 6 is cleared"
	::= { dpsRTUv2 13006 }

dpsRTUv2p12007Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 7 is set"
	::= { dpsRTUv2 12007 }

dpsRTUv2p13007Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 7 is cleared"
	::= { dpsRTUv2 13007 }

dpsRTUv2p12008Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 8 is set"
	::= { dpsRTUv2 12008 }

dpsRTUv2p13008Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 8 is cleared"
	::= { dpsRTUv2 13008 }

dpsRTUv2p12009Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 9 is set"
	::= { dpsRTUv2 12009 }

dpsRTUv2p13009Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 9 is cleared"
	::= { dpsRTUv2 13009 }

dpsRTUv2p12010Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 10 is set"
	::= { dpsRTUv2 12010 }

dpsRTUv2p13010Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 10 is cleared"
	::= { dpsRTUv2 13010 }

dpsRTUv2p12011Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 11 is set"
	::= { dpsRTUv2 12011 }

dpsRTUv2p13011Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 11 is cleared"
	::= { dpsRTUv2 13011 }

dpsRTUv2p12012Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 12 is set"
	::= { dpsRTUv2 12012 }

dpsRTUv2p13012Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 12 is cleared"
	::= { dpsRTUv2 13012 }

dpsRTUv2p12013Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 13 is set"
	::= { dpsRTUv2 12013 }

dpsRTUv2p13013Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 13 is cleared"
	::= { dpsRTUv2 13013 }

dpsRTUv2p12014Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 14 is set"
	::= { dpsRTUv2 12014 }

dpsRTUv2p13014Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 14 is cleared"
	::= { dpsRTUv2 13014 }

dpsRTUv2p12015Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 15 is set"
	::= { dpsRTUv2 12015 }

dpsRTUv2p13015Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 15 is cleared"
	::= { dpsRTUv2 13015 }

dpsRTUv2p12016Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 16 is set"
	::= { dpsRTUv2 12016 }

dpsRTUv2p13016Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 16 is cleared"
	::= { dpsRTUv2 13016 }

dpsRTUv2p12017Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 17 is set"
	::= { dpsRTUv2 12017 }

dpsRTUv2p13017Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 17 is cleared"
	::= { dpsRTUv2 13017 }

dpsRTUv2p12018Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 18 is set"
	::= { dpsRTUv2 12018 }

dpsRTUv2p13018Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 18 is cleared"
	::= { dpsRTUv2 13018 }

dpsRTUv2p12019Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 19 is set"
	::= { dpsRTUv2 12019 }

dpsRTUv2p13019Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 19 is cleared"
	::= { dpsRTUv2 13019 }

dpsRTUv2p12020Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 20 is set"
	::= { dpsRTUv2 12020 }

dpsRTUv2p13020Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 20 is cleared"
	::= { dpsRTUv2 13020 }

dpsRTUv2p12021Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 21 is set"
	::= { dpsRTUv2 12021 }

dpsRTUv2p13021Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 21 is cleared"
	::= { dpsRTUv2 13021 }

dpsRTUv2p12022Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 22 is set"
	::= { dpsRTUv2 12022 }

dpsRTUv2p13022Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 22 is cleared"
	::= { dpsRTUv2 13022 }

dpsRTUv2p12023Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 23 is set"
	::= { dpsRTUv2 12023 }

dpsRTUv2p13023Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 23 is cleared"
	::= { dpsRTUv2 13023 }

dpsRTUv2p12024Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 24 is set"
	::= { dpsRTUv2 12024 }

dpsRTUv2p13024Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 24 is cleared"
	::= { dpsRTUv2 13024 }

dpsRTUv2p12025Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 25 is set"
	::= { dpsRTUv2 12025 }

dpsRTUv2p13025Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 25 is cleared"
	::= { dpsRTUv2 13025 }

dpsRTUv2p12026Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 26 is set"
	::= { dpsRTUv2 12026 }

dpsRTUv2p13026Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 26 is cleared"
	::= { dpsRTUv2 13026 }

dpsRTUv2p12027Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 27 is set"
	::= { dpsRTUv2 12027 }

dpsRTUv2p13027Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 27 is cleared"
	::= { dpsRTUv2 13027 }

dpsRTUv2p12028Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 28 is set"
	::= { dpsRTUv2 12028 }

dpsRTUv2p13028Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 28 is cleared"
	::= { dpsRTUv2 13028 }

dpsRTUv2p12029Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 29 is set"
	::= { dpsRTUv2 12029 }

dpsRTUv2p13029Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 29 is cleared"
	::= { dpsRTUv2 13029 }

dpsRTUv2p12030Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 30 is set"
	::= { dpsRTUv2 12030 }

dpsRTUv2p13030Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 30 is cleared"
	::= { dpsRTUv2 13030 }

dpsRTUv2p12031Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 31 is set"
	::= { dpsRTUv2 12031 }

dpsRTUv2p13031Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 31 is cleared"
	::= { dpsRTUv2 13031 }

dpsRTUv2p12032Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 32 is set"
	::= { dpsRTUv2 12032 }

dpsRTUv2p13032Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 32 is cleared"
	::= { dpsRTUv2 13032 }

dpsRTUv2p12033Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 33 is set"
	::= { dpsRTUv2 12033 }

dpsRTUv2p13033Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 33 is cleared"
	::= { dpsRTUv2 13033 }

dpsRTUv2p12034Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 34 is set"
	::= { dpsRTUv2 12034 }

dpsRTUv2p13034Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 34 is cleared"
	::= { dpsRTUv2 13034 }

dpsRTUv2p12035Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 35 is set"
	::= { dpsRTUv2 12035 }

dpsRTUv2p13035Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 35 is cleared"
	::= { dpsRTUv2 13035 }

dpsRTUv2p12036Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 36 is set"
	::= { dpsRTUv2 12036 }

dpsRTUv2p13036Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 36 is cleared"
	::= { dpsRTUv2 13036 }

dpsRTUv2p12037Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 37 is set"
	::= { dpsRTUv2 12037 }

dpsRTUv2p13037Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 37 is cleared"
	::= { dpsRTUv2 13037 }

dpsRTUv2p12038Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 38 is set"
	::= { dpsRTUv2 12038 }

dpsRTUv2p13038Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 38 is cleared"
	::= { dpsRTUv2 13038 }

dpsRTUv2p12039Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 39 is set"
	::= { dpsRTUv2 12039 }

dpsRTUv2p13039Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 39 is cleared"
	::= { dpsRTUv2 13039 }

dpsRTUv2p12040Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 40 is set"
	::= { dpsRTUv2 12040 }

dpsRTUv2p13040Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 40 is cleared"
	::= { dpsRTUv2 13040 }

dpsRTUv2p12041Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 41 is set"
	::= { dpsRTUv2 12041 }

dpsRTUv2p13041Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 41 is cleared"
	::= { dpsRTUv2 13041 }

dpsRTUv2p12042Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 42 is set"
	::= { dpsRTUv2 12042 }

dpsRTUv2p13042Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 42 is cleared"
	::= { dpsRTUv2 13042 }

dpsRTUv2p12043Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 43 is set"
	::= { dpsRTUv2 12043 }

dpsRTUv2p13043Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 43 is cleared"
	::= { dpsRTUv2 13043 }

dpsRTUv2p12044Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 44 is set"
	::= { dpsRTUv2 12044 }

dpsRTUv2p13044Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 44 is cleared"
	::= { dpsRTUv2 13044 }

dpsRTUv2p12045Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 45 is set"
	::= { dpsRTUv2 12045 }

dpsRTUv2p13045Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 45 is cleared"
	::= { dpsRTUv2 13045 }

dpsRTUv2p12046Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 46 is set"
	::= { dpsRTUv2 12046 }

dpsRTUv2p13046Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 46 is cleared"
	::= { dpsRTUv2 13046 }

dpsRTUv2p12047Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 47 is set"
	::= { dpsRTUv2 12047 }

dpsRTUv2p13047Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 47 is cleared"
	::= { dpsRTUv2 13047 }

dpsRTUv2p12048Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 48 is set"
	::= { dpsRTUv2 12048 }

dpsRTUv2p13048Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 48 is cleared"
	::= { dpsRTUv2 13048 }

dpsRTUv2p12049Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 49 is set"
	::= { dpsRTUv2 12049 }

dpsRTUv2p13049Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 49 is cleared"
	::= { dpsRTUv2 13049 }

dpsRTUv2p12050Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 50 is set"
	::= { dpsRTUv2 12050 }

dpsRTUv2p13050Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 50 is cleared"
	::= { dpsRTUv2 13050 }

dpsRTUv2p12051Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 51 is set"
	::= { dpsRTUv2 12051 }

dpsRTUv2p13051Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 51 is cleared"
	::= { dpsRTUv2 13051 }

dpsRTUv2p12052Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 52 is set"
	::= { dpsRTUv2 12052 }

dpsRTUv2p13052Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 52 is cleared"
	::= { dpsRTUv2 13052 }

dpsRTUv2p12053Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 53 is set"
	::= { dpsRTUv2 12053 }

dpsRTUv2p13053Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 53 is cleared"
	::= { dpsRTUv2 13053 }

dpsRTUv2p12054Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 54 is set"
	::= { dpsRTUv2 12054 }

dpsRTUv2p13054Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 54 is cleared"
	::= { dpsRTUv2 13054 }

dpsRTUv2p12055Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 55 is set"
	::= { dpsRTUv2 12055 }

dpsRTUv2p13055Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 55 is cleared"
	::= { dpsRTUv2 13055 }

dpsRTUv2p12056Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 56 is set"
	::= { dpsRTUv2 12056 }

dpsRTUv2p13056Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 56 is cleared"
	::= { dpsRTUv2 13056 }

dpsRTUv2p12057Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 57 is set"
	::= { dpsRTUv2 12057 }

dpsRTUv2p13057Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 57 is cleared"
	::= { dpsRTUv2 13057 }

dpsRTUv2p12058Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 58 is set"
	::= { dpsRTUv2 12058 }

dpsRTUv2p13058Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 58 is cleared"
	::= { dpsRTUv2 13058 }

dpsRTUv2p12059Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 59 is set"
	::= { dpsRTUv2 12059 }

dpsRTUv2p13059Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 59 is cleared"
	::= { dpsRTUv2 13059 }

dpsRTUv2p12060Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 60 is set"
	::= { dpsRTUv2 12060 }

dpsRTUv2p13060Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 60 is cleared"
	::= { dpsRTUv2 13060 }

dpsRTUv2p12061Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 61 is set"
	::= { dpsRTUv2 12061 }

dpsRTUv2p13061Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 61 is cleared"
	::= { dpsRTUv2 13061 }

dpsRTUv2p12062Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 62 is set"
	::= { dpsRTUv2 12062 }

dpsRTUv2p13062Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 62 is cleared"
	::= { dpsRTUv2 13062 }

dpsRTUv2p12063Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 63 is set"
	::= { dpsRTUv2 12063 }

dpsRTUv2p13063Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 63 is cleared"
	::= { dpsRTUv2 13063 }

dpsRTUv2p12064Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 64 is set"
	::= { dpsRTUv2 12064 }

dpsRTUv2p13064Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 1 point 64 is cleared"
	::= { dpsRTUv2 13064 }

dpsRTUv2p12065Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 1 is set"
	::= { dpsRTUv2 12065 }

dpsRTUv2p13065Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 1 is cleared"
	::= { dpsRTUv2 13065 }

dpsRTUv2p12066Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 2 is set"
	::= { dpsRTUv2 12066 }

dpsRTUv2p13066Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 2 is cleared"
	::= { dpsRTUv2 13066 }

dpsRTUv2p12067Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 3 is set"
	::= { dpsRTUv2 12067 }

dpsRTUv2p13067Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 3 is cleared"
	::= { dpsRTUv2 13067 }

dpsRTUv2p12068Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 4 is set"
	::= { dpsRTUv2 12068 }

dpsRTUv2p13068Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 4 is cleared"
	::= { dpsRTUv2 13068 }

dpsRTUv2p12069Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 5 is set"
	::= { dpsRTUv2 12069 }

dpsRTUv2p13069Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 5 is cleared"
	::= { dpsRTUv2 13069 }

dpsRTUv2p12070Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 6 is set"
	::= { dpsRTUv2 12070 }

dpsRTUv2p13070Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 6 is cleared"
	::= { dpsRTUv2 13070 }

dpsRTUv2p12071Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 7 is set"
	::= { dpsRTUv2 12071 }

dpsRTUv2p13071Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 7 is cleared"
	::= { dpsRTUv2 13071 }

dpsRTUv2p12072Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 8 is set"
	::= { dpsRTUv2 12072 }

dpsRTUv2p13072Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 8 is cleared"
	::= { dpsRTUv2 13072 }

dpsRTUv2p12073Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 9 is set"
	::= { dpsRTUv2 12073 }

dpsRTUv2p13073Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 9 is cleared"
	::= { dpsRTUv2 13073 }

dpsRTUv2p12074Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 10 is set"
	::= { dpsRTUv2 12074 }

dpsRTUv2p13074Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 10 is cleared"
	::= { dpsRTUv2 13074 }

dpsRTUv2p12075Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 11 is set"
	::= { dpsRTUv2 12075 }

dpsRTUv2p13075Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 11 is cleared"
	::= { dpsRTUv2 13075 }

dpsRTUv2p12076Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 12 is set"
	::= { dpsRTUv2 12076 }

dpsRTUv2p13076Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 12 is cleared"
	::= { dpsRTUv2 13076 }

dpsRTUv2p12077Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 13 is set"
	::= { dpsRTUv2 12077 }

dpsRTUv2p13077Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 13 is cleared"
	::= { dpsRTUv2 13077 }

dpsRTUv2p12078Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 14 is set"
	::= { dpsRTUv2 12078 }

dpsRTUv2p13078Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 14 is cleared"
	::= { dpsRTUv2 13078 }

dpsRTUv2p12079Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 15 is set"
	::= { dpsRTUv2 12079 }

dpsRTUv2p13079Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 15 is cleared"
	::= { dpsRTUv2 13079 }

dpsRTUv2p12080Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 16 is set"
	::= { dpsRTUv2 12080 }

dpsRTUv2p13080Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 16 is cleared"
	::= { dpsRTUv2 13080 }

dpsRTUv2p12081Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 17 is set"
	::= { dpsRTUv2 12081 }

dpsRTUv2p13081Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 17 is cleared"
	::= { dpsRTUv2 13081 }

dpsRTUv2p12082Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 18 is set"
	::= { dpsRTUv2 12082 }

dpsRTUv2p13082Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 18 is cleared"
	::= { dpsRTUv2 13082 }

dpsRTUv2p12083Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 19 is set"
	::= { dpsRTUv2 12083 }

dpsRTUv2p13083Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 19 is cleared"
	::= { dpsRTUv2 13083 }

dpsRTUv2p12084Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 20 is set"
	::= { dpsRTUv2 12084 }

dpsRTUv2p13084Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 20 is cleared"
	::= { dpsRTUv2 13084 }

dpsRTUv2p12085Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 21 is set"
	::= { dpsRTUv2 12085 }

dpsRTUv2p13085Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 21 is cleared"
	::= { dpsRTUv2 13085 }

dpsRTUv2p12086Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 22 is set"
	::= { dpsRTUv2 12086 }

dpsRTUv2p13086Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 22 is cleared"
	::= { dpsRTUv2 13086 }

dpsRTUv2p12087Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 23 is set"
	::= { dpsRTUv2 12087 }

dpsRTUv2p13087Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 23 is cleared"
	::= { dpsRTUv2 13087 }

dpsRTUv2p12088Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 24 is set"
	::= { dpsRTUv2 12088 }

dpsRTUv2p13088Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 24 is cleared"
	::= { dpsRTUv2 13088 }

dpsRTUv2p12089Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 25 is set"
	::= { dpsRTUv2 12089 }

dpsRTUv2p13089Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 25 is cleared"
	::= { dpsRTUv2 13089 }

dpsRTUv2p12090Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 26 is set"
	::= { dpsRTUv2 12090 }

dpsRTUv2p13090Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 26 is cleared"
	::= { dpsRTUv2 13090 }

dpsRTUv2p12091Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 27 is set"
	::= { dpsRTUv2 12091 }

dpsRTUv2p13091Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 27 is cleared"
	::= { dpsRTUv2 13091 }

dpsRTUv2p12092Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 28 is set"
	::= { dpsRTUv2 12092 }

dpsRTUv2p13092Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 28 is cleared"
	::= { dpsRTUv2 13092 }

dpsRTUv2p12093Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 29 is set"
	::= { dpsRTUv2 12093 }

dpsRTUv2p13093Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 29 is cleared"
	::= { dpsRTUv2 13093 }

dpsRTUv2p12094Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 30 is set"
	::= { dpsRTUv2 12094 }

dpsRTUv2p13094Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 30 is cleared"
	::= { dpsRTUv2 13094 }

dpsRTUv2p12095Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 31 is set"
	::= { dpsRTUv2 12095 }

dpsRTUv2p13095Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 31 is cleared"
	::= { dpsRTUv2 13095 }

dpsRTUv2p12096Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 32 is set"
	::= { dpsRTUv2 12096 }

dpsRTUv2p13096Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 32 is cleared"
	::= { dpsRTUv2 13096 }

dpsRTUv2p12097Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 33 is set"
	::= { dpsRTUv2 12097 }

dpsRTUv2p13097Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 33 is cleared"
	::= { dpsRTUv2 13097 }

dpsRTUv2p12098Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 34 is set"
	::= { dpsRTUv2 12098 }

dpsRTUv2p13098Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 34 is cleared"
	::= { dpsRTUv2 13098 }

dpsRTUv2p12099Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 35 is set"
	::= { dpsRTUv2 12099 }

dpsRTUv2p13099Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 35 is cleared"
	::= { dpsRTUv2 13099 }

dpsRTUv2p12100Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 36 is set"
	::= { dpsRTUv2 12100 }

dpsRTUv2p13100Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 36 is cleared"
	::= { dpsRTUv2 13100 }

dpsRTUv2p12101Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 37 is set"
	::= { dpsRTUv2 12101 }

dpsRTUv2p13101Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 37 is cleared"
	::= { dpsRTUv2 13101 }

dpsRTUv2p12102Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 38 is set"
	::= { dpsRTUv2 12102 }

dpsRTUv2p13102Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 38 is cleared"
	::= { dpsRTUv2 13102 }

dpsRTUv2p12103Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 39 is set"
	::= { dpsRTUv2 12103 }

dpsRTUv2p13103Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 39 is cleared"
	::= { dpsRTUv2 13103 }

dpsRTUv2p12104Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 40 is set"
	::= { dpsRTUv2 12104 }

dpsRTUv2p13104Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 40 is cleared"
	::= { dpsRTUv2 13104 }

dpsRTUv2p12105Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 41 is set"
	::= { dpsRTUv2 12105 }

dpsRTUv2p13105Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 41 is cleared"
	::= { dpsRTUv2 13105 }

dpsRTUv2p12106Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 42 is set"
	::= { dpsRTUv2 12106 }

dpsRTUv2p13106Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 42 is cleared"
	::= { dpsRTUv2 13106 }

dpsRTUv2p12107Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 43 is set"
	::= { dpsRTUv2 12107 }

dpsRTUv2p13107Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 43 is cleared"
	::= { dpsRTUv2 13107 }

dpsRTUv2p12108Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 44 is set"
	::= { dpsRTUv2 12108 }

dpsRTUv2p13108Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 44 is cleared"
	::= { dpsRTUv2 13108 }

dpsRTUv2p12109Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 45 is set"
	::= { dpsRTUv2 12109 }

dpsRTUv2p13109Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 45 is cleared"
	::= { dpsRTUv2 13109 }

dpsRTUv2p12110Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 46 is set"
	::= { dpsRTUv2 12110 }

dpsRTUv2p13110Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 46 is cleared"
	::= { dpsRTUv2 13110 }

dpsRTUv2p12111Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 47 is set"
	::= { dpsRTUv2 12111 }

dpsRTUv2p13111Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 47 is cleared"
	::= { dpsRTUv2 13111 }

dpsRTUv2p12112Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 48 is set"
	::= { dpsRTUv2 12112 }

dpsRTUv2p13112Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 48 is cleared"
	::= { dpsRTUv2 13112 }

dpsRTUv2p12113Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 49 is set"
	::= { dpsRTUv2 12113 }

dpsRTUv2p13113Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 49 is cleared"
	::= { dpsRTUv2 13113 }

dpsRTUv2p12114Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 50 is set"
	::= { dpsRTUv2 12114 }

dpsRTUv2p13114Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 50 is cleared"
	::= { dpsRTUv2 13114 }

dpsRTUv2p12115Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 51 is set"
	::= { dpsRTUv2 12115 }

dpsRTUv2p13115Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 51 is cleared"
	::= { dpsRTUv2 13115 }

dpsRTUv2p12116Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 52 is set"
	::= { dpsRTUv2 12116 }

dpsRTUv2p13116Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 52 is cleared"
	::= { dpsRTUv2 13116 }

dpsRTUv2p12117Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 53 is set"
	::= { dpsRTUv2 12117 }

dpsRTUv2p13117Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 53 is cleared"
	::= { dpsRTUv2 13117 }

dpsRTUv2p12118Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 54 is set"
	::= { dpsRTUv2 12118 }

dpsRTUv2p13118Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 54 is cleared"
	::= { dpsRTUv2 13118 }

dpsRTUv2p12119Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 55 is set"
	::= { dpsRTUv2 12119 }

dpsRTUv2p13119Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 55 is cleared"
	::= { dpsRTUv2 13119 }

dpsRTUv2p12120Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 56 is set"
	::= { dpsRTUv2 12120 }

dpsRTUv2p13120Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 56 is cleared"
	::= { dpsRTUv2 13120 }

dpsRTUv2p12121Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 57 is set"
	::= { dpsRTUv2 12121 }

dpsRTUv2p13121Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 57 is cleared"
	::= { dpsRTUv2 13121 }

dpsRTUv2p12122Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 58 is set"
	::= { dpsRTUv2 12122 }

dpsRTUv2p13122Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 58 is cleared"
	::= { dpsRTUv2 13122 }

dpsRTUv2p12123Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 59 is set"
	::= { dpsRTUv2 12123 }

dpsRTUv2p13123Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 59 is cleared"
	::= { dpsRTUv2 13123 }

dpsRTUv2p12124Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 60 is set"
	::= { dpsRTUv2 12124 }

dpsRTUv2p13124Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 60 is cleared"
	::= { dpsRTUv2 13124 }

dpsRTUv2p12125Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 61 is set"
	::= { dpsRTUv2 12125 }

dpsRTUv2p13125Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 61 is cleared"
	::= { dpsRTUv2 13125 }

dpsRTUv2p12126Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 62 is set"
	::= { dpsRTUv2 12126 }

dpsRTUv2p13126Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 62 is cleared"
	::= { dpsRTUv2 13126 }

dpsRTUv2p12127Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 63 is set"
	::= { dpsRTUv2 12127 }

dpsRTUv2p13127Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 63 is cleared"
	::= { dpsRTUv2 13127 }

dpsRTUv2p12128Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 64 is set"
	::= { dpsRTUv2 12128 }

dpsRTUv2p13128Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 2 point 64 is cleared"
	::= { dpsRTUv2 13128 }

dpsRTUv2p12129Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 1 is set"
	::= { dpsRTUv2 12129 }

dpsRTUv2p13129Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 1 is cleared"
	::= { dpsRTUv2 13129 }

dpsRTUv2p12130Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 2 is set"
	::= { dpsRTUv2 12130 }

dpsRTUv2p13130Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 2 is cleared"
	::= { dpsRTUv2 13130 }

dpsRTUv2p12131Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 3 is set"
	::= { dpsRTUv2 12131 }

dpsRTUv2p13131Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 3 is cleared"
	::= { dpsRTUv2 13131 }

dpsRTUv2p12132Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 4 is set"
	::= { dpsRTUv2 12132 }

dpsRTUv2p13132Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 4 is cleared"
	::= { dpsRTUv2 13132 }

dpsRTUv2p12133Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 5 is set"
	::= { dpsRTUv2 12133 }

dpsRTUv2p13133Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 5 is cleared"
	::= { dpsRTUv2 13133 }

dpsRTUv2p12134Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 6 is set"
	::= { dpsRTUv2 12134 }

dpsRTUv2p13134Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 6 is cleared"
	::= { dpsRTUv2 13134 }

dpsRTUv2p12135Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 7 is set"
	::= { dpsRTUv2 12135 }

dpsRTUv2p13135Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 7 is cleared"
	::= { dpsRTUv2 13135 }

dpsRTUv2p12136Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 8 is set"
	::= { dpsRTUv2 12136 }

dpsRTUv2p13136Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 8 is cleared"
	::= { dpsRTUv2 13136 }

dpsRTUv2p12137Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 9 is set"
	::= { dpsRTUv2 12137 }

dpsRTUv2p13137Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 9 is cleared"
	::= { dpsRTUv2 13137 }

dpsRTUv2p12138Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 10 is set"
	::= { dpsRTUv2 12138 }

dpsRTUv2p13138Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 10 is cleared"
	::= { dpsRTUv2 13138 }

dpsRTUv2p12139Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 11 is set"
	::= { dpsRTUv2 12139 }

dpsRTUv2p13139Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 11 is cleared"
	::= { dpsRTUv2 13139 }

dpsRTUv2p12140Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 12 is set"
	::= { dpsRTUv2 12140 }

dpsRTUv2p13140Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 12 is cleared"
	::= { dpsRTUv2 13140 }

dpsRTUv2p12141Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 13 is set"
	::= { dpsRTUv2 12141 }

dpsRTUv2p13141Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 13 is cleared"
	::= { dpsRTUv2 13141 }

dpsRTUv2p12142Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 14 is set"
	::= { dpsRTUv2 12142 }

dpsRTUv2p13142Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 14 is cleared"
	::= { dpsRTUv2 13142 }

dpsRTUv2p12143Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 15 is set"
	::= { dpsRTUv2 12143 }

dpsRTUv2p13143Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 15 is cleared"
	::= { dpsRTUv2 13143 }

dpsRTUv2p12144Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 16 is set"
	::= { dpsRTUv2 12144 }

dpsRTUv2p13144Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 16 is cleared"
	::= { dpsRTUv2 13144 }

dpsRTUv2p12145Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 17 is set"
	::= { dpsRTUv2 12145 }

dpsRTUv2p13145Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 17 is cleared"
	::= { dpsRTUv2 13145 }

dpsRTUv2p12146Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 18 is set"
	::= { dpsRTUv2 12146 }

dpsRTUv2p13146Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 18 is cleared"
	::= { dpsRTUv2 13146 }

dpsRTUv2p12147Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 19 is set"
	::= { dpsRTUv2 12147 }

dpsRTUv2p13147Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 19 is cleared"
	::= { dpsRTUv2 13147 }

dpsRTUv2p12148Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 20 is set"
	::= { dpsRTUv2 12148 }

dpsRTUv2p13148Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 20 is cleared"
	::= { dpsRTUv2 13148 }

dpsRTUv2p12149Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 21 is set"
	::= { dpsRTUv2 12149 }

dpsRTUv2p13149Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 21 is cleared"
	::= { dpsRTUv2 13149 }

dpsRTUv2p12150Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 22 is set"
	::= { dpsRTUv2 12150 }

dpsRTUv2p13150Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 22 is cleared"
	::= { dpsRTUv2 13150 }

dpsRTUv2p12151Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 23 is set"
	::= { dpsRTUv2 12151 }

dpsRTUv2p13151Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 23 is cleared"
	::= { dpsRTUv2 13151 }

dpsRTUv2p12152Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 24 is set"
	::= { dpsRTUv2 12152 }

dpsRTUv2p13152Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 24 is cleared"
	::= { dpsRTUv2 13152 }

dpsRTUv2p12153Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 25 is set"
	::= { dpsRTUv2 12153 }

dpsRTUv2p13153Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 25 is cleared"
	::= { dpsRTUv2 13153 }

dpsRTUv2p12154Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 26 is set"
	::= { dpsRTUv2 12154 }

dpsRTUv2p13154Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 26 is cleared"
	::= { dpsRTUv2 13154 }

dpsRTUv2p12155Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 27 is set"
	::= { dpsRTUv2 12155 }

dpsRTUv2p13155Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 27 is cleared"
	::= { dpsRTUv2 13155 }

dpsRTUv2p12156Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 28 is set"
	::= { dpsRTUv2 12156 }

dpsRTUv2p13156Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 28 is cleared"
	::= { dpsRTUv2 13156 }

dpsRTUv2p12157Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 29 is set"
	::= { dpsRTUv2 12157 }

dpsRTUv2p13157Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 29 is cleared"
	::= { dpsRTUv2 13157 }

dpsRTUv2p12158Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 30 is set"
	::= { dpsRTUv2 12158 }

dpsRTUv2p13158Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 30 is cleared"
	::= { dpsRTUv2 13158 }

dpsRTUv2p12159Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 31 is set"
	::= { dpsRTUv2 12159 }

dpsRTUv2p13159Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 31 is cleared"
	::= { dpsRTUv2 13159 }

dpsRTUv2p12160Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 32 is set"
	::= { dpsRTUv2 12160 }

dpsRTUv2p13160Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 32 is cleared"
	::= { dpsRTUv2 13160 }

dpsRTUv2p12161Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 33 is set"
	::= { dpsRTUv2 12161 }

dpsRTUv2p13161Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 33 is cleared"
	::= { dpsRTUv2 13161 }

dpsRTUv2p12162Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 34 is set"
	::= { dpsRTUv2 12162 }

dpsRTUv2p13162Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 34 is cleared"
	::= { dpsRTUv2 13162 }

dpsRTUv2p12163Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 35 is set"
	::= { dpsRTUv2 12163 }

dpsRTUv2p13163Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 35 is cleared"
	::= { dpsRTUv2 13163 }

dpsRTUv2p12164Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 36 is set"
	::= { dpsRTUv2 12164 }

dpsRTUv2p13164Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 36 is cleared"
	::= { dpsRTUv2 13164 }

dpsRTUv2p12165Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 37 is set"
	::= { dpsRTUv2 12165 }

dpsRTUv2p13165Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 37 is cleared"
	::= { dpsRTUv2 13165 }

dpsRTUv2p12166Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 38 is set"
	::= { dpsRTUv2 12166 }

dpsRTUv2p13166Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 38 is cleared"
	::= { dpsRTUv2 13166 }

dpsRTUv2p12167Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 39 is set"
	::= { dpsRTUv2 12167 }

dpsRTUv2p13167Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 39 is cleared"
	::= { dpsRTUv2 13167 }

dpsRTUv2p12168Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 40 is set"
	::= { dpsRTUv2 12168 }

dpsRTUv2p13168Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 40 is cleared"
	::= { dpsRTUv2 13168 }

dpsRTUv2p12169Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 41 is set"
	::= { dpsRTUv2 12169 }

dpsRTUv2p13169Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 41 is cleared"
	::= { dpsRTUv2 13169 }

dpsRTUv2p12170Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 42 is set"
	::= { dpsRTUv2 12170 }

dpsRTUv2p13170Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 42 is cleared"
	::= { dpsRTUv2 13170 }

dpsRTUv2p12171Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 43 is set"
	::= { dpsRTUv2 12171 }

dpsRTUv2p13171Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 43 is cleared"
	::= { dpsRTUv2 13171 }

dpsRTUv2p12172Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 44 is set"
	::= { dpsRTUv2 12172 }

dpsRTUv2p13172Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 44 is cleared"
	::= { dpsRTUv2 13172 }

dpsRTUv2p12173Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 45 is set"
	::= { dpsRTUv2 12173 }

dpsRTUv2p13173Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 45 is cleared"
	::= { dpsRTUv2 13173 }

dpsRTUv2p12174Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 46 is set"
	::= { dpsRTUv2 12174 }

dpsRTUv2p13174Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 46 is cleared"
	::= { dpsRTUv2 13174 }

dpsRTUv2p12175Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 47 is set"
	::= { dpsRTUv2 12175 }

dpsRTUv2p13175Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 47 is cleared"
	::= { dpsRTUv2 13175 }

dpsRTUv2p12176Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 48 is set"
	::= { dpsRTUv2 12176 }

dpsRTUv2p13176Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 48 is cleared"
	::= { dpsRTUv2 13176 }

dpsRTUv2p12177Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 49 is set"
	::= { dpsRTUv2 12177 }

dpsRTUv2p13177Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 49 is cleared"
	::= { dpsRTUv2 13177 }

dpsRTUv2p12178Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 50 is set"
	::= { dpsRTUv2 12178 }

dpsRTUv2p13178Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 50 is cleared"
	::= { dpsRTUv2 13178 }

dpsRTUv2p12179Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 51 is set"
	::= { dpsRTUv2 12179 }

dpsRTUv2p13179Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 51 is cleared"
	::= { dpsRTUv2 13179 }

dpsRTUv2p12180Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 52 is set"
	::= { dpsRTUv2 12180 }

dpsRTUv2p13180Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 52 is cleared"
	::= { dpsRTUv2 13180 }

dpsRTUv2p12181Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 53 is set"
	::= { dpsRTUv2 12181 }

dpsRTUv2p13181Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 53 is cleared"
	::= { dpsRTUv2 13181 }

dpsRTUv2p12182Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 54 is set"
	::= { dpsRTUv2 12182 }

dpsRTUv2p13182Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 54 is cleared"
	::= { dpsRTUv2 13182 }

dpsRTUv2p12183Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 55 is set"
	::= { dpsRTUv2 12183 }

dpsRTUv2p13183Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 55 is cleared"
	::= { dpsRTUv2 13183 }

dpsRTUv2p12184Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 56 is set"
	::= { dpsRTUv2 12184 }

dpsRTUv2p13184Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 56 is cleared"
	::= { dpsRTUv2 13184 }

dpsRTUv2p12185Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 57 is set"
	::= { dpsRTUv2 12185 }

dpsRTUv2p13185Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 57 is cleared"
	::= { dpsRTUv2 13185 }

dpsRTUv2p12186Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 58 is set"
	::= { dpsRTUv2 12186 }

dpsRTUv2p13186Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 58 is cleared"
	::= { dpsRTUv2 13186 }

dpsRTUv2p12187Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 59 is set"
	::= { dpsRTUv2 12187 }

dpsRTUv2p13187Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 59 is cleared"
	::= { dpsRTUv2 13187 }

dpsRTUv2p12188Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 60 is set"
	::= { dpsRTUv2 12188 }

dpsRTUv2p13188Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 60 is cleared"
	::= { dpsRTUv2 13188 }

dpsRTUv2p12189Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 61 is set"
	::= { dpsRTUv2 12189 }

dpsRTUv2p13189Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 61 is cleared"
	::= { dpsRTUv2 13189 }

dpsRTUv2p12190Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 62 is set"
	::= { dpsRTUv2 12190 }

dpsRTUv2p13190Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 62 is cleared"
	::= { dpsRTUv2 13190 }

dpsRTUv2p12191Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 63 is set"
	::= { dpsRTUv2 12191 }

dpsRTUv2p13191Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 63 is cleared"
	::= { dpsRTUv2 13191 }

dpsRTUv2p12192Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 64 is set"
	::= { dpsRTUv2 12192 }

dpsRTUv2p13192Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 3 point 64 is cleared"
	::= { dpsRTUv2 13192 }

dpsRTUv2p12193Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 1 is set"
	::= { dpsRTUv2 12193 }

dpsRTUv2p13193Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 1 is cleared"
	::= { dpsRTUv2 13193 }

dpsRTUv2p12194Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 2 is set"
	::= { dpsRTUv2 12194 }

dpsRTUv2p13194Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 2 is cleared"
	::= { dpsRTUv2 13194 }

dpsRTUv2p12195Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 3 is set"
	::= { dpsRTUv2 12195 }

dpsRTUv2p13195Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 3 is cleared"
	::= { dpsRTUv2 13195 }

dpsRTUv2p12196Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 4 is set"
	::= { dpsRTUv2 12196 }

dpsRTUv2p13196Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 4 is cleared"
	::= { dpsRTUv2 13196 }

dpsRTUv2p12197Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 5 is set"
	::= { dpsRTUv2 12197 }

dpsRTUv2p13197Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 5 is cleared"
	::= { dpsRTUv2 13197 }

dpsRTUv2p12198Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 6 is set"
	::= { dpsRTUv2 12198 }

dpsRTUv2p13198Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 6 is cleared"
	::= { dpsRTUv2 13198 }

dpsRTUv2p12199Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 7 is set"
	::= { dpsRTUv2 12199 }

dpsRTUv2p13199Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 7 is cleared"
	::= { dpsRTUv2 13199 }

dpsRTUv2p12200Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 8 is set"
	::= { dpsRTUv2 12200 }

dpsRTUv2p13200Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 8 is cleared"
	::= { dpsRTUv2 13200 }

dpsRTUv2p12201Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 9 is set"
	::= { dpsRTUv2 12201 }

dpsRTUv2p13201Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 9 is cleared"
	::= { dpsRTUv2 13201 }

dpsRTUv2p12202Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 10 is set"
	::= { dpsRTUv2 12202 }

dpsRTUv2p13202Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 10 is cleared"
	::= { dpsRTUv2 13202 }

dpsRTUv2p12203Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 11 is set"
	::= { dpsRTUv2 12203 }

dpsRTUv2p13203Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 11 is cleared"
	::= { dpsRTUv2 13203 }

dpsRTUv2p12204Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 12 is set"
	::= { dpsRTUv2 12204 }

dpsRTUv2p13204Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 12 is cleared"
	::= { dpsRTUv2 13204 }

dpsRTUv2p12205Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 13 is set"
	::= { dpsRTUv2 12205 }

dpsRTUv2p13205Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 13 is cleared"
	::= { dpsRTUv2 13205 }

dpsRTUv2p12206Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 14 is set"
	::= { dpsRTUv2 12206 }

dpsRTUv2p13206Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 14 is cleared"
	::= { dpsRTUv2 13206 }

dpsRTUv2p12207Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 15 is set"
	::= { dpsRTUv2 12207 }

dpsRTUv2p13207Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 15 is cleared"
	::= { dpsRTUv2 13207 }

dpsRTUv2p12208Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 16 is set"
	::= { dpsRTUv2 12208 }

dpsRTUv2p13208Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 16 is cleared"
	::= { dpsRTUv2 13208 }

dpsRTUv2p12209Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 17 is set"
	::= { dpsRTUv2 12209 }

dpsRTUv2p13209Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 17 is cleared"
	::= { dpsRTUv2 13209 }

dpsRTUv2p12210Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 18 is set"
	::= { dpsRTUv2 12210 }

dpsRTUv2p13210Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 18 is cleared"
	::= { dpsRTUv2 13210 }

dpsRTUv2p12211Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 19 is set"
	::= { dpsRTUv2 12211 }

dpsRTUv2p13211Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 19 is cleared"
	::= { dpsRTUv2 13211 }

dpsRTUv2p12212Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 20 is set"
	::= { dpsRTUv2 12212 }

dpsRTUv2p13212Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 20 is cleared"
	::= { dpsRTUv2 13212 }

dpsRTUv2p12213Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 21 is set"
	::= { dpsRTUv2 12213 }

dpsRTUv2p13213Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 21 is cleared"
	::= { dpsRTUv2 13213 }

dpsRTUv2p12214Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 22 is set"
	::= { dpsRTUv2 12214 }

dpsRTUv2p13214Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 22 is cleared"
	::= { dpsRTUv2 13214 }

dpsRTUv2p12215Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 23 is set"
	::= { dpsRTUv2 12215 }

dpsRTUv2p13215Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 23 is cleared"
	::= { dpsRTUv2 13215 }

dpsRTUv2p12216Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 24 is set"
	::= { dpsRTUv2 12216 }

dpsRTUv2p13216Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 24 is cleared"
	::= { dpsRTUv2 13216 }

dpsRTUv2p12217Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 25 is set"
	::= { dpsRTUv2 12217 }

dpsRTUv2p13217Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 25 is cleared"
	::= { dpsRTUv2 13217 }

dpsRTUv2p12218Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 26 is set"
	::= { dpsRTUv2 12218 }

dpsRTUv2p13218Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 26 is cleared"
	::= { dpsRTUv2 13218 }

dpsRTUv2p12219Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 27 is set"
	::= { dpsRTUv2 12219 }

dpsRTUv2p13219Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 27 is cleared"
	::= { dpsRTUv2 13219 }

dpsRTUv2p12220Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 28 is set"
	::= { dpsRTUv2 12220 }

dpsRTUv2p13220Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 28 is cleared"
	::= { dpsRTUv2 13220 }

dpsRTUv2p12221Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 29 is set"
	::= { dpsRTUv2 12221 }

dpsRTUv2p13221Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 29 is cleared"
	::= { dpsRTUv2 13221 }

dpsRTUv2p12222Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 30 is set"
	::= { dpsRTUv2 12222 }

dpsRTUv2p13222Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 30 is cleared"
	::= { dpsRTUv2 13222 }

dpsRTUv2p12223Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 31 is set"
	::= { dpsRTUv2 12223 }

dpsRTUv2p13223Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 31 is cleared"
	::= { dpsRTUv2 13223 }

dpsRTUv2p12224Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 32 is set"
	::= { dpsRTUv2 12224 }

dpsRTUv2p13224Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 32 is cleared"
	::= { dpsRTUv2 13224 }

dpsRTUv2p12225Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 33 is set"
	::= { dpsRTUv2 12225 }

dpsRTUv2p13225Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 33 is cleared"
	::= { dpsRTUv2 13225 }

dpsRTUv2p12226Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 34 is set"
	::= { dpsRTUv2 12226 }

dpsRTUv2p13226Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 34 is cleared"
	::= { dpsRTUv2 13226 }

dpsRTUv2p12227Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 35 is set"
	::= { dpsRTUv2 12227 }

dpsRTUv2p13227Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 35 is cleared"
	::= { dpsRTUv2 13227 }

dpsRTUv2p12228Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 36 is set"
	::= { dpsRTUv2 12228 }

dpsRTUv2p13228Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 36 is cleared"
	::= { dpsRTUv2 13228 }

dpsRTUv2p12229Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 37 is set"
	::= { dpsRTUv2 12229 }

dpsRTUv2p13229Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 37 is cleared"
	::= { dpsRTUv2 13229 }

dpsRTUv2p12230Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 38 is set"
	::= { dpsRTUv2 12230 }

dpsRTUv2p13230Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 38 is cleared"
	::= { dpsRTUv2 13230 }

dpsRTUv2p12231Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 39 is set"
	::= { dpsRTUv2 12231 }

dpsRTUv2p13231Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 39 is cleared"
	::= { dpsRTUv2 13231 }

dpsRTUv2p12232Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 40 is set"
	::= { dpsRTUv2 12232 }

dpsRTUv2p13232Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 40 is cleared"
	::= { dpsRTUv2 13232 }

dpsRTUv2p12233Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 41 is set"
	::= { dpsRTUv2 12233 }

dpsRTUv2p13233Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 41 is cleared"
	::= { dpsRTUv2 13233 }

dpsRTUv2p12234Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 42 is set"
	::= { dpsRTUv2 12234 }

dpsRTUv2p13234Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 42 is cleared"
	::= { dpsRTUv2 13234 }

dpsRTUv2p12235Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 43 is set"
	::= { dpsRTUv2 12235 }

dpsRTUv2p13235Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 43 is cleared"
	::= { dpsRTUv2 13235 }

dpsRTUv2p12236Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 44 is set"
	::= { dpsRTUv2 12236 }

dpsRTUv2p13236Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 44 is cleared"
	::= { dpsRTUv2 13236 }

dpsRTUv2p12237Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 45 is set"
	::= { dpsRTUv2 12237 }

dpsRTUv2p13237Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 45 is cleared"
	::= { dpsRTUv2 13237 }

dpsRTUv2p12238Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 46 is set"
	::= { dpsRTUv2 12238 }

dpsRTUv2p13238Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 46 is cleared"
	::= { dpsRTUv2 13238 }

dpsRTUv2p12239Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 47 is set"
	::= { dpsRTUv2 12239 }

dpsRTUv2p13239Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 47 is cleared"
	::= { dpsRTUv2 13239 }

dpsRTUv2p12240Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 48 is set"
	::= { dpsRTUv2 12240 }

dpsRTUv2p13240Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 48 is cleared"
	::= { dpsRTUv2 13240 }

dpsRTUv2p12241Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 49 is set"
	::= { dpsRTUv2 12241 }

dpsRTUv2p13241Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 49 is cleared"
	::= { dpsRTUv2 13241 }

dpsRTUv2p12242Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 50 is set"
	::= { dpsRTUv2 12242 }

dpsRTUv2p13242Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 50 is cleared"
	::= { dpsRTUv2 13242 }

dpsRTUv2p12243Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 51 is set"
	::= { dpsRTUv2 12243 }

dpsRTUv2p13243Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 51 is cleared"
	::= { dpsRTUv2 13243 }

dpsRTUv2p12244Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 52 is set"
	::= { dpsRTUv2 12244 }

dpsRTUv2p13244Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 52 is cleared"
	::= { dpsRTUv2 13244 }

dpsRTUv2p12245Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 53 is set"
	::= { dpsRTUv2 12245 }

dpsRTUv2p13245Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 53 is cleared"
	::= { dpsRTUv2 13245 }

dpsRTUv2p12246Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 54 is set"
	::= { dpsRTUv2 12246 }

dpsRTUv2p13246Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 54 is cleared"
	::= { dpsRTUv2 13246 }

dpsRTUv2p12247Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 55 is set"
	::= { dpsRTUv2 12247 }

dpsRTUv2p13247Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 55 is cleared"
	::= { dpsRTUv2 13247 }

dpsRTUv2p12248Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 56 is set"
	::= { dpsRTUv2 12248 }

dpsRTUv2p13248Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 56 is cleared"
	::= { dpsRTUv2 13248 }

dpsRTUv2p12249Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 57 is set"
	::= { dpsRTUv2 12249 }

dpsRTUv2p13249Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 57 is cleared"
	::= { dpsRTUv2 13249 }

dpsRTUv2p12250Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 58 is set"
	::= { dpsRTUv2 12250 }

dpsRTUv2p13250Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 58 is cleared"
	::= { dpsRTUv2 13250 }

dpsRTUv2p12251Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 59 is set"
	::= { dpsRTUv2 12251 }

dpsRTUv2p13251Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 59 is cleared"
	::= { dpsRTUv2 13251 }

dpsRTUv2p12252Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 60 is set"
	::= { dpsRTUv2 12252 }

dpsRTUv2p13252Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 60 is cleared"
	::= { dpsRTUv2 13252 }

dpsRTUv2p12253Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 61 is set"
	::= { dpsRTUv2 12253 }

dpsRTUv2p13253Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 61 is cleared"
	::= { dpsRTUv2 13253 }

dpsRTUv2p12254Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 62 is set"
	::= { dpsRTUv2 12254 }

dpsRTUv2p13254Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 62 is cleared"
	::= { dpsRTUv2 13254 }

dpsRTUv2p12255Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 63 is set"
	::= { dpsRTUv2 12255 }

dpsRTUv2p13255Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 63 is cleared"
	::= { dpsRTUv2 13255 }

dpsRTUv2p12256Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 64 is set"
	::= { dpsRTUv2 12256 }

dpsRTUv2p13256Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 4 point 64 is cleared"
	::= { dpsRTUv2 13256 }

dpsRTUv2p12257Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 1 is set"
	::= { dpsRTUv2 12257 }

dpsRTUv2p13257Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 1 is cleared"
	::= { dpsRTUv2 13257 }

dpsRTUv2p12258Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 2 is set"
	::= { dpsRTUv2 12258 }

dpsRTUv2p13258Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 2 is cleared"
	::= { dpsRTUv2 13258 }

dpsRTUv2p12259Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 3 is set"
	::= { dpsRTUv2 12259 }

dpsRTUv2p13259Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 3 is cleared"
	::= { dpsRTUv2 13259 }

dpsRTUv2p12260Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 4 is set"
	::= { dpsRTUv2 12260 }

dpsRTUv2p13260Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 4 is cleared"
	::= { dpsRTUv2 13260 }

dpsRTUv2p12261Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 5 is set"
	::= { dpsRTUv2 12261 }

dpsRTUv2p13261Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 5 is cleared"
	::= { dpsRTUv2 13261 }

dpsRTUv2p12262Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 6 is set"
	::= { dpsRTUv2 12262 }

dpsRTUv2p13262Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 6 is cleared"
	::= { dpsRTUv2 13262 }

dpsRTUv2p12263Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 7 is set"
	::= { dpsRTUv2 12263 }

dpsRTUv2p13263Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 7 is cleared"
	::= { dpsRTUv2 13263 }

dpsRTUv2p12264Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 8 is set"
	::= { dpsRTUv2 12264 }

dpsRTUv2p13264Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 8 is cleared"
	::= { dpsRTUv2 13264 }

dpsRTUv2p12265Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 9 is set"
	::= { dpsRTUv2 12265 }

dpsRTUv2p13265Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 9 is cleared"
	::= { dpsRTUv2 13265 }

dpsRTUv2p12266Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 10 is set"
	::= { dpsRTUv2 12266 }

dpsRTUv2p13266Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 10 is cleared"
	::= { dpsRTUv2 13266 }

dpsRTUv2p12267Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 11 is set"
	::= { dpsRTUv2 12267 }

dpsRTUv2p13267Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 11 is cleared"
	::= { dpsRTUv2 13267 }

dpsRTUv2p12268Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 12 is set"
	::= { dpsRTUv2 12268 }

dpsRTUv2p13268Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 12 is cleared"
	::= { dpsRTUv2 13268 }

dpsRTUv2p12269Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 13 is set"
	::= { dpsRTUv2 12269 }

dpsRTUv2p13269Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 13 is cleared"
	::= { dpsRTUv2 13269 }

dpsRTUv2p12270Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 14 is set"
	::= { dpsRTUv2 12270 }

dpsRTUv2p13270Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 14 is cleared"
	::= { dpsRTUv2 13270 }

dpsRTUv2p12271Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 15 is set"
	::= { dpsRTUv2 12271 }

dpsRTUv2p13271Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 15 is cleared"
	::= { dpsRTUv2 13271 }

dpsRTUv2p12272Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 16 is set"
	::= { dpsRTUv2 12272 }

dpsRTUv2p13272Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 16 is cleared"
	::= { dpsRTUv2 13272 }

dpsRTUv2p12273Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 17 is set"
	::= { dpsRTUv2 12273 }

dpsRTUv2p13273Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 17 is cleared"
	::= { dpsRTUv2 13273 }

dpsRTUv2p12274Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 18 is set"
	::= { dpsRTUv2 12274 }

dpsRTUv2p13274Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 18 is cleared"
	::= { dpsRTUv2 13274 }

dpsRTUv2p12275Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 19 is set"
	::= { dpsRTUv2 12275 }

dpsRTUv2p13275Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 19 is cleared"
	::= { dpsRTUv2 13275 }

dpsRTUv2p12276Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 20 is set"
	::= { dpsRTUv2 12276 }

dpsRTUv2p13276Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 20 is cleared"
	::= { dpsRTUv2 13276 }

dpsRTUv2p12277Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 21 is set"
	::= { dpsRTUv2 12277 }

dpsRTUv2p13277Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 21 is cleared"
	::= { dpsRTUv2 13277 }

dpsRTUv2p12278Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 22 is set"
	::= { dpsRTUv2 12278 }

dpsRTUv2p13278Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 22 is cleared"
	::= { dpsRTUv2 13278 }

dpsRTUv2p12279Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 23 is set"
	::= { dpsRTUv2 12279 }

dpsRTUv2p13279Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 23 is cleared"
	::= { dpsRTUv2 13279 }

dpsRTUv2p12280Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 24 is set"
	::= { dpsRTUv2 12280 }

dpsRTUv2p13280Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 24 is cleared"
	::= { dpsRTUv2 13280 }

dpsRTUv2p12281Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 25 is set"
	::= { dpsRTUv2 12281 }

dpsRTUv2p13281Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 25 is cleared"
	::= { dpsRTUv2 13281 }

dpsRTUv2p12282Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 26 is set"
	::= { dpsRTUv2 12282 }

dpsRTUv2p13282Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 26 is cleared"
	::= { dpsRTUv2 13282 }

dpsRTUv2p12283Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 27 is set"
	::= { dpsRTUv2 12283 }

dpsRTUv2p13283Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 27 is cleared"
	::= { dpsRTUv2 13283 }

dpsRTUv2p12284Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 28 is set"
	::= { dpsRTUv2 12284 }

dpsRTUv2p13284Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 28 is cleared"
	::= { dpsRTUv2 13284 }

dpsRTUv2p12285Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 29 is set"
	::= { dpsRTUv2 12285 }

dpsRTUv2p13285Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 29 is cleared"
	::= { dpsRTUv2 13285 }

dpsRTUv2p12286Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 30 is set"
	::= { dpsRTUv2 12286 }

dpsRTUv2p13286Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 30 is cleared"
	::= { dpsRTUv2 13286 }

dpsRTUv2p12287Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 31 is set"
	::= { dpsRTUv2 12287 }

dpsRTUv2p13287Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 31 is cleared"
	::= { dpsRTUv2 13287 }

dpsRTUv2p12288Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 32 is set"
	::= { dpsRTUv2 12288 }

dpsRTUv2p13288Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 32 is cleared"
	::= { dpsRTUv2 13288 }

dpsRTUv2p12289Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 33 is set"
	::= { dpsRTUv2 12289 }

dpsRTUv2p13289Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 33 is cleared"
	::= { dpsRTUv2 13289 }

dpsRTUv2p12290Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 34 is set"
	::= { dpsRTUv2 12290 }

dpsRTUv2p13290Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 34 is cleared"
	::= { dpsRTUv2 13290 }

dpsRTUv2p12291Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 35 is set"
	::= { dpsRTUv2 12291 }

dpsRTUv2p13291Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 35 is cleared"
	::= { dpsRTUv2 13291 }

dpsRTUv2p12292Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 36 is set"
	::= { dpsRTUv2 12292 }

dpsRTUv2p13292Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 36 is cleared"
	::= { dpsRTUv2 13292 }

dpsRTUv2p12293Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 37 is set"
	::= { dpsRTUv2 12293 }

dpsRTUv2p13293Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 37 is cleared"
	::= { dpsRTUv2 13293 }

dpsRTUv2p12294Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 38 is set"
	::= { dpsRTUv2 12294 }

dpsRTUv2p13294Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 38 is cleared"
	::= { dpsRTUv2 13294 }

dpsRTUv2p12295Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 39 is set"
	::= { dpsRTUv2 12295 }

dpsRTUv2p13295Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 39 is cleared"
	::= { dpsRTUv2 13295 }

dpsRTUv2p12296Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 40 is set"
	::= { dpsRTUv2 12296 }

dpsRTUv2p13296Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 40 is cleared"
	::= { dpsRTUv2 13296 }

dpsRTUv2p12297Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 41 is set"
	::= { dpsRTUv2 12297 }

dpsRTUv2p13297Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 41 is cleared"
	::= { dpsRTUv2 13297 }

dpsRTUv2p12298Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 42 is set"
	::= { dpsRTUv2 12298 }

dpsRTUv2p13298Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 42 is cleared"
	::= { dpsRTUv2 13298 }

dpsRTUv2p12299Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 43 is set"
	::= { dpsRTUv2 12299 }

dpsRTUv2p13299Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 43 is cleared"
	::= { dpsRTUv2 13299 }

dpsRTUv2p12300Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 44 is set"
	::= { dpsRTUv2 12300 }

dpsRTUv2p13300Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 44 is cleared"
	::= { dpsRTUv2 13300 }

dpsRTUv2p12301Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 45 is set"
	::= { dpsRTUv2 12301 }

dpsRTUv2p13301Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 45 is cleared"
	::= { dpsRTUv2 13301 }

dpsRTUv2p12302Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 46 is set"
	::= { dpsRTUv2 12302 }

dpsRTUv2p13302Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 46 is cleared"
	::= { dpsRTUv2 13302 }

dpsRTUv2p12303Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 47 is set"
	::= { dpsRTUv2 12303 }

dpsRTUv2p13303Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 47 is cleared"
	::= { dpsRTUv2 13303 }

dpsRTUv2p12304Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 48 is set"
	::= { dpsRTUv2 12304 }

dpsRTUv2p13304Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 48 is cleared"
	::= { dpsRTUv2 13304 }

dpsRTUv2p12305Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 49 is set"
	::= { dpsRTUv2 12305 }

dpsRTUv2p13305Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 49 is cleared"
	::= { dpsRTUv2 13305 }

dpsRTUv2p12306Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 50 is set"
	::= { dpsRTUv2 12306 }

dpsRTUv2p13306Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 50 is cleared"
	::= { dpsRTUv2 13306 }

dpsRTUv2p12307Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 51 is set"
	::= { dpsRTUv2 12307 }

dpsRTUv2p13307Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 51 is cleared"
	::= { dpsRTUv2 13307 }

dpsRTUv2p12308Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 52 is set"
	::= { dpsRTUv2 12308 }

dpsRTUv2p13308Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 52 is cleared"
	::= { dpsRTUv2 13308 }

dpsRTUv2p12309Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 53 is set"
	::= { dpsRTUv2 12309 }

dpsRTUv2p13309Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 53 is cleared"
	::= { dpsRTUv2 13309 }

dpsRTUv2p12310Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 54 is set"
	::= { dpsRTUv2 12310 }

dpsRTUv2p13310Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 54 is cleared"
	::= { dpsRTUv2 13310 }

dpsRTUv2p12311Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 55 is set"
	::= { dpsRTUv2 12311 }

dpsRTUv2p13311Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 55 is cleared"
	::= { dpsRTUv2 13311 }

dpsRTUv2p12312Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 56 is set"
	::= { dpsRTUv2 12312 }

dpsRTUv2p13312Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 56 is cleared"
	::= { dpsRTUv2 13312 }

dpsRTUv2p12313Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 57 is set"
	::= { dpsRTUv2 12313 }

dpsRTUv2p13313Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 57 is cleared"
	::= { dpsRTUv2 13313 }

dpsRTUv2p12314Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 58 is set"
	::= { dpsRTUv2 12314 }

dpsRTUv2p13314Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 58 is cleared"
	::= { dpsRTUv2 13314 }

dpsRTUv2p12315Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 59 is set"
	::= { dpsRTUv2 12315 }

dpsRTUv2p13315Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 59 is cleared"
	::= { dpsRTUv2 13315 }

dpsRTUv2p12316Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 60 is set"
	::= { dpsRTUv2 12316 }

dpsRTUv2p13316Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 60 is cleared"
	::= { dpsRTUv2 13316 }

dpsRTUv2p12317Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 61 is set"
	::= { dpsRTUv2 12317 }

dpsRTUv2p13317Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 61 is cleared"
	::= { dpsRTUv2 13317 }

dpsRTUv2p12318Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 62 is set"
	::= { dpsRTUv2 12318 }

dpsRTUv2p13318Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 62 is cleared"
	::= { dpsRTUv2 13318 }

dpsRTUv2p12319Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 63 is set"
	::= { dpsRTUv2 12319 }

dpsRTUv2p13319Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 63 is cleared"
	::= { dpsRTUv2 13319 }

dpsRTUv2p12320Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 64 is set"
	::= { dpsRTUv2 12320 }

dpsRTUv2p13320Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 5 point 64 is cleared"
	::= { dpsRTUv2 13320 }

dpsRTUv2p12321Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 1 is set"
	::= { dpsRTUv2 12321 }

dpsRTUv2p13321Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 1 is cleared"
	::= { dpsRTUv2 13321 }

dpsRTUv2p12322Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 2 is set"
	::= { dpsRTUv2 12322 }

dpsRTUv2p13322Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 2 is cleared"
	::= { dpsRTUv2 13322 }

dpsRTUv2p12323Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 3 is set"
	::= { dpsRTUv2 12323 }

dpsRTUv2p13323Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 3 is cleared"
	::= { dpsRTUv2 13323 }

dpsRTUv2p12324Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 4 is set"
	::= { dpsRTUv2 12324 }

dpsRTUv2p13324Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 4 is cleared"
	::= { dpsRTUv2 13324 }

dpsRTUv2p12325Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 5 is set"
	::= { dpsRTUv2 12325 }

dpsRTUv2p13325Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 5 is cleared"
	::= { dpsRTUv2 13325 }

dpsRTUv2p12326Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 6 is set"
	::= { dpsRTUv2 12326 }

dpsRTUv2p13326Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 6 is cleared"
	::= { dpsRTUv2 13326 }

dpsRTUv2p12327Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 7 is set"
	::= { dpsRTUv2 12327 }

dpsRTUv2p13327Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 7 is cleared"
	::= { dpsRTUv2 13327 }

dpsRTUv2p12328Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 8 is set"
	::= { dpsRTUv2 12328 }

dpsRTUv2p13328Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 8 is cleared"
	::= { dpsRTUv2 13328 }

dpsRTUv2p12329Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 9 is set"
	::= { dpsRTUv2 12329 }

dpsRTUv2p13329Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 9 is cleared"
	::= { dpsRTUv2 13329 }

dpsRTUv2p12330Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 10 is set"
	::= { dpsRTUv2 12330 }

dpsRTUv2p13330Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 10 is cleared"
	::= { dpsRTUv2 13330 }

dpsRTUv2p12331Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 11 is set"
	::= { dpsRTUv2 12331 }

dpsRTUv2p13331Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 11 is cleared"
	::= { dpsRTUv2 13331 }

dpsRTUv2p12332Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 12 is set"
	::= { dpsRTUv2 12332 }

dpsRTUv2p13332Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 12 is cleared"
	::= { dpsRTUv2 13332 }

dpsRTUv2p12333Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 13 is set"
	::= { dpsRTUv2 12333 }

dpsRTUv2p13333Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 13 is cleared"
	::= { dpsRTUv2 13333 }

dpsRTUv2p12334Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 14 is set"
	::= { dpsRTUv2 12334 }

dpsRTUv2p13334Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 14 is cleared"
	::= { dpsRTUv2 13334 }

dpsRTUv2p12335Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 15 is set"
	::= { dpsRTUv2 12335 }

dpsRTUv2p13335Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 15 is cleared"
	::= { dpsRTUv2 13335 }

dpsRTUv2p12336Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 16 is set"
	::= { dpsRTUv2 12336 }

dpsRTUv2p13336Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 16 is cleared"
	::= { dpsRTUv2 13336 }

dpsRTUv2p12337Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 17 is set"
	::= { dpsRTUv2 12337 }

dpsRTUv2p13337Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 17 is cleared"
	::= { dpsRTUv2 13337 }

dpsRTUv2p12338Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 18 is set"
	::= { dpsRTUv2 12338 }

dpsRTUv2p13338Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 18 is cleared"
	::= { dpsRTUv2 13338 }

dpsRTUv2p12339Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 19 is set"
	::= { dpsRTUv2 12339 }

dpsRTUv2p13339Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 19 is cleared"
	::= { dpsRTUv2 13339 }

dpsRTUv2p12340Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 20 is set"
	::= { dpsRTUv2 12340 }

dpsRTUv2p13340Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 20 is cleared"
	::= { dpsRTUv2 13340 }

dpsRTUv2p12341Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 21 is set"
	::= { dpsRTUv2 12341 }

dpsRTUv2p13341Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 21 is cleared"
	::= { dpsRTUv2 13341 }

dpsRTUv2p12342Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 22 is set"
	::= { dpsRTUv2 12342 }

dpsRTUv2p13342Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 22 is cleared"
	::= { dpsRTUv2 13342 }

dpsRTUv2p12343Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 23 is set"
	::= { dpsRTUv2 12343 }

dpsRTUv2p13343Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 23 is cleared"
	::= { dpsRTUv2 13343 }

dpsRTUv2p12344Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 24 is set"
	::= { dpsRTUv2 12344 }

dpsRTUv2p13344Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 24 is cleared"
	::= { dpsRTUv2 13344 }

dpsRTUv2p12345Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 25 is set"
	::= { dpsRTUv2 12345 }

dpsRTUv2p13345Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 25 is cleared"
	::= { dpsRTUv2 13345 }

dpsRTUv2p12346Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 26 is set"
	::= { dpsRTUv2 12346 }

dpsRTUv2p13346Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 26 is cleared"
	::= { dpsRTUv2 13346 }

dpsRTUv2p12347Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 27 is set"
	::= { dpsRTUv2 12347 }

dpsRTUv2p13347Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 27 is cleared"
	::= { dpsRTUv2 13347 }

dpsRTUv2p12348Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 28 is set"
	::= { dpsRTUv2 12348 }

dpsRTUv2p13348Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 28 is cleared"
	::= { dpsRTUv2 13348 }

dpsRTUv2p12349Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 29 is set"
	::= { dpsRTUv2 12349 }

dpsRTUv2p13349Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 29 is cleared"
	::= { dpsRTUv2 13349 }

dpsRTUv2p12350Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 30 is set"
	::= { dpsRTUv2 12350 }

dpsRTUv2p13350Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 30 is cleared"
	::= { dpsRTUv2 13350 }

dpsRTUv2p12351Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 31 is set"
	::= { dpsRTUv2 12351 }

dpsRTUv2p13351Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 31 is cleared"
	::= { dpsRTUv2 13351 }

dpsRTUv2p12352Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 32 is set"
	::= { dpsRTUv2 12352 }

dpsRTUv2p13352Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 32 is cleared"
	::= { dpsRTUv2 13352 }

dpsRTUv2p12353Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 33 is set"
	::= { dpsRTUv2 12353 }

dpsRTUv2p13353Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 33 is cleared"
	::= { dpsRTUv2 13353 }

dpsRTUv2p12354Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 34 is set"
	::= { dpsRTUv2 12354 }

dpsRTUv2p13354Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 34 is cleared"
	::= { dpsRTUv2 13354 }

dpsRTUv2p12355Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 35 is set"
	::= { dpsRTUv2 12355 }

dpsRTUv2p13355Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 35 is cleared"
	::= { dpsRTUv2 13355 }

dpsRTUv2p12356Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 36 is set"
	::= { dpsRTUv2 12356 }

dpsRTUv2p13356Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 36 is cleared"
	::= { dpsRTUv2 13356 }

dpsRTUv2p12357Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 37 is set"
	::= { dpsRTUv2 12357 }

dpsRTUv2p13357Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 37 is cleared"
	::= { dpsRTUv2 13357 }

dpsRTUv2p12358Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 38 is set"
	::= { dpsRTUv2 12358 }

dpsRTUv2p13358Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 38 is cleared"
	::= { dpsRTUv2 13358 }

dpsRTUv2p12359Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 39 is set"
	::= { dpsRTUv2 12359 }

dpsRTUv2p13359Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 39 is cleared"
	::= { dpsRTUv2 13359 }

dpsRTUv2p12360Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 40 is set"
	::= { dpsRTUv2 12360 }

dpsRTUv2p13360Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 40 is cleared"
	::= { dpsRTUv2 13360 }

dpsRTUv2p12361Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 41 is set"
	::= { dpsRTUv2 12361 }

dpsRTUv2p13361Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 41 is cleared"
	::= { dpsRTUv2 13361 }

dpsRTUv2p12362Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 42 is set"
	::= { dpsRTUv2 12362 }

dpsRTUv2p13362Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 42 is cleared"
	::= { dpsRTUv2 13362 }

dpsRTUv2p12363Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 43 is set"
	::= { dpsRTUv2 12363 }

dpsRTUv2p13363Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 43 is cleared"
	::= { dpsRTUv2 13363 }

dpsRTUv2p12364Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 44 is set"
	::= { dpsRTUv2 12364 }

dpsRTUv2p13364Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 44 is cleared"
	::= { dpsRTUv2 13364 }

dpsRTUv2p12365Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 45 is set"
	::= { dpsRTUv2 12365 }

dpsRTUv2p13365Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 45 is cleared"
	::= { dpsRTUv2 13365 }

dpsRTUv2p12366Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 46 is set"
	::= { dpsRTUv2 12366 }

dpsRTUv2p13366Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 46 is cleared"
	::= { dpsRTUv2 13366 }

dpsRTUv2p12367Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 47 is set"
	::= { dpsRTUv2 12367 }

dpsRTUv2p13367Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 47 is cleared"
	::= { dpsRTUv2 13367 }

dpsRTUv2p12368Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 48 is set"
	::= { dpsRTUv2 12368 }

dpsRTUv2p13368Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 48 is cleared"
	::= { dpsRTUv2 13368 }

dpsRTUv2p12369Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 49 is set"
	::= { dpsRTUv2 12369 }

dpsRTUv2p13369Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 49 is cleared"
	::= { dpsRTUv2 13369 }

dpsRTUv2p12370Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 50 is set"
	::= { dpsRTUv2 12370 }

dpsRTUv2p13370Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 50 is cleared"
	::= { dpsRTUv2 13370 }

dpsRTUv2p12371Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 51 is set"
	::= { dpsRTUv2 12371 }

dpsRTUv2p13371Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 51 is cleared"
	::= { dpsRTUv2 13371 }

dpsRTUv2p12372Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 52 is set"
	::= { dpsRTUv2 12372 }

dpsRTUv2p13372Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 52 is cleared"
	::= { dpsRTUv2 13372 }

dpsRTUv2p12373Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 53 is set"
	::= { dpsRTUv2 12373 }

dpsRTUv2p13373Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 53 is cleared"
	::= { dpsRTUv2 13373 }

dpsRTUv2p12374Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 54 is set"
	::= { dpsRTUv2 12374 }

dpsRTUv2p13374Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 54 is cleared"
	::= { dpsRTUv2 13374 }

dpsRTUv2p12375Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 55 is set"
	::= { dpsRTUv2 12375 }

dpsRTUv2p13375Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 55 is cleared"
	::= { dpsRTUv2 13375 }

dpsRTUv2p12376Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 56 is set"
	::= { dpsRTUv2 12376 }

dpsRTUv2p13376Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 56 is cleared"
	::= { dpsRTUv2 13376 }

dpsRTUv2p12377Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 57 is set"
	::= { dpsRTUv2 12377 }

dpsRTUv2p13377Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 57 is cleared"
	::= { dpsRTUv2 13377 }

dpsRTUv2p12378Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 58 is set"
	::= { dpsRTUv2 12378 }

dpsRTUv2p13378Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 58 is cleared"
	::= { dpsRTUv2 13378 }

dpsRTUv2p12379Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 59 is set"
	::= { dpsRTUv2 12379 }

dpsRTUv2p13379Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 59 is cleared"
	::= { dpsRTUv2 13379 }

dpsRTUv2p12380Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 60 is set"
	::= { dpsRTUv2 12380 }

dpsRTUv2p13380Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 60 is cleared"
	::= { dpsRTUv2 13380 }

dpsRTUv2p12381Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 61 is set"
	::= { dpsRTUv2 12381 }

dpsRTUv2p13381Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 61 is cleared"
	::= { dpsRTUv2 13381 }

dpsRTUv2p12382Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 62 is set"
	::= { dpsRTUv2 12382 }

dpsRTUv2p13382Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 62 is cleared"
	::= { dpsRTUv2 13382 }

dpsRTUv2p12383Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 63 is set"
	::= { dpsRTUv2 12383 }

dpsRTUv2p13383Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 63 is cleared"
	::= { dpsRTUv2 13383 }

dpsRTUv2p12384Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 64 is set"
	::= { dpsRTUv2 12384 }

dpsRTUv2p13384Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 6 point 64 is cleared"
	::= { dpsRTUv2 13384 }

dpsRTUv2p12385Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 1 is set"
	::= { dpsRTUv2 12385 }

dpsRTUv2p13385Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 1 is cleared"
	::= { dpsRTUv2 13385 }

dpsRTUv2p12386Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 2 is set"
	::= { dpsRTUv2 12386 }

dpsRTUv2p13386Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 2 is cleared"
	::= { dpsRTUv2 13386 }

dpsRTUv2p12387Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 3 is set"
	::= { dpsRTUv2 12387 }

dpsRTUv2p13387Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 3 is cleared"
	::= { dpsRTUv2 13387 }

dpsRTUv2p12388Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 4 is set"
	::= { dpsRTUv2 12388 }

dpsRTUv2p13388Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 4 is cleared"
	::= { dpsRTUv2 13388 }

dpsRTUv2p12389Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 5 is set"
	::= { dpsRTUv2 12389 }

dpsRTUv2p13389Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 5 is cleared"
	::= { dpsRTUv2 13389 }

dpsRTUv2p12390Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 6 is set"
	::= { dpsRTUv2 12390 }

dpsRTUv2p13390Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 6 is cleared"
	::= { dpsRTUv2 13390 }

dpsRTUv2p12391Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 7 is set"
	::= { dpsRTUv2 12391 }

dpsRTUv2p13391Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 7 is cleared"
	::= { dpsRTUv2 13391 }

dpsRTUv2p12392Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 8 is set"
	::= { dpsRTUv2 12392 }

dpsRTUv2p13392Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 8 is cleared"
	::= { dpsRTUv2 13392 }

dpsRTUv2p12393Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 9 is set"
	::= { dpsRTUv2 12393 }

dpsRTUv2p13393Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 9 is cleared"
	::= { dpsRTUv2 13393 }

dpsRTUv2p12394Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 10 is set"
	::= { dpsRTUv2 12394 }

dpsRTUv2p13394Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 10 is cleared"
	::= { dpsRTUv2 13394 }

dpsRTUv2p12395Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 11 is set"
	::= { dpsRTUv2 12395 }

dpsRTUv2p13395Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 11 is cleared"
	::= { dpsRTUv2 13395 }

dpsRTUv2p12396Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 12 is set"
	::= { dpsRTUv2 12396 }

dpsRTUv2p13396Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 12 is cleared"
	::= { dpsRTUv2 13396 }

dpsRTUv2p12397Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 13 is set"
	::= { dpsRTUv2 12397 }

dpsRTUv2p13397Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 13 is cleared"
	::= { dpsRTUv2 13397 }

dpsRTUv2p12398Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 14 is set"
	::= { dpsRTUv2 12398 }

dpsRTUv2p13398Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 14 is cleared"
	::= { dpsRTUv2 13398 }

dpsRTUv2p12399Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 15 is set"
	::= { dpsRTUv2 12399 }

dpsRTUv2p13399Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 15 is cleared"
	::= { dpsRTUv2 13399 }

dpsRTUv2p12400Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 16 is set"
	::= { dpsRTUv2 12400 }

dpsRTUv2p13400Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 16 is cleared"
	::= { dpsRTUv2 13400 }

dpsRTUv2p12401Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 17 is set"
	::= { dpsRTUv2 12401 }

dpsRTUv2p13401Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 17 is cleared"
	::= { dpsRTUv2 13401 }

dpsRTUv2p12402Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 18 is set"
	::= { dpsRTUv2 12402 }

dpsRTUv2p13402Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 18 is cleared"
	::= { dpsRTUv2 13402 }

dpsRTUv2p12403Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 19 is set"
	::= { dpsRTUv2 12403 }

dpsRTUv2p13403Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 19 is cleared"
	::= { dpsRTUv2 13403 }

dpsRTUv2p12404Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 20 is set"
	::= { dpsRTUv2 12404 }

dpsRTUv2p13404Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 20 is cleared"
	::= { dpsRTUv2 13404 }

dpsRTUv2p12405Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 21 is set"
	::= { dpsRTUv2 12405 }

dpsRTUv2p13405Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 21 is cleared"
	::= { dpsRTUv2 13405 }

dpsRTUv2p12406Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 22 is set"
	::= { dpsRTUv2 12406 }

dpsRTUv2p13406Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 22 is cleared"
	::= { dpsRTUv2 13406 }

dpsRTUv2p12407Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 23 is set"
	::= { dpsRTUv2 12407 }

dpsRTUv2p13407Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 23 is cleared"
	::= { dpsRTUv2 13407 }

dpsRTUv2p12408Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 24 is set"
	::= { dpsRTUv2 12408 }

dpsRTUv2p13408Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 24 is cleared"
	::= { dpsRTUv2 13408 }

dpsRTUv2p12409Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 25 is set"
	::= { dpsRTUv2 12409 }

dpsRTUv2p13409Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 25 is cleared"
	::= { dpsRTUv2 13409 }

dpsRTUv2p12410Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 26 is set"
	::= { dpsRTUv2 12410 }

dpsRTUv2p13410Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 26 is cleared"
	::= { dpsRTUv2 13410 }

dpsRTUv2p12411Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 27 is set"
	::= { dpsRTUv2 12411 }

dpsRTUv2p13411Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 27 is cleared"
	::= { dpsRTUv2 13411 }

dpsRTUv2p12412Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 28 is set"
	::= { dpsRTUv2 12412 }

dpsRTUv2p13412Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 28 is cleared"
	::= { dpsRTUv2 13412 }

dpsRTUv2p12413Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 29 is set"
	::= { dpsRTUv2 12413 }

dpsRTUv2p13413Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 29 is cleared"
	::= { dpsRTUv2 13413 }

dpsRTUv2p12414Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 30 is set"
	::= { dpsRTUv2 12414 }

dpsRTUv2p13414Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 30 is cleared"
	::= { dpsRTUv2 13414 }

dpsRTUv2p12415Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 31 is set"
	::= { dpsRTUv2 12415 }

dpsRTUv2p13415Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 31 is cleared"
	::= { dpsRTUv2 13415 }

dpsRTUv2p12416Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 32 is set"
	::= { dpsRTUv2 12416 }

dpsRTUv2p13416Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 32 is cleared"
	::= { dpsRTUv2 13416 }

dpsRTUv2p12417Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 33 is set"
	::= { dpsRTUv2 12417 }

dpsRTUv2p13417Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 33 is cleared"
	::= { dpsRTUv2 13417 }

dpsRTUv2p12418Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 34 is set"
	::= { dpsRTUv2 12418 }

dpsRTUv2p13418Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 34 is cleared"
	::= { dpsRTUv2 13418 }

dpsRTUv2p12419Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 35 is set"
	::= { dpsRTUv2 12419 }

dpsRTUv2p13419Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 35 is cleared"
	::= { dpsRTUv2 13419 }

dpsRTUv2p12420Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 36 is set"
	::= { dpsRTUv2 12420 }

dpsRTUv2p13420Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 36 is cleared"
	::= { dpsRTUv2 13420 }

dpsRTUv2p12421Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 37 is set"
	::= { dpsRTUv2 12421 }

dpsRTUv2p13421Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 37 is cleared"
	::= { dpsRTUv2 13421 }

dpsRTUv2p12422Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 38 is set"
	::= { dpsRTUv2 12422 }

dpsRTUv2p13422Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 38 is cleared"
	::= { dpsRTUv2 13422 }

dpsRTUv2p12423Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 39 is set"
	::= { dpsRTUv2 12423 }

dpsRTUv2p13423Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 39 is cleared"
	::= { dpsRTUv2 13423 }

dpsRTUv2p12424Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 40 is set"
	::= { dpsRTUv2 12424 }

dpsRTUv2p13424Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 40 is cleared"
	::= { dpsRTUv2 13424 }

dpsRTUv2p12425Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 41 is set"
	::= { dpsRTUv2 12425 }

dpsRTUv2p13425Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 41 is cleared"
	::= { dpsRTUv2 13425 }

dpsRTUv2p12426Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 42 is set"
	::= { dpsRTUv2 12426 }

dpsRTUv2p13426Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 42 is cleared"
	::= { dpsRTUv2 13426 }

dpsRTUv2p12427Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 43 is set"
	::= { dpsRTUv2 12427 }

dpsRTUv2p13427Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 43 is cleared"
	::= { dpsRTUv2 13427 }

dpsRTUv2p12428Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 44 is set"
	::= { dpsRTUv2 12428 }

dpsRTUv2p13428Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 44 is cleared"
	::= { dpsRTUv2 13428 }

dpsRTUv2p12429Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 45 is set"
	::= { dpsRTUv2 12429 }

dpsRTUv2p13429Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 45 is cleared"
	::= { dpsRTUv2 13429 }

dpsRTUv2p12430Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 46 is set"
	::= { dpsRTUv2 12430 }

dpsRTUv2p13430Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 46 is cleared"
	::= { dpsRTUv2 13430 }

dpsRTUv2p12431Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 47 is set"
	::= { dpsRTUv2 12431 }

dpsRTUv2p13431Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 47 is cleared"
	::= { dpsRTUv2 13431 }

dpsRTUv2p12432Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 48 is set"
	::= { dpsRTUv2 12432 }

dpsRTUv2p13432Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 48 is cleared"
	::= { dpsRTUv2 13432 }

dpsRTUv2p12433Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 49 is set"
	::= { dpsRTUv2 12433 }

dpsRTUv2p13433Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 49 is cleared"
	::= { dpsRTUv2 13433 }

dpsRTUv2p12434Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 50 is set"
	::= { dpsRTUv2 12434 }

dpsRTUv2p13434Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 50 is cleared"
	::= { dpsRTUv2 13434 }

dpsRTUv2p12435Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 51 is set"
	::= { dpsRTUv2 12435 }

dpsRTUv2p13435Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 51 is cleared"
	::= { dpsRTUv2 13435 }

dpsRTUv2p12436Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 52 is set"
	::= { dpsRTUv2 12436 }

dpsRTUv2p13436Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 52 is cleared"
	::= { dpsRTUv2 13436 }

dpsRTUv2p12437Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 53 is set"
	::= { dpsRTUv2 12437 }

dpsRTUv2p13437Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 53 is cleared"
	::= { dpsRTUv2 13437 }

dpsRTUv2p12438Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 54 is set"
	::= { dpsRTUv2 12438 }

dpsRTUv2p13438Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 54 is cleared"
	::= { dpsRTUv2 13438 }

dpsRTUv2p12439Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 55 is set"
	::= { dpsRTUv2 12439 }

dpsRTUv2p13439Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 55 is cleared"
	::= { dpsRTUv2 13439 }

dpsRTUv2p12440Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 56 is set"
	::= { dpsRTUv2 12440 }

dpsRTUv2p13440Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 56 is cleared"
	::= { dpsRTUv2 13440 }

dpsRTUv2p12441Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 57 is set"
	::= { dpsRTUv2 12441 }

dpsRTUv2p13441Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 57 is cleared"
	::= { dpsRTUv2 13441 }

dpsRTUv2p12442Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 58 is set"
	::= { dpsRTUv2 12442 }

dpsRTUv2p13442Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 58 is cleared"
	::= { dpsRTUv2 13442 }

dpsRTUv2p12443Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 59 is set"
	::= { dpsRTUv2 12443 }

dpsRTUv2p13443Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 59 is cleared"
	::= { dpsRTUv2 13443 }

dpsRTUv2p12444Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 60 is set"
	::= { dpsRTUv2 12444 }

dpsRTUv2p13444Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 60 is cleared"
	::= { dpsRTUv2 13444 }

dpsRTUv2p12445Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 61 is set"
	::= { dpsRTUv2 12445 }

dpsRTUv2p13445Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 61 is cleared"
	::= { dpsRTUv2 13445 }

dpsRTUv2p12446Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 62 is set"
	::= { dpsRTUv2 12446 }

dpsRTUv2p13446Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 62 is cleared"
	::= { dpsRTUv2 13446 }

dpsRTUv2p12447Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 63 is set"
	::= { dpsRTUv2 12447 }

dpsRTUv2p13447Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 63 is cleared"
	::= { dpsRTUv2 13447 }

dpsRTUv2p12448Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 64 is set"
	::= { dpsRTUv2 12448 }

dpsRTUv2p13448Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 7 point 64 is cleared"
	::= { dpsRTUv2 13448 }

dpsRTUv2p12449Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 1 is set"
	::= { dpsRTUv2 12449 }

dpsRTUv2p13449Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 1 is cleared"
	::= { dpsRTUv2 13449 }

dpsRTUv2p12450Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 2 is set"
	::= { dpsRTUv2 12450 }

dpsRTUv2p13450Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 2 is cleared"
	::= { dpsRTUv2 13450 }

dpsRTUv2p12451Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 3 is set"
	::= { dpsRTUv2 12451 }

dpsRTUv2p13451Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 3 is cleared"
	::= { dpsRTUv2 13451 }

dpsRTUv2p12452Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 4 is set"
	::= { dpsRTUv2 12452 }

dpsRTUv2p13452Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 4 is cleared"
	::= { dpsRTUv2 13452 }

dpsRTUv2p12453Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 5 is set"
	::= { dpsRTUv2 12453 }

dpsRTUv2p13453Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 5 is cleared"
	::= { dpsRTUv2 13453 }

dpsRTUv2p12454Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 6 is set"
	::= { dpsRTUv2 12454 }

dpsRTUv2p13454Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 6 is cleared"
	::= { dpsRTUv2 13454 }

dpsRTUv2p12455Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 7 is set"
	::= { dpsRTUv2 12455 }

dpsRTUv2p13455Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 7 is cleared"
	::= { dpsRTUv2 13455 }

dpsRTUv2p12456Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 8 is set"
	::= { dpsRTUv2 12456 }

dpsRTUv2p13456Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 8 is cleared"
	::= { dpsRTUv2 13456 }

dpsRTUv2p12457Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 9 is set"
	::= { dpsRTUv2 12457 }

dpsRTUv2p13457Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 9 is cleared"
	::= { dpsRTUv2 13457 }

dpsRTUv2p12458Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 10 is set"
	::= { dpsRTUv2 12458 }

dpsRTUv2p13458Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 10 is cleared"
	::= { dpsRTUv2 13458 }

dpsRTUv2p12459Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 11 is set"
	::= { dpsRTUv2 12459 }

dpsRTUv2p13459Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 11 is cleared"
	::= { dpsRTUv2 13459 }

dpsRTUv2p12460Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 12 is set"
	::= { dpsRTUv2 12460 }

dpsRTUv2p13460Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 12 is cleared"
	::= { dpsRTUv2 13460 }

dpsRTUv2p12461Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 13 is set"
	::= { dpsRTUv2 12461 }

dpsRTUv2p13461Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 13 is cleared"
	::= { dpsRTUv2 13461 }

dpsRTUv2p12462Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 14 is set"
	::= { dpsRTUv2 12462 }

dpsRTUv2p13462Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 14 is cleared"
	::= { dpsRTUv2 13462 }

dpsRTUv2p12463Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 15 is set"
	::= { dpsRTUv2 12463 }

dpsRTUv2p13463Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 15 is cleared"
	::= { dpsRTUv2 13463 }

dpsRTUv2p12464Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 16 is set"
	::= { dpsRTUv2 12464 }

dpsRTUv2p13464Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 16 is cleared"
	::= { dpsRTUv2 13464 }

dpsRTUv2p12465Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 17 is set"
	::= { dpsRTUv2 12465 }

dpsRTUv2p13465Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 17 is cleared"
	::= { dpsRTUv2 13465 }

dpsRTUv2p12466Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 18 is set"
	::= { dpsRTUv2 12466 }

dpsRTUv2p13466Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 18 is cleared"
	::= { dpsRTUv2 13466 }

dpsRTUv2p12467Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 19 is set"
	::= { dpsRTUv2 12467 }

dpsRTUv2p13467Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 19 is cleared"
	::= { dpsRTUv2 13467 }

dpsRTUv2p12468Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 20 is set"
	::= { dpsRTUv2 12468 }

dpsRTUv2p13468Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 20 is cleared"
	::= { dpsRTUv2 13468 }

dpsRTUv2p12469Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 21 is set"
	::= { dpsRTUv2 12469 }

dpsRTUv2p13469Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 21 is cleared"
	::= { dpsRTUv2 13469 }

dpsRTUv2p12470Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 22 is set"
	::= { dpsRTUv2 12470 }

dpsRTUv2p13470Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 22 is cleared"
	::= { dpsRTUv2 13470 }

dpsRTUv2p12471Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 23 is set"
	::= { dpsRTUv2 12471 }

dpsRTUv2p13471Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 23 is cleared"
	::= { dpsRTUv2 13471 }

dpsRTUv2p12472Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 24 is set"
	::= { dpsRTUv2 12472 }

dpsRTUv2p13472Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 24 is cleared"
	::= { dpsRTUv2 13472 }

dpsRTUv2p12473Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 25 is set"
	::= { dpsRTUv2 12473 }

dpsRTUv2p13473Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 25 is cleared"
	::= { dpsRTUv2 13473 }

dpsRTUv2p12474Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 26 is set"
	::= { dpsRTUv2 12474 }

dpsRTUv2p13474Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 26 is cleared"
	::= { dpsRTUv2 13474 }

dpsRTUv2p12475Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 27 is set"
	::= { dpsRTUv2 12475 }

dpsRTUv2p13475Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 27 is cleared"
	::= { dpsRTUv2 13475 }

dpsRTUv2p12476Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 28 is set"
	::= { dpsRTUv2 12476 }

dpsRTUv2p13476Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 28 is cleared"
	::= { dpsRTUv2 13476 }

dpsRTUv2p12477Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 29 is set"
	::= { dpsRTUv2 12477 }

dpsRTUv2p13477Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 29 is cleared"
	::= { dpsRTUv2 13477 }

dpsRTUv2p12478Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 30 is set"
	::= { dpsRTUv2 12478 }

dpsRTUv2p13478Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 30 is cleared"
	::= { dpsRTUv2 13478 }

dpsRTUv2p12479Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 31 is set"
	::= { dpsRTUv2 12479 }

dpsRTUv2p13479Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 31 is cleared"
	::= { dpsRTUv2 13479 }

dpsRTUv2p12480Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 32 is set"
	::= { dpsRTUv2 12480 }

dpsRTUv2p13480Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 32 is cleared"
	::= { dpsRTUv2 13480 }

dpsRTUv2p12481Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 33 is set"
	::= { dpsRTUv2 12481 }

dpsRTUv2p13481Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 33 is cleared"
	::= { dpsRTUv2 13481 }

dpsRTUv2p12482Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 34 is set"
	::= { dpsRTUv2 12482 }

dpsRTUv2p13482Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 34 is cleared"
	::= { dpsRTUv2 13482 }

dpsRTUv2p12483Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 35 is set"
	::= { dpsRTUv2 12483 }

dpsRTUv2p13483Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 35 is cleared"
	::= { dpsRTUv2 13483 }

dpsRTUv2p12484Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 36 is set"
	::= { dpsRTUv2 12484 }

dpsRTUv2p13484Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 36 is cleared"
	::= { dpsRTUv2 13484 }

dpsRTUv2p12485Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 37 is set"
	::= { dpsRTUv2 12485 }

dpsRTUv2p13485Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 37 is cleared"
	::= { dpsRTUv2 13485 }

dpsRTUv2p12486Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 38 is set"
	::= { dpsRTUv2 12486 }

dpsRTUv2p13486Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 38 is cleared"
	::= { dpsRTUv2 13486 }

dpsRTUv2p12487Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 39 is set"
	::= { dpsRTUv2 12487 }

dpsRTUv2p13487Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 39 is cleared"
	::= { dpsRTUv2 13487 }

dpsRTUv2p12488Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 40 is set"
	::= { dpsRTUv2 12488 }

dpsRTUv2p13488Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 40 is cleared"
	::= { dpsRTUv2 13488 }

dpsRTUv2p12489Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 41 is set"
	::= { dpsRTUv2 12489 }

dpsRTUv2p13489Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 41 is cleared"
	::= { dpsRTUv2 13489 }

dpsRTUv2p12490Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 42 is set"
	::= { dpsRTUv2 12490 }

dpsRTUv2p13490Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 42 is cleared"
	::= { dpsRTUv2 13490 }

dpsRTUv2p12491Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 43 is set"
	::= { dpsRTUv2 12491 }

dpsRTUv2p13491Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 43 is cleared"
	::= { dpsRTUv2 13491 }

dpsRTUv2p12492Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 44 is set"
	::= { dpsRTUv2 12492 }

dpsRTUv2p13492Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 44 is cleared"
	::= { dpsRTUv2 13492 }

dpsRTUv2p12493Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 45 is set"
	::= { dpsRTUv2 12493 }

dpsRTUv2p13493Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 45 is cleared"
	::= { dpsRTUv2 13493 }

dpsRTUv2p12494Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 46 is set"
	::= { dpsRTUv2 12494 }

dpsRTUv2p13494Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 46 is cleared"
	::= { dpsRTUv2 13494 }

dpsRTUv2p12495Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 47 is set"
	::= { dpsRTUv2 12495 }

dpsRTUv2p13495Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 47 is cleared"
	::= { dpsRTUv2 13495 }

dpsRTUv2p12496Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 48 is set"
	::= { dpsRTUv2 12496 }

dpsRTUv2p13496Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 48 is cleared"
	::= { dpsRTUv2 13496 }

dpsRTUv2p12497Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 49 is set"
	::= { dpsRTUv2 12497 }

dpsRTUv2p13497Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 49 is cleared"
	::= { dpsRTUv2 13497 }

dpsRTUv2p12498Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 50 is set"
	::= { dpsRTUv2 12498 }

dpsRTUv2p13498Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 50 is cleared"
	::= { dpsRTUv2 13498 }

dpsRTUv2p12499Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 51 is set"
	::= { dpsRTUv2 12499 }

dpsRTUv2p13499Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 51 is cleared"
	::= { dpsRTUv2 13499 }

dpsRTUv2p12500Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 52 is set"
	::= { dpsRTUv2 12500 }

dpsRTUv2p13500Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 52 is cleared"
	::= { dpsRTUv2 13500 }

dpsRTUv2p12501Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 53 is set"
	::= { dpsRTUv2 12501 }

dpsRTUv2p13501Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 53 is cleared"
	::= { dpsRTUv2 13501 }

dpsRTUv2p12502Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 54 is set"
	::= { dpsRTUv2 12502 }

dpsRTUv2p13502Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 54 is cleared"
	::= { dpsRTUv2 13502 }

dpsRTUv2p12503Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 55 is set"
	::= { dpsRTUv2 12503 }

dpsRTUv2p13503Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 55 is cleared"
	::= { dpsRTUv2 13503 }

dpsRTUv2p12504Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 56 is set"
	::= { dpsRTUv2 12504 }

dpsRTUv2p13504Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 56 is cleared"
	::= { dpsRTUv2 13504 }

dpsRTUv2p12505Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 57 is set"
	::= { dpsRTUv2 12505 }

dpsRTUv2p13505Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 57 is cleared"
	::= { dpsRTUv2 13505 }

dpsRTUv2p12506Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 58 is set"
	::= { dpsRTUv2 12506 }

dpsRTUv2p13506Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 58 is cleared"
	::= { dpsRTUv2 13506 }

dpsRTUv2p12507Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 59 is set"
	::= { dpsRTUv2 12507 }

dpsRTUv2p13507Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 59 is cleared"
	::= { dpsRTUv2 13507 }

dpsRTUv2p12508Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 60 is set"
	::= { dpsRTUv2 12508 }

dpsRTUv2p13508Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 60 is cleared"
	::= { dpsRTUv2 13508 }

dpsRTUv2p12509Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 61 is set"
	::= { dpsRTUv2 12509 }

dpsRTUv2p13509Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 61 is cleared"
	::= { dpsRTUv2 13509 }

dpsRTUv2p12510Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 62 is set"
	::= { dpsRTUv2 12510 }

dpsRTUv2p13510Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 62 is cleared"
	::= { dpsRTUv2 13510 }

dpsRTUv2p12511Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 63 is set"
	::= { dpsRTUv2 12511 }

dpsRTUv2p13511Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 63 is cleared"
	::= { dpsRTUv2 13511 }

dpsRTUv2p12512Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 64 is set"
	::= { dpsRTUv2 12512 }

dpsRTUv2p13512Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 2 display 8 point 64 is cleared"
	::= { dpsRTUv2 13512 }
dpsRTUv2p14001Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 1 is set"
	::= { dpsRTUv2 14001 }

dpsRTUv2p15001Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 1 is cleared"
	::= { dpsRTUv2 15001 }

dpsRTUv2p14002Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 2 is set"
	::= { dpsRTUv2 14002 }

dpsRTUv2p15002Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 2 is cleared"
	::= { dpsRTUv2 15002 }

dpsRTUv2p14003Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 3 is set"
	::= { dpsRTUv2 14003 }

dpsRTUv2p15003Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 3 is cleared"
	::= { dpsRTUv2 15003 }

dpsRTUv2p14004Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 4 is set"
	::= { dpsRTUv2 14004 }

dpsRTUv2p15004Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 4 is cleared"
	::= { dpsRTUv2 15004 }

dpsRTUv2p14005Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 5 is set"
	::= { dpsRTUv2 14005 }

dpsRTUv2p15005Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 5 is cleared"
	::= { dpsRTUv2 15005 }

dpsRTUv2p14006Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 6 is set"
	::= { dpsRTUv2 14006 }

dpsRTUv2p15006Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 6 is cleared"
	::= { dpsRTUv2 15006 }

dpsRTUv2p14007Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 7 is set"
	::= { dpsRTUv2 14007 }

dpsRTUv2p15007Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 7 is cleared"
	::= { dpsRTUv2 15007 }

dpsRTUv2p14008Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 8 is set"
	::= { dpsRTUv2 14008 }

dpsRTUv2p15008Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 8 is cleared"
	::= { dpsRTUv2 15008 }

dpsRTUv2p14009Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 9 is set"
	::= { dpsRTUv2 14009 }

dpsRTUv2p15009Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 9 is cleared"
	::= { dpsRTUv2 15009 }

dpsRTUv2p14010Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 10 is set"
	::= { dpsRTUv2 14010 }

dpsRTUv2p15010Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 10 is cleared"
	::= { dpsRTUv2 15010 }

dpsRTUv2p14011Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 11 is set"
	::= { dpsRTUv2 14011 }

dpsRTUv2p15011Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 11 is cleared"
	::= { dpsRTUv2 15011 }

dpsRTUv2p14012Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 12 is set"
	::= { dpsRTUv2 14012 }

dpsRTUv2p15012Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 12 is cleared"
	::= { dpsRTUv2 15012 }

dpsRTUv2p14013Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 13 is set"
	::= { dpsRTUv2 14013 }

dpsRTUv2p15013Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 13 is cleared"
	::= { dpsRTUv2 15013 }

dpsRTUv2p14014Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 14 is set"
	::= { dpsRTUv2 14014 }

dpsRTUv2p15014Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 14 is cleared"
	::= { dpsRTUv2 15014 }

dpsRTUv2p14015Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 15 is set"
	::= { dpsRTUv2 14015 }

dpsRTUv2p15015Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 15 is cleared"
	::= { dpsRTUv2 15015 }

dpsRTUv2p14016Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 16 is set"
	::= { dpsRTUv2 14016 }

dpsRTUv2p15016Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 16 is cleared"
	::= { dpsRTUv2 15016 }

dpsRTUv2p14017Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 17 is set"
	::= { dpsRTUv2 14017 }

dpsRTUv2p15017Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 17 is cleared"
	::= { dpsRTUv2 15017 }

dpsRTUv2p14018Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 18 is set"
	::= { dpsRTUv2 14018 }

dpsRTUv2p15018Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 18 is cleared"
	::= { dpsRTUv2 15018 }

dpsRTUv2p14019Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 19 is set"
	::= { dpsRTUv2 14019 }

dpsRTUv2p15019Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 19 is cleared"
	::= { dpsRTUv2 15019 }

dpsRTUv2p14020Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 20 is set"
	::= { dpsRTUv2 14020 }

dpsRTUv2p15020Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 20 is cleared"
	::= { dpsRTUv2 15020 }

dpsRTUv2p14021Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 21 is set"
	::= { dpsRTUv2 14021 }

dpsRTUv2p15021Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 21 is cleared"
	::= { dpsRTUv2 15021 }

dpsRTUv2p14022Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 22 is set"
	::= { dpsRTUv2 14022 }

dpsRTUv2p15022Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 22 is cleared"
	::= { dpsRTUv2 15022 }

dpsRTUv2p14023Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 23 is set"
	::= { dpsRTUv2 14023 }

dpsRTUv2p15023Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 23 is cleared"
	::= { dpsRTUv2 15023 }

dpsRTUv2p14024Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 24 is set"
	::= { dpsRTUv2 14024 }

dpsRTUv2p15024Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 24 is cleared"
	::= { dpsRTUv2 15024 }

dpsRTUv2p14025Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 25 is set"
	::= { dpsRTUv2 14025 }

dpsRTUv2p15025Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 25 is cleared"
	::= { dpsRTUv2 15025 }

dpsRTUv2p14026Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 26 is set"
	::= { dpsRTUv2 14026 }

dpsRTUv2p15026Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 26 is cleared"
	::= { dpsRTUv2 15026 }

dpsRTUv2p14027Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 27 is set"
	::= { dpsRTUv2 14027 }

dpsRTUv2p15027Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 27 is cleared"
	::= { dpsRTUv2 15027 }

dpsRTUv2p14028Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 28 is set"
	::= { dpsRTUv2 14028 }

dpsRTUv2p15028Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 28 is cleared"
	::= { dpsRTUv2 15028 }

dpsRTUv2p14029Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 29 is set"
	::= { dpsRTUv2 14029 }

dpsRTUv2p15029Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 29 is cleared"
	::= { dpsRTUv2 15029 }

dpsRTUv2p14030Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 30 is set"
	::= { dpsRTUv2 14030 }

dpsRTUv2p15030Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 30 is cleared"
	::= { dpsRTUv2 15030 }

dpsRTUv2p14031Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 31 is set"
	::= { dpsRTUv2 14031 }

dpsRTUv2p15031Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 31 is cleared"
	::= { dpsRTUv2 15031 }

dpsRTUv2p14032Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 32 is set"
	::= { dpsRTUv2 14032 }

dpsRTUv2p15032Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 32 is cleared"
	::= { dpsRTUv2 15032 }

dpsRTUv2p14033Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 33 is set"
	::= { dpsRTUv2 14033 }

dpsRTUv2p15033Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 33 is cleared"
	::= { dpsRTUv2 15033 }

dpsRTUv2p14034Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 34 is set"
	::= { dpsRTUv2 14034 }

dpsRTUv2p15034Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 34 is cleared"
	::= { dpsRTUv2 15034 }

dpsRTUv2p14035Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 35 is set"
	::= { dpsRTUv2 14035 }

dpsRTUv2p15035Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 35 is cleared"
	::= { dpsRTUv2 15035 }

dpsRTUv2p14036Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 36 is set"
	::= { dpsRTUv2 14036 }

dpsRTUv2p15036Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 36 is cleared"
	::= { dpsRTUv2 15036 }

dpsRTUv2p14037Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 37 is set"
	::= { dpsRTUv2 14037 }

dpsRTUv2p15037Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 37 is cleared"
	::= { dpsRTUv2 15037 }

dpsRTUv2p14038Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 38 is set"
	::= { dpsRTUv2 14038 }

dpsRTUv2p15038Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 38 is cleared"
	::= { dpsRTUv2 15038 }

dpsRTUv2p14039Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 39 is set"
	::= { dpsRTUv2 14039 }

dpsRTUv2p15039Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 39 is cleared"
	::= { dpsRTUv2 15039 }

dpsRTUv2p14040Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 40 is set"
	::= { dpsRTUv2 14040 }

dpsRTUv2p15040Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 40 is cleared"
	::= { dpsRTUv2 15040 }

dpsRTUv2p14041Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 41 is set"
	::= { dpsRTUv2 14041 }

dpsRTUv2p15041Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 41 is cleared"
	::= { dpsRTUv2 15041 }

dpsRTUv2p14042Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 42 is set"
	::= { dpsRTUv2 14042 }

dpsRTUv2p15042Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 42 is cleared"
	::= { dpsRTUv2 15042 }

dpsRTUv2p14043Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 43 is set"
	::= { dpsRTUv2 14043 }

dpsRTUv2p15043Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 43 is cleared"
	::= { dpsRTUv2 15043 }

dpsRTUv2p14044Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 44 is set"
	::= { dpsRTUv2 14044 }

dpsRTUv2p15044Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 44 is cleared"
	::= { dpsRTUv2 15044 }

dpsRTUv2p14045Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 45 is set"
	::= { dpsRTUv2 14045 }

dpsRTUv2p15045Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 45 is cleared"
	::= { dpsRTUv2 15045 }

dpsRTUv2p14046Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 46 is set"
	::= { dpsRTUv2 14046 }

dpsRTUv2p15046Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 46 is cleared"
	::= { dpsRTUv2 15046 }

dpsRTUv2p14047Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 47 is set"
	::= { dpsRTUv2 14047 }

dpsRTUv2p15047Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 47 is cleared"
	::= { dpsRTUv2 15047 }

dpsRTUv2p14048Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 48 is set"
	::= { dpsRTUv2 14048 }

dpsRTUv2p15048Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 48 is cleared"
	::= { dpsRTUv2 15048 }

dpsRTUv2p14049Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 49 is set"
	::= { dpsRTUv2 14049 }

dpsRTUv2p15049Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 49 is cleared"
	::= { dpsRTUv2 15049 }

dpsRTUv2p14050Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 50 is set"
	::= { dpsRTUv2 14050 }

dpsRTUv2p15050Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 50 is cleared"
	::= { dpsRTUv2 15050 }

dpsRTUv2p14051Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 51 is set"
	::= { dpsRTUv2 14051 }

dpsRTUv2p15051Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 51 is cleared"
	::= { dpsRTUv2 15051 }

dpsRTUv2p14052Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 52 is set"
	::= { dpsRTUv2 14052 }

dpsRTUv2p15052Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 52 is cleared"
	::= { dpsRTUv2 15052 }

dpsRTUv2p14053Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 53 is set"
	::= { dpsRTUv2 14053 }

dpsRTUv2p15053Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 53 is cleared"
	::= { dpsRTUv2 15053 }

dpsRTUv2p14054Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 54 is set"
	::= { dpsRTUv2 14054 }

dpsRTUv2p15054Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 54 is cleared"
	::= { dpsRTUv2 15054 }

dpsRTUv2p14055Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 55 is set"
	::= { dpsRTUv2 14055 }

dpsRTUv2p15055Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 55 is cleared"
	::= { dpsRTUv2 15055 }

dpsRTUv2p14056Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 56 is set"
	::= { dpsRTUv2 14056 }

dpsRTUv2p15056Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 56 is cleared"
	::= { dpsRTUv2 15056 }

dpsRTUv2p14057Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 57 is set"
	::= { dpsRTUv2 14057 }

dpsRTUv2p15057Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 57 is cleared"
	::= { dpsRTUv2 15057 }

dpsRTUv2p14058Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 58 is set"
	::= { dpsRTUv2 14058 }

dpsRTUv2p15058Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 58 is cleared"
	::= { dpsRTUv2 15058 }

dpsRTUv2p14059Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 59 is set"
	::= { dpsRTUv2 14059 }

dpsRTUv2p15059Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 59 is cleared"
	::= { dpsRTUv2 15059 }

dpsRTUv2p14060Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 60 is set"
	::= { dpsRTUv2 14060 }

dpsRTUv2p15060Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 60 is cleared"
	::= { dpsRTUv2 15060 }

dpsRTUv2p14061Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 61 is set"
	::= { dpsRTUv2 14061 }

dpsRTUv2p15061Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 61 is cleared"
	::= { dpsRTUv2 15061 }

dpsRTUv2p14062Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 62 is set"
	::= { dpsRTUv2 14062 }

dpsRTUv2p15062Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 62 is cleared"
	::= { dpsRTUv2 15062 }

dpsRTUv2p14063Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 63 is set"
	::= { dpsRTUv2 14063 }

dpsRTUv2p15063Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 63 is cleared"
	::= { dpsRTUv2 15063 }

dpsRTUv2p14064Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 64 is set"
	::= { dpsRTUv2 14064 }

dpsRTUv2p15064Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 1 point 64 is cleared"
	::= { dpsRTUv2 15064 }

dpsRTUv2p14065Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 1 is set"
	::= { dpsRTUv2 14065 }

dpsRTUv2p15065Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 1 is cleared"
	::= { dpsRTUv2 15065 }

dpsRTUv2p14066Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 2 is set"
	::= { dpsRTUv2 14066 }

dpsRTUv2p15066Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 2 is cleared"
	::= { dpsRTUv2 15066 }

dpsRTUv2p14067Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 3 is set"
	::= { dpsRTUv2 14067 }

dpsRTUv2p15067Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 3 is cleared"
	::= { dpsRTUv2 15067 }

dpsRTUv2p14068Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 4 is set"
	::= { dpsRTUv2 14068 }

dpsRTUv2p15068Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 4 is cleared"
	::= { dpsRTUv2 15068 }

dpsRTUv2p14069Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 5 is set"
	::= { dpsRTUv2 14069 }

dpsRTUv2p15069Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 5 is cleared"
	::= { dpsRTUv2 15069 }

dpsRTUv2p14070Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 6 is set"
	::= { dpsRTUv2 14070 }

dpsRTUv2p15070Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 6 is cleared"
	::= { dpsRTUv2 15070 }

dpsRTUv2p14071Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 7 is set"
	::= { dpsRTUv2 14071 }

dpsRTUv2p15071Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 7 is cleared"
	::= { dpsRTUv2 15071 }

dpsRTUv2p14072Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 8 is set"
	::= { dpsRTUv2 14072 }

dpsRTUv2p15072Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 8 is cleared"
	::= { dpsRTUv2 15072 }

dpsRTUv2p14073Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 9 is set"
	::= { dpsRTUv2 14073 }

dpsRTUv2p15073Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 9 is cleared"
	::= { dpsRTUv2 15073 }

dpsRTUv2p14074Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 10 is set"
	::= { dpsRTUv2 14074 }

dpsRTUv2p15074Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 10 is cleared"
	::= { dpsRTUv2 15074 }

dpsRTUv2p14075Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 11 is set"
	::= { dpsRTUv2 14075 }

dpsRTUv2p15075Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 11 is cleared"
	::= { dpsRTUv2 15075 }

dpsRTUv2p14076Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 12 is set"
	::= { dpsRTUv2 14076 }

dpsRTUv2p15076Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 12 is cleared"
	::= { dpsRTUv2 15076 }

dpsRTUv2p14077Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 13 is set"
	::= { dpsRTUv2 14077 }

dpsRTUv2p15077Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 13 is cleared"
	::= { dpsRTUv2 15077 }

dpsRTUv2p14078Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 14 is set"
	::= { dpsRTUv2 14078 }

dpsRTUv2p15078Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 14 is cleared"
	::= { dpsRTUv2 15078 }

dpsRTUv2p14079Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 15 is set"
	::= { dpsRTUv2 14079 }

dpsRTUv2p15079Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 15 is cleared"
	::= { dpsRTUv2 15079 }

dpsRTUv2p14080Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 16 is set"
	::= { dpsRTUv2 14080 }

dpsRTUv2p15080Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 16 is cleared"
	::= { dpsRTUv2 15080 }

dpsRTUv2p14081Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 17 is set"
	::= { dpsRTUv2 14081 }

dpsRTUv2p15081Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 17 is cleared"
	::= { dpsRTUv2 15081 }

dpsRTUv2p14082Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 18 is set"
	::= { dpsRTUv2 14082 }

dpsRTUv2p15082Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 18 is cleared"
	::= { dpsRTUv2 15082 }

dpsRTUv2p14083Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 19 is set"
	::= { dpsRTUv2 14083 }

dpsRTUv2p15083Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 19 is cleared"
	::= { dpsRTUv2 15083 }

dpsRTUv2p14084Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 20 is set"
	::= { dpsRTUv2 14084 }

dpsRTUv2p15084Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 20 is cleared"
	::= { dpsRTUv2 15084 }

dpsRTUv2p14085Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 21 is set"
	::= { dpsRTUv2 14085 }

dpsRTUv2p15085Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 21 is cleared"
	::= { dpsRTUv2 15085 }

dpsRTUv2p14086Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 22 is set"
	::= { dpsRTUv2 14086 }

dpsRTUv2p15086Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 22 is cleared"
	::= { dpsRTUv2 15086 }

dpsRTUv2p14087Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 23 is set"
	::= { dpsRTUv2 14087 }

dpsRTUv2p15087Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 23 is cleared"
	::= { dpsRTUv2 15087 }

dpsRTUv2p14088Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 24 is set"
	::= { dpsRTUv2 14088 }

dpsRTUv2p15088Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 24 is cleared"
	::= { dpsRTUv2 15088 }

dpsRTUv2p14089Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 25 is set"
	::= { dpsRTUv2 14089 }

dpsRTUv2p15089Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 25 is cleared"
	::= { dpsRTUv2 15089 }

dpsRTUv2p14090Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 26 is set"
	::= { dpsRTUv2 14090 }

dpsRTUv2p15090Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 26 is cleared"
	::= { dpsRTUv2 15090 }

dpsRTUv2p14091Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 27 is set"
	::= { dpsRTUv2 14091 }

dpsRTUv2p15091Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 27 is cleared"
	::= { dpsRTUv2 15091 }

dpsRTUv2p14092Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 28 is set"
	::= { dpsRTUv2 14092 }

dpsRTUv2p15092Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 28 is cleared"
	::= { dpsRTUv2 15092 }

dpsRTUv2p14093Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 29 is set"
	::= { dpsRTUv2 14093 }

dpsRTUv2p15093Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 29 is cleared"
	::= { dpsRTUv2 15093 }

dpsRTUv2p14094Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 30 is set"
	::= { dpsRTUv2 14094 }

dpsRTUv2p15094Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 30 is cleared"
	::= { dpsRTUv2 15094 }

dpsRTUv2p14095Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 31 is set"
	::= { dpsRTUv2 14095 }

dpsRTUv2p15095Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 31 is cleared"
	::= { dpsRTUv2 15095 }

dpsRTUv2p14096Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 32 is set"
	::= { dpsRTUv2 14096 }

dpsRTUv2p15096Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 32 is cleared"
	::= { dpsRTUv2 15096 }

dpsRTUv2p14097Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 33 is set"
	::= { dpsRTUv2 14097 }

dpsRTUv2p15097Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 33 is cleared"
	::= { dpsRTUv2 15097 }

dpsRTUv2p14098Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 34 is set"
	::= { dpsRTUv2 14098 }

dpsRTUv2p15098Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 34 is cleared"
	::= { dpsRTUv2 15098 }

dpsRTUv2p14099Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 35 is set"
	::= { dpsRTUv2 14099 }

dpsRTUv2p15099Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 35 is cleared"
	::= { dpsRTUv2 15099 }

dpsRTUv2p14100Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 36 is set"
	::= { dpsRTUv2 14100 }

dpsRTUv2p15100Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 36 is cleared"
	::= { dpsRTUv2 15100 }

dpsRTUv2p14101Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 37 is set"
	::= { dpsRTUv2 14101 }

dpsRTUv2p15101Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 37 is cleared"
	::= { dpsRTUv2 15101 }

dpsRTUv2p14102Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 38 is set"
	::= { dpsRTUv2 14102 }

dpsRTUv2p15102Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 38 is cleared"
	::= { dpsRTUv2 15102 }

dpsRTUv2p14103Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 39 is set"
	::= { dpsRTUv2 14103 }

dpsRTUv2p15103Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 39 is cleared"
	::= { dpsRTUv2 15103 }

dpsRTUv2p14104Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 40 is set"
	::= { dpsRTUv2 14104 }

dpsRTUv2p15104Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 40 is cleared"
	::= { dpsRTUv2 15104 }

dpsRTUv2p14105Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 41 is set"
	::= { dpsRTUv2 14105 }

dpsRTUv2p15105Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 41 is cleared"
	::= { dpsRTUv2 15105 }

dpsRTUv2p14106Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 42 is set"
	::= { dpsRTUv2 14106 }

dpsRTUv2p15106Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 42 is cleared"
	::= { dpsRTUv2 15106 }

dpsRTUv2p14107Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 43 is set"
	::= { dpsRTUv2 14107 }

dpsRTUv2p15107Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 43 is cleared"
	::= { dpsRTUv2 15107 }

dpsRTUv2p14108Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 44 is set"
	::= { dpsRTUv2 14108 }

dpsRTUv2p15108Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 44 is cleared"
	::= { dpsRTUv2 15108 }

dpsRTUv2p14109Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 45 is set"
	::= { dpsRTUv2 14109 }

dpsRTUv2p15109Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 45 is cleared"
	::= { dpsRTUv2 15109 }

dpsRTUv2p14110Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 46 is set"
	::= { dpsRTUv2 14110 }

dpsRTUv2p15110Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 46 is cleared"
	::= { dpsRTUv2 15110 }

dpsRTUv2p14111Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 47 is set"
	::= { dpsRTUv2 14111 }

dpsRTUv2p15111Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 47 is cleared"
	::= { dpsRTUv2 15111 }

dpsRTUv2p14112Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 48 is set"
	::= { dpsRTUv2 14112 }

dpsRTUv2p15112Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 48 is cleared"
	::= { dpsRTUv2 15112 }

dpsRTUv2p14113Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 49 is set"
	::= { dpsRTUv2 14113 }

dpsRTUv2p15113Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 49 is cleared"
	::= { dpsRTUv2 15113 }

dpsRTUv2p14114Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 50 is set"
	::= { dpsRTUv2 14114 }

dpsRTUv2p15114Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 50 is cleared"
	::= { dpsRTUv2 15114 }

dpsRTUv2p14115Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 51 is set"
	::= { dpsRTUv2 14115 }

dpsRTUv2p15115Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 51 is cleared"
	::= { dpsRTUv2 15115 }

dpsRTUv2p14116Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 52 is set"
	::= { dpsRTUv2 14116 }

dpsRTUv2p15116Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 52 is cleared"
	::= { dpsRTUv2 15116 }

dpsRTUv2p14117Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 53 is set"
	::= { dpsRTUv2 14117 }

dpsRTUv2p15117Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 53 is cleared"
	::= { dpsRTUv2 15117 }

dpsRTUv2p14118Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 54 is set"
	::= { dpsRTUv2 14118 }

dpsRTUv2p15118Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 54 is cleared"
	::= { dpsRTUv2 15118 }

dpsRTUv2p14119Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 55 is set"
	::= { dpsRTUv2 14119 }

dpsRTUv2p15119Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 55 is cleared"
	::= { dpsRTUv2 15119 }

dpsRTUv2p14120Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 56 is set"
	::= { dpsRTUv2 14120 }

dpsRTUv2p15120Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 56 is cleared"
	::= { dpsRTUv2 15120 }

dpsRTUv2p14121Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 57 is set"
	::= { dpsRTUv2 14121 }

dpsRTUv2p15121Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 57 is cleared"
	::= { dpsRTUv2 15121 }

dpsRTUv2p14122Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 58 is set"
	::= { dpsRTUv2 14122 }

dpsRTUv2p15122Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 58 is cleared"
	::= { dpsRTUv2 15122 }

dpsRTUv2p14123Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 59 is set"
	::= { dpsRTUv2 14123 }

dpsRTUv2p15123Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 59 is cleared"
	::= { dpsRTUv2 15123 }

dpsRTUv2p14124Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 60 is set"
	::= { dpsRTUv2 14124 }

dpsRTUv2p15124Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 60 is cleared"
	::= { dpsRTUv2 15124 }

dpsRTUv2p14125Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 61 is set"
	::= { dpsRTUv2 14125 }

dpsRTUv2p15125Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 61 is cleared"
	::= { dpsRTUv2 15125 }

dpsRTUv2p14126Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 62 is set"
	::= { dpsRTUv2 14126 }

dpsRTUv2p15126Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 62 is cleared"
	::= { dpsRTUv2 15126 }

dpsRTUv2p14127Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 63 is set"
	::= { dpsRTUv2 14127 }

dpsRTUv2p15127Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 63 is cleared"
	::= { dpsRTUv2 15127 }

dpsRTUv2p14128Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 64 is set"
	::= { dpsRTUv2 14128 }

dpsRTUv2p15128Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 2 point 64 is cleared"
	::= { dpsRTUv2 15128 }

dpsRTUv2p14129Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 1 is set"
	::= { dpsRTUv2 14129 }

dpsRTUv2p15129Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 1 is cleared"
	::= { dpsRTUv2 15129 }

dpsRTUv2p14130Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 2 is set"
	::= { dpsRTUv2 14130 }

dpsRTUv2p15130Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 2 is cleared"
	::= { dpsRTUv2 15130 }

dpsRTUv2p14131Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 3 is set"
	::= { dpsRTUv2 14131 }

dpsRTUv2p15131Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 3 is cleared"
	::= { dpsRTUv2 15131 }

dpsRTUv2p14132Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 4 is set"
	::= { dpsRTUv2 14132 }

dpsRTUv2p15132Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 4 is cleared"
	::= { dpsRTUv2 15132 }

dpsRTUv2p14133Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 5 is set"
	::= { dpsRTUv2 14133 }

dpsRTUv2p15133Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 5 is cleared"
	::= { dpsRTUv2 15133 }

dpsRTUv2p14134Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 6 is set"
	::= { dpsRTUv2 14134 }

dpsRTUv2p15134Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 6 is cleared"
	::= { dpsRTUv2 15134 }

dpsRTUv2p14135Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 7 is set"
	::= { dpsRTUv2 14135 }

dpsRTUv2p15135Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 7 is cleared"
	::= { dpsRTUv2 15135 }

dpsRTUv2p14136Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 8 is set"
	::= { dpsRTUv2 14136 }

dpsRTUv2p15136Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 8 is cleared"
	::= { dpsRTUv2 15136 }

dpsRTUv2p14137Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 9 is set"
	::= { dpsRTUv2 14137 }

dpsRTUv2p15137Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 9 is cleared"
	::= { dpsRTUv2 15137 }

dpsRTUv2p14138Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 10 is set"
	::= { dpsRTUv2 14138 }

dpsRTUv2p15138Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 10 is cleared"
	::= { dpsRTUv2 15138 }

dpsRTUv2p14139Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 11 is set"
	::= { dpsRTUv2 14139 }

dpsRTUv2p15139Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 11 is cleared"
	::= { dpsRTUv2 15139 }

dpsRTUv2p14140Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 12 is set"
	::= { dpsRTUv2 14140 }

dpsRTUv2p15140Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 12 is cleared"
	::= { dpsRTUv2 15140 }

dpsRTUv2p14141Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 13 is set"
	::= { dpsRTUv2 14141 }

dpsRTUv2p15141Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 13 is cleared"
	::= { dpsRTUv2 15141 }

dpsRTUv2p14142Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 14 is set"
	::= { dpsRTUv2 14142 }

dpsRTUv2p15142Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 14 is cleared"
	::= { dpsRTUv2 15142 }

dpsRTUv2p14143Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 15 is set"
	::= { dpsRTUv2 14143 }

dpsRTUv2p15143Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 15 is cleared"
	::= { dpsRTUv2 15143 }

dpsRTUv2p14144Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 16 is set"
	::= { dpsRTUv2 14144 }

dpsRTUv2p15144Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 16 is cleared"
	::= { dpsRTUv2 15144 }

dpsRTUv2p14145Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 17 is set"
	::= { dpsRTUv2 14145 }

dpsRTUv2p15145Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 17 is cleared"
	::= { dpsRTUv2 15145 }

dpsRTUv2p14146Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 18 is set"
	::= { dpsRTUv2 14146 }

dpsRTUv2p15146Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 18 is cleared"
	::= { dpsRTUv2 15146 }

dpsRTUv2p14147Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 19 is set"
	::= { dpsRTUv2 14147 }

dpsRTUv2p15147Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 19 is cleared"
	::= { dpsRTUv2 15147 }

dpsRTUv2p14148Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 20 is set"
	::= { dpsRTUv2 14148 }

dpsRTUv2p15148Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 20 is cleared"
	::= { dpsRTUv2 15148 }

dpsRTUv2p14149Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 21 is set"
	::= { dpsRTUv2 14149 }

dpsRTUv2p15149Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 21 is cleared"
	::= { dpsRTUv2 15149 }

dpsRTUv2p14150Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 22 is set"
	::= { dpsRTUv2 14150 }

dpsRTUv2p15150Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 22 is cleared"
	::= { dpsRTUv2 15150 }

dpsRTUv2p14151Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 23 is set"
	::= { dpsRTUv2 14151 }

dpsRTUv2p15151Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 23 is cleared"
	::= { dpsRTUv2 15151 }

dpsRTUv2p14152Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 24 is set"
	::= { dpsRTUv2 14152 }

dpsRTUv2p15152Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 24 is cleared"
	::= { dpsRTUv2 15152 }

dpsRTUv2p14153Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 25 is set"
	::= { dpsRTUv2 14153 }

dpsRTUv2p15153Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 25 is cleared"
	::= { dpsRTUv2 15153 }

dpsRTUv2p14154Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 26 is set"
	::= { dpsRTUv2 14154 }

dpsRTUv2p15154Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 26 is cleared"
	::= { dpsRTUv2 15154 }

dpsRTUv2p14155Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 27 is set"
	::= { dpsRTUv2 14155 }

dpsRTUv2p15155Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 27 is cleared"
	::= { dpsRTUv2 15155 }

dpsRTUv2p14156Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 28 is set"
	::= { dpsRTUv2 14156 }

dpsRTUv2p15156Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 28 is cleared"
	::= { dpsRTUv2 15156 }

dpsRTUv2p14157Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 29 is set"
	::= { dpsRTUv2 14157 }

dpsRTUv2p15157Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 29 is cleared"
	::= { dpsRTUv2 15157 }

dpsRTUv2p14158Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 30 is set"
	::= { dpsRTUv2 14158 }

dpsRTUv2p15158Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 30 is cleared"
	::= { dpsRTUv2 15158 }

dpsRTUv2p14159Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 31 is set"
	::= { dpsRTUv2 14159 }

dpsRTUv2p15159Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 31 is cleared"
	::= { dpsRTUv2 15159 }

dpsRTUv2p14160Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 32 is set"
	::= { dpsRTUv2 14160 }

dpsRTUv2p15160Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 32 is cleared"
	::= { dpsRTUv2 15160 }

dpsRTUv2p14161Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 33 is set"
	::= { dpsRTUv2 14161 }

dpsRTUv2p15161Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 33 is cleared"
	::= { dpsRTUv2 15161 }

dpsRTUv2p14162Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 34 is set"
	::= { dpsRTUv2 14162 }

dpsRTUv2p15162Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 34 is cleared"
	::= { dpsRTUv2 15162 }

dpsRTUv2p14163Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 35 is set"
	::= { dpsRTUv2 14163 }

dpsRTUv2p15163Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 35 is cleared"
	::= { dpsRTUv2 15163 }

dpsRTUv2p14164Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 36 is set"
	::= { dpsRTUv2 14164 }

dpsRTUv2p15164Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 36 is cleared"
	::= { dpsRTUv2 15164 }

dpsRTUv2p14165Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 37 is set"
	::= { dpsRTUv2 14165 }

dpsRTUv2p15165Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 37 is cleared"
	::= { dpsRTUv2 15165 }

dpsRTUv2p14166Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 38 is set"
	::= { dpsRTUv2 14166 }

dpsRTUv2p15166Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 38 is cleared"
	::= { dpsRTUv2 15166 }

dpsRTUv2p14167Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 39 is set"
	::= { dpsRTUv2 14167 }

dpsRTUv2p15167Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 39 is cleared"
	::= { dpsRTUv2 15167 }

dpsRTUv2p14168Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 40 is set"
	::= { dpsRTUv2 14168 }

dpsRTUv2p15168Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 40 is cleared"
	::= { dpsRTUv2 15168 }

dpsRTUv2p14169Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 41 is set"
	::= { dpsRTUv2 14169 }

dpsRTUv2p15169Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 41 is cleared"
	::= { dpsRTUv2 15169 }

dpsRTUv2p14170Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 42 is set"
	::= { dpsRTUv2 14170 }

dpsRTUv2p15170Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 42 is cleared"
	::= { dpsRTUv2 15170 }

dpsRTUv2p14171Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 43 is set"
	::= { dpsRTUv2 14171 }

dpsRTUv2p15171Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 43 is cleared"
	::= { dpsRTUv2 15171 }

dpsRTUv2p14172Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 44 is set"
	::= { dpsRTUv2 14172 }

dpsRTUv2p15172Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 44 is cleared"
	::= { dpsRTUv2 15172 }

dpsRTUv2p14173Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 45 is set"
	::= { dpsRTUv2 14173 }

dpsRTUv2p15173Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 45 is cleared"
	::= { dpsRTUv2 15173 }

dpsRTUv2p14174Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 46 is set"
	::= { dpsRTUv2 14174 }

dpsRTUv2p15174Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 46 is cleared"
	::= { dpsRTUv2 15174 }

dpsRTUv2p14175Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 47 is set"
	::= { dpsRTUv2 14175 }

dpsRTUv2p15175Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 47 is cleared"
	::= { dpsRTUv2 15175 }

dpsRTUv2p14176Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 48 is set"
	::= { dpsRTUv2 14176 }

dpsRTUv2p15176Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 48 is cleared"
	::= { dpsRTUv2 15176 }

dpsRTUv2p14177Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 49 is set"
	::= { dpsRTUv2 14177 }

dpsRTUv2p15177Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 49 is cleared"
	::= { dpsRTUv2 15177 }

dpsRTUv2p14178Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 50 is set"
	::= { dpsRTUv2 14178 }

dpsRTUv2p15178Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 50 is cleared"
	::= { dpsRTUv2 15178 }

dpsRTUv2p14179Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 51 is set"
	::= { dpsRTUv2 14179 }

dpsRTUv2p15179Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 51 is cleared"
	::= { dpsRTUv2 15179 }

dpsRTUv2p14180Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 52 is set"
	::= { dpsRTUv2 14180 }

dpsRTUv2p15180Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 52 is cleared"
	::= { dpsRTUv2 15180 }

dpsRTUv2p14181Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 53 is set"
	::= { dpsRTUv2 14181 }

dpsRTUv2p15181Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 53 is cleared"
	::= { dpsRTUv2 15181 }

dpsRTUv2p14182Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 54 is set"
	::= { dpsRTUv2 14182 }

dpsRTUv2p15182Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 54 is cleared"
	::= { dpsRTUv2 15182 }

dpsRTUv2p14183Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 55 is set"
	::= { dpsRTUv2 14183 }

dpsRTUv2p15183Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 55 is cleared"
	::= { dpsRTUv2 15183 }

dpsRTUv2p14184Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 56 is set"
	::= { dpsRTUv2 14184 }

dpsRTUv2p15184Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 56 is cleared"
	::= { dpsRTUv2 15184 }

dpsRTUv2p14185Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 57 is set"
	::= { dpsRTUv2 14185 }

dpsRTUv2p15185Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 57 is cleared"
	::= { dpsRTUv2 15185 }

dpsRTUv2p14186Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 58 is set"
	::= { dpsRTUv2 14186 }

dpsRTUv2p15186Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 58 is cleared"
	::= { dpsRTUv2 15186 }

dpsRTUv2p14187Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 59 is set"
	::= { dpsRTUv2 14187 }

dpsRTUv2p15187Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 59 is cleared"
	::= { dpsRTUv2 15187 }

dpsRTUv2p14188Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 60 is set"
	::= { dpsRTUv2 14188 }

dpsRTUv2p15188Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 60 is cleared"
	::= { dpsRTUv2 15188 }

dpsRTUv2p14189Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 61 is set"
	::= { dpsRTUv2 14189 }

dpsRTUv2p15189Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 61 is cleared"
	::= { dpsRTUv2 15189 }

dpsRTUv2p14190Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 62 is set"
	::= { dpsRTUv2 14190 }

dpsRTUv2p15190Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 62 is cleared"
	::= { dpsRTUv2 15190 }

dpsRTUv2p14191Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 63 is set"
	::= { dpsRTUv2 14191 }

dpsRTUv2p15191Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 63 is cleared"
	::= { dpsRTUv2 15191 }

dpsRTUv2p14192Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 64 is set"
	::= { dpsRTUv2 14192 }

dpsRTUv2p15192Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 3 point 64 is cleared"
	::= { dpsRTUv2 15192 }

dpsRTUv2p14193Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 1 is set"
	::= { dpsRTUv2 14193 }

dpsRTUv2p15193Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 1 is cleared"
	::= { dpsRTUv2 15193 }

dpsRTUv2p14194Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 2 is set"
	::= { dpsRTUv2 14194 }

dpsRTUv2p15194Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 2 is cleared"
	::= { dpsRTUv2 15194 }

dpsRTUv2p14195Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 3 is set"
	::= { dpsRTUv2 14195 }

dpsRTUv2p15195Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 3 is cleared"
	::= { dpsRTUv2 15195 }

dpsRTUv2p14196Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 4 is set"
	::= { dpsRTUv2 14196 }

dpsRTUv2p15196Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 4 is cleared"
	::= { dpsRTUv2 15196 }

dpsRTUv2p14197Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 5 is set"
	::= { dpsRTUv2 14197 }

dpsRTUv2p15197Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 5 is cleared"
	::= { dpsRTUv2 15197 }

dpsRTUv2p14198Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 6 is set"
	::= { dpsRTUv2 14198 }

dpsRTUv2p15198Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 6 is cleared"
	::= { dpsRTUv2 15198 }

dpsRTUv2p14199Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 7 is set"
	::= { dpsRTUv2 14199 }

dpsRTUv2p15199Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 7 is cleared"
	::= { dpsRTUv2 15199 }

dpsRTUv2p14200Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 8 is set"
	::= { dpsRTUv2 14200 }

dpsRTUv2p15200Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 8 is cleared"
	::= { dpsRTUv2 15200 }

dpsRTUv2p14201Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 9 is set"
	::= { dpsRTUv2 14201 }

dpsRTUv2p15201Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 9 is cleared"
	::= { dpsRTUv2 15201 }

dpsRTUv2p14202Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 10 is set"
	::= { dpsRTUv2 14202 }

dpsRTUv2p15202Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 10 is cleared"
	::= { dpsRTUv2 15202 }

dpsRTUv2p14203Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 11 is set"
	::= { dpsRTUv2 14203 }

dpsRTUv2p15203Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 11 is cleared"
	::= { dpsRTUv2 15203 }

dpsRTUv2p14204Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 12 is set"
	::= { dpsRTUv2 14204 }

dpsRTUv2p15204Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 12 is cleared"
	::= { dpsRTUv2 15204 }

dpsRTUv2p14205Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 13 is set"
	::= { dpsRTUv2 14205 }

dpsRTUv2p15205Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 13 is cleared"
	::= { dpsRTUv2 15205 }

dpsRTUv2p14206Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 14 is set"
	::= { dpsRTUv2 14206 }

dpsRTUv2p15206Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 14 is cleared"
	::= { dpsRTUv2 15206 }

dpsRTUv2p14207Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 15 is set"
	::= { dpsRTUv2 14207 }

dpsRTUv2p15207Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 15 is cleared"
	::= { dpsRTUv2 15207 }

dpsRTUv2p14208Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 16 is set"
	::= { dpsRTUv2 14208 }

dpsRTUv2p15208Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 16 is cleared"
	::= { dpsRTUv2 15208 }

dpsRTUv2p14209Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 17 is set"
	::= { dpsRTUv2 14209 }

dpsRTUv2p15209Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 17 is cleared"
	::= { dpsRTUv2 15209 }

dpsRTUv2p14210Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 18 is set"
	::= { dpsRTUv2 14210 }

dpsRTUv2p15210Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 18 is cleared"
	::= { dpsRTUv2 15210 }

dpsRTUv2p14211Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 19 is set"
	::= { dpsRTUv2 14211 }

dpsRTUv2p15211Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 19 is cleared"
	::= { dpsRTUv2 15211 }

dpsRTUv2p14212Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 20 is set"
	::= { dpsRTUv2 14212 }

dpsRTUv2p15212Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 20 is cleared"
	::= { dpsRTUv2 15212 }

dpsRTUv2p14213Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 21 is set"
	::= { dpsRTUv2 14213 }

dpsRTUv2p15213Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 21 is cleared"
	::= { dpsRTUv2 15213 }

dpsRTUv2p14214Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 22 is set"
	::= { dpsRTUv2 14214 }

dpsRTUv2p15214Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 22 is cleared"
	::= { dpsRTUv2 15214 }

dpsRTUv2p14215Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 23 is set"
	::= { dpsRTUv2 14215 }

dpsRTUv2p15215Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 23 is cleared"
	::= { dpsRTUv2 15215 }

dpsRTUv2p14216Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 24 is set"
	::= { dpsRTUv2 14216 }

dpsRTUv2p15216Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 24 is cleared"
	::= { dpsRTUv2 15216 }

dpsRTUv2p14217Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 25 is set"
	::= { dpsRTUv2 14217 }

dpsRTUv2p15217Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 25 is cleared"
	::= { dpsRTUv2 15217 }

dpsRTUv2p14218Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 26 is set"
	::= { dpsRTUv2 14218 }

dpsRTUv2p15218Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 26 is cleared"
	::= { dpsRTUv2 15218 }

dpsRTUv2p14219Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 27 is set"
	::= { dpsRTUv2 14219 }

dpsRTUv2p15219Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 27 is cleared"
	::= { dpsRTUv2 15219 }

dpsRTUv2p14220Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 28 is set"
	::= { dpsRTUv2 14220 }

dpsRTUv2p15220Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 28 is cleared"
	::= { dpsRTUv2 15220 }

dpsRTUv2p14221Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 29 is set"
	::= { dpsRTUv2 14221 }

dpsRTUv2p15221Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 29 is cleared"
	::= { dpsRTUv2 15221 }

dpsRTUv2p14222Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 30 is set"
	::= { dpsRTUv2 14222 }

dpsRTUv2p15222Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 30 is cleared"
	::= { dpsRTUv2 15222 }

dpsRTUv2p14223Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 31 is set"
	::= { dpsRTUv2 14223 }

dpsRTUv2p15223Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 31 is cleared"
	::= { dpsRTUv2 15223 }

dpsRTUv2p14224Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 32 is set"
	::= { dpsRTUv2 14224 }

dpsRTUv2p15224Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 32 is cleared"
	::= { dpsRTUv2 15224 }

dpsRTUv2p14225Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 33 is set"
	::= { dpsRTUv2 14225 }

dpsRTUv2p15225Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 33 is cleared"
	::= { dpsRTUv2 15225 }

dpsRTUv2p14226Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 34 is set"
	::= { dpsRTUv2 14226 }

dpsRTUv2p15226Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 34 is cleared"
	::= { dpsRTUv2 15226 }

dpsRTUv2p14227Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 35 is set"
	::= { dpsRTUv2 14227 }

dpsRTUv2p15227Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 35 is cleared"
	::= { dpsRTUv2 15227 }

dpsRTUv2p14228Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 36 is set"
	::= { dpsRTUv2 14228 }

dpsRTUv2p15228Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 36 is cleared"
	::= { dpsRTUv2 15228 }

dpsRTUv2p14229Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 37 is set"
	::= { dpsRTUv2 14229 }

dpsRTUv2p15229Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 37 is cleared"
	::= { dpsRTUv2 15229 }

dpsRTUv2p14230Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 38 is set"
	::= { dpsRTUv2 14230 }

dpsRTUv2p15230Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 38 is cleared"
	::= { dpsRTUv2 15230 }

dpsRTUv2p14231Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 39 is set"
	::= { dpsRTUv2 14231 }

dpsRTUv2p15231Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 39 is cleared"
	::= { dpsRTUv2 15231 }

dpsRTUv2p14232Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 40 is set"
	::= { dpsRTUv2 14232 }

dpsRTUv2p15232Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 40 is cleared"
	::= { dpsRTUv2 15232 }

dpsRTUv2p14233Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 41 is set"
	::= { dpsRTUv2 14233 }

dpsRTUv2p15233Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 41 is cleared"
	::= { dpsRTUv2 15233 }

dpsRTUv2p14234Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 42 is set"
	::= { dpsRTUv2 14234 }

dpsRTUv2p15234Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 42 is cleared"
	::= { dpsRTUv2 15234 }

dpsRTUv2p14235Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 43 is set"
	::= { dpsRTUv2 14235 }

dpsRTUv2p15235Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 43 is cleared"
	::= { dpsRTUv2 15235 }

dpsRTUv2p14236Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 44 is set"
	::= { dpsRTUv2 14236 }

dpsRTUv2p15236Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 44 is cleared"
	::= { dpsRTUv2 15236 }

dpsRTUv2p14237Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 45 is set"
	::= { dpsRTUv2 14237 }

dpsRTUv2p15237Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 45 is cleared"
	::= { dpsRTUv2 15237 }

dpsRTUv2p14238Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 46 is set"
	::= { dpsRTUv2 14238 }

dpsRTUv2p15238Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 46 is cleared"
	::= { dpsRTUv2 15238 }

dpsRTUv2p14239Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 47 is set"
	::= { dpsRTUv2 14239 }

dpsRTUv2p15239Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 47 is cleared"
	::= { dpsRTUv2 15239 }

dpsRTUv2p14240Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 48 is set"
	::= { dpsRTUv2 14240 }

dpsRTUv2p15240Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 48 is cleared"
	::= { dpsRTUv2 15240 }

dpsRTUv2p14241Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 49 is set"
	::= { dpsRTUv2 14241 }

dpsRTUv2p15241Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 49 is cleared"
	::= { dpsRTUv2 15241 }

dpsRTUv2p14242Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 50 is set"
	::= { dpsRTUv2 14242 }

dpsRTUv2p15242Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 50 is cleared"
	::= { dpsRTUv2 15242 }

dpsRTUv2p14243Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 51 is set"
	::= { dpsRTUv2 14243 }

dpsRTUv2p15243Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 51 is cleared"
	::= { dpsRTUv2 15243 }

dpsRTUv2p14244Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 52 is set"
	::= { dpsRTUv2 14244 }

dpsRTUv2p15244Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 52 is cleared"
	::= { dpsRTUv2 15244 }

dpsRTUv2p14245Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 53 is set"
	::= { dpsRTUv2 14245 }

dpsRTUv2p15245Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 53 is cleared"
	::= { dpsRTUv2 15245 }

dpsRTUv2p14246Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 54 is set"
	::= { dpsRTUv2 14246 }

dpsRTUv2p15246Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 54 is cleared"
	::= { dpsRTUv2 15246 }

dpsRTUv2p14247Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 55 is set"
	::= { dpsRTUv2 14247 }

dpsRTUv2p15247Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 55 is cleared"
	::= { dpsRTUv2 15247 }

dpsRTUv2p14248Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 56 is set"
	::= { dpsRTUv2 14248 }

dpsRTUv2p15248Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 56 is cleared"
	::= { dpsRTUv2 15248 }

dpsRTUv2p14249Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 57 is set"
	::= { dpsRTUv2 14249 }

dpsRTUv2p15249Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 57 is cleared"
	::= { dpsRTUv2 15249 }

dpsRTUv2p14250Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 58 is set"
	::= { dpsRTUv2 14250 }

dpsRTUv2p15250Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 58 is cleared"
	::= { dpsRTUv2 15250 }

dpsRTUv2p14251Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 59 is set"
	::= { dpsRTUv2 14251 }

dpsRTUv2p15251Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 59 is cleared"
	::= { dpsRTUv2 15251 }

dpsRTUv2p14252Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 60 is set"
	::= { dpsRTUv2 14252 }

dpsRTUv2p15252Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 60 is cleared"
	::= { dpsRTUv2 15252 }

dpsRTUv2p14253Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 61 is set"
	::= { dpsRTUv2 14253 }

dpsRTUv2p15253Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 61 is cleared"
	::= { dpsRTUv2 15253 }

dpsRTUv2p14254Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 62 is set"
	::= { dpsRTUv2 14254 }

dpsRTUv2p15254Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 62 is cleared"
	::= { dpsRTUv2 15254 }

dpsRTUv2p14255Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 63 is set"
	::= { dpsRTUv2 14255 }

dpsRTUv2p15255Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 63 is cleared"
	::= { dpsRTUv2 15255 }

dpsRTUv2p14256Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 64 is set"
	::= { dpsRTUv2 14256 }

dpsRTUv2p15256Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 4 point 64 is cleared"
	::= { dpsRTUv2 15256 }

dpsRTUv2p14257Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 1 is set"
	::= { dpsRTUv2 14257 }

dpsRTUv2p15257Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 1 is cleared"
	::= { dpsRTUv2 15257 }

dpsRTUv2p14258Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 2 is set"
	::= { dpsRTUv2 14258 }

dpsRTUv2p15258Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 2 is cleared"
	::= { dpsRTUv2 15258 }

dpsRTUv2p14259Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 3 is set"
	::= { dpsRTUv2 14259 }

dpsRTUv2p15259Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 3 is cleared"
	::= { dpsRTUv2 15259 }

dpsRTUv2p14260Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 4 is set"
	::= { dpsRTUv2 14260 }

dpsRTUv2p15260Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 4 is cleared"
	::= { dpsRTUv2 15260 }

dpsRTUv2p14261Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 5 is set"
	::= { dpsRTUv2 14261 }

dpsRTUv2p15261Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 5 is cleared"
	::= { dpsRTUv2 15261 }

dpsRTUv2p14262Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 6 is set"
	::= { dpsRTUv2 14262 }

dpsRTUv2p15262Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 6 is cleared"
	::= { dpsRTUv2 15262 }

dpsRTUv2p14263Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 7 is set"
	::= { dpsRTUv2 14263 }

dpsRTUv2p15263Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 7 is cleared"
	::= { dpsRTUv2 15263 }

dpsRTUv2p14264Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 8 is set"
	::= { dpsRTUv2 14264 }

dpsRTUv2p15264Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 8 is cleared"
	::= { dpsRTUv2 15264 }

dpsRTUv2p14265Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 9 is set"
	::= { dpsRTUv2 14265 }

dpsRTUv2p15265Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 9 is cleared"
	::= { dpsRTUv2 15265 }

dpsRTUv2p14266Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 10 is set"
	::= { dpsRTUv2 14266 }

dpsRTUv2p15266Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 10 is cleared"
	::= { dpsRTUv2 15266 }

dpsRTUv2p14267Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 11 is set"
	::= { dpsRTUv2 14267 }

dpsRTUv2p15267Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 11 is cleared"
	::= { dpsRTUv2 15267 }

dpsRTUv2p14268Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 12 is set"
	::= { dpsRTUv2 14268 }

dpsRTUv2p15268Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 12 is cleared"
	::= { dpsRTUv2 15268 }

dpsRTUv2p14269Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 13 is set"
	::= { dpsRTUv2 14269 }

dpsRTUv2p15269Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 13 is cleared"
	::= { dpsRTUv2 15269 }

dpsRTUv2p14270Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 14 is set"
	::= { dpsRTUv2 14270 }

dpsRTUv2p15270Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 14 is cleared"
	::= { dpsRTUv2 15270 }

dpsRTUv2p14271Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 15 is set"
	::= { dpsRTUv2 14271 }

dpsRTUv2p15271Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 15 is cleared"
	::= { dpsRTUv2 15271 }

dpsRTUv2p14272Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 16 is set"
	::= { dpsRTUv2 14272 }

dpsRTUv2p15272Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 16 is cleared"
	::= { dpsRTUv2 15272 }

dpsRTUv2p14273Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 17 is set"
	::= { dpsRTUv2 14273 }

dpsRTUv2p15273Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 17 is cleared"
	::= { dpsRTUv2 15273 }

dpsRTUv2p14274Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 18 is set"
	::= { dpsRTUv2 14274 }

dpsRTUv2p15274Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 18 is cleared"
	::= { dpsRTUv2 15274 }

dpsRTUv2p14275Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 19 is set"
	::= { dpsRTUv2 14275 }

dpsRTUv2p15275Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 19 is cleared"
	::= { dpsRTUv2 15275 }

dpsRTUv2p14276Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 20 is set"
	::= { dpsRTUv2 14276 }

dpsRTUv2p15276Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 20 is cleared"
	::= { dpsRTUv2 15276 }

dpsRTUv2p14277Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 21 is set"
	::= { dpsRTUv2 14277 }

dpsRTUv2p15277Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 21 is cleared"
	::= { dpsRTUv2 15277 }

dpsRTUv2p14278Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 22 is set"
	::= { dpsRTUv2 14278 }

dpsRTUv2p15278Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 22 is cleared"
	::= { dpsRTUv2 15278 }

dpsRTUv2p14279Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 23 is set"
	::= { dpsRTUv2 14279 }

dpsRTUv2p15279Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 23 is cleared"
	::= { dpsRTUv2 15279 }

dpsRTUv2p14280Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 24 is set"
	::= { dpsRTUv2 14280 }

dpsRTUv2p15280Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 24 is cleared"
	::= { dpsRTUv2 15280 }

dpsRTUv2p14281Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 25 is set"
	::= { dpsRTUv2 14281 }

dpsRTUv2p15281Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 25 is cleared"
	::= { dpsRTUv2 15281 }

dpsRTUv2p14282Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 26 is set"
	::= { dpsRTUv2 14282 }

dpsRTUv2p15282Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 26 is cleared"
	::= { dpsRTUv2 15282 }

dpsRTUv2p14283Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 27 is set"
	::= { dpsRTUv2 14283 }

dpsRTUv2p15283Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 27 is cleared"
	::= { dpsRTUv2 15283 }

dpsRTUv2p14284Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 28 is set"
	::= { dpsRTUv2 14284 }

dpsRTUv2p15284Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 28 is cleared"
	::= { dpsRTUv2 15284 }

dpsRTUv2p14285Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 29 is set"
	::= { dpsRTUv2 14285 }

dpsRTUv2p15285Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 29 is cleared"
	::= { dpsRTUv2 15285 }

dpsRTUv2p14286Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 30 is set"
	::= { dpsRTUv2 14286 }

dpsRTUv2p15286Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 30 is cleared"
	::= { dpsRTUv2 15286 }

dpsRTUv2p14287Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 31 is set"
	::= { dpsRTUv2 14287 }

dpsRTUv2p15287Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 31 is cleared"
	::= { dpsRTUv2 15287 }

dpsRTUv2p14288Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 32 is set"
	::= { dpsRTUv2 14288 }

dpsRTUv2p15288Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 32 is cleared"
	::= { dpsRTUv2 15288 }

dpsRTUv2p14289Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 33 is set"
	::= { dpsRTUv2 14289 }

dpsRTUv2p15289Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 33 is cleared"
	::= { dpsRTUv2 15289 }

dpsRTUv2p14290Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 34 is set"
	::= { dpsRTUv2 14290 }

dpsRTUv2p15290Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 34 is cleared"
	::= { dpsRTUv2 15290 }

dpsRTUv2p14291Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 35 is set"
	::= { dpsRTUv2 14291 }

dpsRTUv2p15291Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 35 is cleared"
	::= { dpsRTUv2 15291 }

dpsRTUv2p14292Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 36 is set"
	::= { dpsRTUv2 14292 }

dpsRTUv2p15292Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 36 is cleared"
	::= { dpsRTUv2 15292 }

dpsRTUv2p14293Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 37 is set"
	::= { dpsRTUv2 14293 }

dpsRTUv2p15293Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 37 is cleared"
	::= { dpsRTUv2 15293 }

dpsRTUv2p14294Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 38 is set"
	::= { dpsRTUv2 14294 }

dpsRTUv2p15294Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 38 is cleared"
	::= { dpsRTUv2 15294 }

dpsRTUv2p14295Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 39 is set"
	::= { dpsRTUv2 14295 }

dpsRTUv2p15295Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 39 is cleared"
	::= { dpsRTUv2 15295 }

dpsRTUv2p14296Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 40 is set"
	::= { dpsRTUv2 14296 }

dpsRTUv2p15296Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 40 is cleared"
	::= { dpsRTUv2 15296 }

dpsRTUv2p14297Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 41 is set"
	::= { dpsRTUv2 14297 }

dpsRTUv2p15297Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 41 is cleared"
	::= { dpsRTUv2 15297 }

dpsRTUv2p14298Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 42 is set"
	::= { dpsRTUv2 14298 }

dpsRTUv2p15298Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 42 is cleared"
	::= { dpsRTUv2 15298 }

dpsRTUv2p14299Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 43 is set"
	::= { dpsRTUv2 14299 }

dpsRTUv2p15299Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 43 is cleared"
	::= { dpsRTUv2 15299 }

dpsRTUv2p14300Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 44 is set"
	::= { dpsRTUv2 14300 }

dpsRTUv2p15300Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 44 is cleared"
	::= { dpsRTUv2 15300 }

dpsRTUv2p14301Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 45 is set"
	::= { dpsRTUv2 14301 }

dpsRTUv2p15301Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 45 is cleared"
	::= { dpsRTUv2 15301 }

dpsRTUv2p14302Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 46 is set"
	::= { dpsRTUv2 14302 }

dpsRTUv2p15302Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 46 is cleared"
	::= { dpsRTUv2 15302 }

dpsRTUv2p14303Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 47 is set"
	::= { dpsRTUv2 14303 }

dpsRTUv2p15303Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 47 is cleared"
	::= { dpsRTUv2 15303 }

dpsRTUv2p14304Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 48 is set"
	::= { dpsRTUv2 14304 }

dpsRTUv2p15304Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 48 is cleared"
	::= { dpsRTUv2 15304 }

dpsRTUv2p14305Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 49 is set"
	::= { dpsRTUv2 14305 }

dpsRTUv2p15305Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 49 is cleared"
	::= { dpsRTUv2 15305 }

dpsRTUv2p14306Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 50 is set"
	::= { dpsRTUv2 14306 }

dpsRTUv2p15306Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 50 is cleared"
	::= { dpsRTUv2 15306 }

dpsRTUv2p14307Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 51 is set"
	::= { dpsRTUv2 14307 }

dpsRTUv2p15307Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 51 is cleared"
	::= { dpsRTUv2 15307 }

dpsRTUv2p14308Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 52 is set"
	::= { dpsRTUv2 14308 }

dpsRTUv2p15308Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 52 is cleared"
	::= { dpsRTUv2 15308 }

dpsRTUv2p14309Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 53 is set"
	::= { dpsRTUv2 14309 }

dpsRTUv2p15309Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 53 is cleared"
	::= { dpsRTUv2 15309 }

dpsRTUv2p14310Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 54 is set"
	::= { dpsRTUv2 14310 }

dpsRTUv2p15310Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 54 is cleared"
	::= { dpsRTUv2 15310 }

dpsRTUv2p14311Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 55 is set"
	::= { dpsRTUv2 14311 }

dpsRTUv2p15311Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 55 is cleared"
	::= { dpsRTUv2 15311 }

dpsRTUv2p14312Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 56 is set"
	::= { dpsRTUv2 14312 }

dpsRTUv2p15312Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 56 is cleared"
	::= { dpsRTUv2 15312 }

dpsRTUv2p14313Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 57 is set"
	::= { dpsRTUv2 14313 }

dpsRTUv2p15313Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 57 is cleared"
	::= { dpsRTUv2 15313 }

dpsRTUv2p14314Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 58 is set"
	::= { dpsRTUv2 14314 }

dpsRTUv2p15314Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 58 is cleared"
	::= { dpsRTUv2 15314 }

dpsRTUv2p14315Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 59 is set"
	::= { dpsRTUv2 14315 }

dpsRTUv2p15315Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 59 is cleared"
	::= { dpsRTUv2 15315 }

dpsRTUv2p14316Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 60 is set"
	::= { dpsRTUv2 14316 }

dpsRTUv2p15316Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 60 is cleared"
	::= { dpsRTUv2 15316 }

dpsRTUv2p14317Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 61 is set"
	::= { dpsRTUv2 14317 }

dpsRTUv2p15317Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 61 is cleared"
	::= { dpsRTUv2 15317 }

dpsRTUv2p14318Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 62 is set"
	::= { dpsRTUv2 14318 }

dpsRTUv2p15318Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 62 is cleared"
	::= { dpsRTUv2 15318 }

dpsRTUv2p14319Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 63 is set"
	::= { dpsRTUv2 14319 }

dpsRTUv2p15319Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 63 is cleared"
	::= { dpsRTUv2 15319 }

dpsRTUv2p14320Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 64 is set"
	::= { dpsRTUv2 14320 }

dpsRTUv2p15320Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 5 point 64 is cleared"
	::= { dpsRTUv2 15320 }

dpsRTUv2p14321Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 1 is set"
	::= { dpsRTUv2 14321 }

dpsRTUv2p15321Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 1 is cleared"
	::= { dpsRTUv2 15321 }

dpsRTUv2p14322Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 2 is set"
	::= { dpsRTUv2 14322 }

dpsRTUv2p15322Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 2 is cleared"
	::= { dpsRTUv2 15322 }

dpsRTUv2p14323Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 3 is set"
	::= { dpsRTUv2 14323 }

dpsRTUv2p15323Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 3 is cleared"
	::= { dpsRTUv2 15323 }

dpsRTUv2p14324Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 4 is set"
	::= { dpsRTUv2 14324 }

dpsRTUv2p15324Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 4 is cleared"
	::= { dpsRTUv2 15324 }

dpsRTUv2p14325Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 5 is set"
	::= { dpsRTUv2 14325 }

dpsRTUv2p15325Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 5 is cleared"
	::= { dpsRTUv2 15325 }

dpsRTUv2p14326Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 6 is set"
	::= { dpsRTUv2 14326 }

dpsRTUv2p15326Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 6 is cleared"
	::= { dpsRTUv2 15326 }

dpsRTUv2p14327Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 7 is set"
	::= { dpsRTUv2 14327 }

dpsRTUv2p15327Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 7 is cleared"
	::= { dpsRTUv2 15327 }

dpsRTUv2p14328Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 8 is set"
	::= { dpsRTUv2 14328 }

dpsRTUv2p15328Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 8 is cleared"
	::= { dpsRTUv2 15328 }

dpsRTUv2p14329Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 9 is set"
	::= { dpsRTUv2 14329 }

dpsRTUv2p15329Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 9 is cleared"
	::= { dpsRTUv2 15329 }

dpsRTUv2p14330Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 10 is set"
	::= { dpsRTUv2 14330 }

dpsRTUv2p15330Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 10 is cleared"
	::= { dpsRTUv2 15330 }

dpsRTUv2p14331Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 11 is set"
	::= { dpsRTUv2 14331 }

dpsRTUv2p15331Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 11 is cleared"
	::= { dpsRTUv2 15331 }

dpsRTUv2p14332Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 12 is set"
	::= { dpsRTUv2 14332 }

dpsRTUv2p15332Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 12 is cleared"
	::= { dpsRTUv2 15332 }

dpsRTUv2p14333Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 13 is set"
	::= { dpsRTUv2 14333 }

dpsRTUv2p15333Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 13 is cleared"
	::= { dpsRTUv2 15333 }

dpsRTUv2p14334Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 14 is set"
	::= { dpsRTUv2 14334 }

dpsRTUv2p15334Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 14 is cleared"
	::= { dpsRTUv2 15334 }

dpsRTUv2p14335Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 15 is set"
	::= { dpsRTUv2 14335 }

dpsRTUv2p15335Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 15 is cleared"
	::= { dpsRTUv2 15335 }

dpsRTUv2p14336Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 16 is set"
	::= { dpsRTUv2 14336 }

dpsRTUv2p15336Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 16 is cleared"
	::= { dpsRTUv2 15336 }

dpsRTUv2p14337Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 17 is set"
	::= { dpsRTUv2 14337 }

dpsRTUv2p15337Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 17 is cleared"
	::= { dpsRTUv2 15337 }

dpsRTUv2p14338Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 18 is set"
	::= { dpsRTUv2 14338 }

dpsRTUv2p15338Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 18 is cleared"
	::= { dpsRTUv2 15338 }

dpsRTUv2p14339Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 19 is set"
	::= { dpsRTUv2 14339 }

dpsRTUv2p15339Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 19 is cleared"
	::= { dpsRTUv2 15339 }

dpsRTUv2p14340Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 20 is set"
	::= { dpsRTUv2 14340 }

dpsRTUv2p15340Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 20 is cleared"
	::= { dpsRTUv2 15340 }

dpsRTUv2p14341Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 21 is set"
	::= { dpsRTUv2 14341 }

dpsRTUv2p15341Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 21 is cleared"
	::= { dpsRTUv2 15341 }

dpsRTUv2p14342Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 22 is set"
	::= { dpsRTUv2 14342 }

dpsRTUv2p15342Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 22 is cleared"
	::= { dpsRTUv2 15342 }

dpsRTUv2p14343Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 23 is set"
	::= { dpsRTUv2 14343 }

dpsRTUv2p15343Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 23 is cleared"
	::= { dpsRTUv2 15343 }

dpsRTUv2p14344Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 24 is set"
	::= { dpsRTUv2 14344 }

dpsRTUv2p15344Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 24 is cleared"
	::= { dpsRTUv2 15344 }

dpsRTUv2p14345Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 25 is set"
	::= { dpsRTUv2 14345 }

dpsRTUv2p15345Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 25 is cleared"
	::= { dpsRTUv2 15345 }

dpsRTUv2p14346Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 26 is set"
	::= { dpsRTUv2 14346 }

dpsRTUv2p15346Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 26 is cleared"
	::= { dpsRTUv2 15346 }

dpsRTUv2p14347Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 27 is set"
	::= { dpsRTUv2 14347 }

dpsRTUv2p15347Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 27 is cleared"
	::= { dpsRTUv2 15347 }

dpsRTUv2p14348Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 28 is set"
	::= { dpsRTUv2 14348 }

dpsRTUv2p15348Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 28 is cleared"
	::= { dpsRTUv2 15348 }

dpsRTUv2p14349Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 29 is set"
	::= { dpsRTUv2 14349 }

dpsRTUv2p15349Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 29 is cleared"
	::= { dpsRTUv2 15349 }

dpsRTUv2p14350Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 30 is set"
	::= { dpsRTUv2 14350 }

dpsRTUv2p15350Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 30 is cleared"
	::= { dpsRTUv2 15350 }

dpsRTUv2p14351Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 31 is set"
	::= { dpsRTUv2 14351 }

dpsRTUv2p15351Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 31 is cleared"
	::= { dpsRTUv2 15351 }

dpsRTUv2p14352Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 32 is set"
	::= { dpsRTUv2 14352 }

dpsRTUv2p15352Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 32 is cleared"
	::= { dpsRTUv2 15352 }

dpsRTUv2p14353Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 33 is set"
	::= { dpsRTUv2 14353 }

dpsRTUv2p15353Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 33 is cleared"
	::= { dpsRTUv2 15353 }

dpsRTUv2p14354Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 34 is set"
	::= { dpsRTUv2 14354 }

dpsRTUv2p15354Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 34 is cleared"
	::= { dpsRTUv2 15354 }

dpsRTUv2p14355Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 35 is set"
	::= { dpsRTUv2 14355 }

dpsRTUv2p15355Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 35 is cleared"
	::= { dpsRTUv2 15355 }

dpsRTUv2p14356Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 36 is set"
	::= { dpsRTUv2 14356 }

dpsRTUv2p15356Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 36 is cleared"
	::= { dpsRTUv2 15356 }

dpsRTUv2p14357Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 37 is set"
	::= { dpsRTUv2 14357 }

dpsRTUv2p15357Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 37 is cleared"
	::= { dpsRTUv2 15357 }

dpsRTUv2p14358Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 38 is set"
	::= { dpsRTUv2 14358 }

dpsRTUv2p15358Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 38 is cleared"
	::= { dpsRTUv2 15358 }

dpsRTUv2p14359Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 39 is set"
	::= { dpsRTUv2 14359 }

dpsRTUv2p15359Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 39 is cleared"
	::= { dpsRTUv2 15359 }

dpsRTUv2p14360Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 40 is set"
	::= { dpsRTUv2 14360 }

dpsRTUv2p15360Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 40 is cleared"
	::= { dpsRTUv2 15360 }

dpsRTUv2p14361Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 41 is set"
	::= { dpsRTUv2 14361 }

dpsRTUv2p15361Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 41 is cleared"
	::= { dpsRTUv2 15361 }

dpsRTUv2p14362Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 42 is set"
	::= { dpsRTUv2 14362 }

dpsRTUv2p15362Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 42 is cleared"
	::= { dpsRTUv2 15362 }

dpsRTUv2p14363Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 43 is set"
	::= { dpsRTUv2 14363 }

dpsRTUv2p15363Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 43 is cleared"
	::= { dpsRTUv2 15363 }

dpsRTUv2p14364Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 44 is set"
	::= { dpsRTUv2 14364 }

dpsRTUv2p15364Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 44 is cleared"
	::= { dpsRTUv2 15364 }

dpsRTUv2p14365Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 45 is set"
	::= { dpsRTUv2 14365 }

dpsRTUv2p15365Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 45 is cleared"
	::= { dpsRTUv2 15365 }

dpsRTUv2p14366Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 46 is set"
	::= { dpsRTUv2 14366 }

dpsRTUv2p15366Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 46 is cleared"
	::= { dpsRTUv2 15366 }

dpsRTUv2p14367Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 47 is set"
	::= { dpsRTUv2 14367 }

dpsRTUv2p15367Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 47 is cleared"
	::= { dpsRTUv2 15367 }

dpsRTUv2p14368Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 48 is set"
	::= { dpsRTUv2 14368 }

dpsRTUv2p15368Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 48 is cleared"
	::= { dpsRTUv2 15368 }

dpsRTUv2p14369Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 49 is set"
	::= { dpsRTUv2 14369 }

dpsRTUv2p15369Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 49 is cleared"
	::= { dpsRTUv2 15369 }

dpsRTUv2p14370Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 50 is set"
	::= { dpsRTUv2 14370 }

dpsRTUv2p15370Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 50 is cleared"
	::= { dpsRTUv2 15370 }

dpsRTUv2p14371Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 51 is set"
	::= { dpsRTUv2 14371 }

dpsRTUv2p15371Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 51 is cleared"
	::= { dpsRTUv2 15371 }

dpsRTUv2p14372Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 52 is set"
	::= { dpsRTUv2 14372 }

dpsRTUv2p15372Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 52 is cleared"
	::= { dpsRTUv2 15372 }

dpsRTUv2p14373Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 53 is set"
	::= { dpsRTUv2 14373 }

dpsRTUv2p15373Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 53 is cleared"
	::= { dpsRTUv2 15373 }

dpsRTUv2p14374Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 54 is set"
	::= { dpsRTUv2 14374 }

dpsRTUv2p15374Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 54 is cleared"
	::= { dpsRTUv2 15374 }

dpsRTUv2p14375Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 55 is set"
	::= { dpsRTUv2 14375 }

dpsRTUv2p15375Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 55 is cleared"
	::= { dpsRTUv2 15375 }

dpsRTUv2p14376Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 56 is set"
	::= { dpsRTUv2 14376 }

dpsRTUv2p15376Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 56 is cleared"
	::= { dpsRTUv2 15376 }

dpsRTUv2p14377Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 57 is set"
	::= { dpsRTUv2 14377 }

dpsRTUv2p15377Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 57 is cleared"
	::= { dpsRTUv2 15377 }

dpsRTUv2p14378Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 58 is set"
	::= { dpsRTUv2 14378 }

dpsRTUv2p15378Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 58 is cleared"
	::= { dpsRTUv2 15378 }

dpsRTUv2p14379Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 59 is set"
	::= { dpsRTUv2 14379 }

dpsRTUv2p15379Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 59 is cleared"
	::= { dpsRTUv2 15379 }

dpsRTUv2p14380Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 60 is set"
	::= { dpsRTUv2 14380 }

dpsRTUv2p15380Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 60 is cleared"
	::= { dpsRTUv2 15380 }

dpsRTUv2p14381Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 61 is set"
	::= { dpsRTUv2 14381 }

dpsRTUv2p15381Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 61 is cleared"
	::= { dpsRTUv2 15381 }

dpsRTUv2p14382Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 62 is set"
	::= { dpsRTUv2 14382 }

dpsRTUv2p15382Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 62 is cleared"
	::= { dpsRTUv2 15382 }

dpsRTUv2p14383Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 63 is set"
	::= { dpsRTUv2 14383 }

dpsRTUv2p15383Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 63 is cleared"
	::= { dpsRTUv2 15383 }

dpsRTUv2p14384Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 64 is set"
	::= { dpsRTUv2 14384 }

dpsRTUv2p15384Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 6 point 64 is cleared"
	::= { dpsRTUv2 15384 }

dpsRTUv2p14385Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 1 is set"
	::= { dpsRTUv2 14385 }

dpsRTUv2p15385Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 1 is cleared"
	::= { dpsRTUv2 15385 }

dpsRTUv2p14386Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 2 is set"
	::= { dpsRTUv2 14386 }

dpsRTUv2p15386Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 2 is cleared"
	::= { dpsRTUv2 15386 }

dpsRTUv2p14387Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 3 is set"
	::= { dpsRTUv2 14387 }

dpsRTUv2p15387Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 3 is cleared"
	::= { dpsRTUv2 15387 }

dpsRTUv2p14388Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 4 is set"
	::= { dpsRTUv2 14388 }

dpsRTUv2p15388Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 4 is cleared"
	::= { dpsRTUv2 15388 }

dpsRTUv2p14389Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 5 is set"
	::= { dpsRTUv2 14389 }

dpsRTUv2p15389Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 5 is cleared"
	::= { dpsRTUv2 15389 }

dpsRTUv2p14390Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 6 is set"
	::= { dpsRTUv2 14390 }

dpsRTUv2p15390Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 6 is cleared"
	::= { dpsRTUv2 15390 }

dpsRTUv2p14391Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 7 is set"
	::= { dpsRTUv2 14391 }

dpsRTUv2p15391Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 7 is cleared"
	::= { dpsRTUv2 15391 }

dpsRTUv2p14392Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 8 is set"
	::= { dpsRTUv2 14392 }

dpsRTUv2p15392Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 8 is cleared"
	::= { dpsRTUv2 15392 }

dpsRTUv2p14393Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 9 is set"
	::= { dpsRTUv2 14393 }

dpsRTUv2p15393Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 9 is cleared"
	::= { dpsRTUv2 15393 }

dpsRTUv2p14394Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 10 is set"
	::= { dpsRTUv2 14394 }

dpsRTUv2p15394Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 10 is cleared"
	::= { dpsRTUv2 15394 }

dpsRTUv2p14395Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 11 is set"
	::= { dpsRTUv2 14395 }

dpsRTUv2p15395Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 11 is cleared"
	::= { dpsRTUv2 15395 }

dpsRTUv2p14396Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 12 is set"
	::= { dpsRTUv2 14396 }

dpsRTUv2p15396Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 12 is cleared"
	::= { dpsRTUv2 15396 }

dpsRTUv2p14397Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 13 is set"
	::= { dpsRTUv2 14397 }

dpsRTUv2p15397Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 13 is cleared"
	::= { dpsRTUv2 15397 }

dpsRTUv2p14398Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 14 is set"
	::= { dpsRTUv2 14398 }

dpsRTUv2p15398Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 14 is cleared"
	::= { dpsRTUv2 15398 }

dpsRTUv2p14399Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 15 is set"
	::= { dpsRTUv2 14399 }

dpsRTUv2p15399Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 15 is cleared"
	::= { dpsRTUv2 15399 }

dpsRTUv2p14400Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 16 is set"
	::= { dpsRTUv2 14400 }

dpsRTUv2p15400Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 16 is cleared"
	::= { dpsRTUv2 15400 }

dpsRTUv2p14401Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 17 is set"
	::= { dpsRTUv2 14401 }

dpsRTUv2p15401Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 17 is cleared"
	::= { dpsRTUv2 15401 }

dpsRTUv2p14402Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 18 is set"
	::= { dpsRTUv2 14402 }

dpsRTUv2p15402Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 18 is cleared"
	::= { dpsRTUv2 15402 }

dpsRTUv2p14403Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 19 is set"
	::= { dpsRTUv2 14403 }

dpsRTUv2p15403Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 19 is cleared"
	::= { dpsRTUv2 15403 }

dpsRTUv2p14404Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 20 is set"
	::= { dpsRTUv2 14404 }

dpsRTUv2p15404Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 20 is cleared"
	::= { dpsRTUv2 15404 }

dpsRTUv2p14405Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 21 is set"
	::= { dpsRTUv2 14405 }

dpsRTUv2p15405Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 21 is cleared"
	::= { dpsRTUv2 15405 }

dpsRTUv2p14406Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 22 is set"
	::= { dpsRTUv2 14406 }

dpsRTUv2p15406Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 22 is cleared"
	::= { dpsRTUv2 15406 }

dpsRTUv2p14407Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 23 is set"
	::= { dpsRTUv2 14407 }

dpsRTUv2p15407Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 23 is cleared"
	::= { dpsRTUv2 15407 }

dpsRTUv2p14408Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 24 is set"
	::= { dpsRTUv2 14408 }

dpsRTUv2p15408Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 24 is cleared"
	::= { dpsRTUv2 15408 }

dpsRTUv2p14409Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 25 is set"
	::= { dpsRTUv2 14409 }

dpsRTUv2p15409Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 25 is cleared"
	::= { dpsRTUv2 15409 }

dpsRTUv2p14410Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 26 is set"
	::= { dpsRTUv2 14410 }

dpsRTUv2p15410Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 26 is cleared"
	::= { dpsRTUv2 15410 }

dpsRTUv2p14411Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 27 is set"
	::= { dpsRTUv2 14411 }

dpsRTUv2p15411Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 27 is cleared"
	::= { dpsRTUv2 15411 }

dpsRTUv2p14412Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 28 is set"
	::= { dpsRTUv2 14412 }

dpsRTUv2p15412Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 28 is cleared"
	::= { dpsRTUv2 15412 }

dpsRTUv2p14413Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 29 is set"
	::= { dpsRTUv2 14413 }

dpsRTUv2p15413Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 29 is cleared"
	::= { dpsRTUv2 15413 }

dpsRTUv2p14414Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 30 is set"
	::= { dpsRTUv2 14414 }

dpsRTUv2p15414Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 30 is cleared"
	::= { dpsRTUv2 15414 }

dpsRTUv2p14415Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 31 is set"
	::= { dpsRTUv2 14415 }

dpsRTUv2p15415Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 31 is cleared"
	::= { dpsRTUv2 15415 }

dpsRTUv2p14416Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 32 is set"
	::= { dpsRTUv2 14416 }

dpsRTUv2p15416Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 32 is cleared"
	::= { dpsRTUv2 15416 }

dpsRTUv2p14417Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 33 is set"
	::= { dpsRTUv2 14417 }

dpsRTUv2p15417Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 33 is cleared"
	::= { dpsRTUv2 15417 }

dpsRTUv2p14418Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 34 is set"
	::= { dpsRTUv2 14418 }

dpsRTUv2p15418Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 34 is cleared"
	::= { dpsRTUv2 15418 }

dpsRTUv2p14419Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 35 is set"
	::= { dpsRTUv2 14419 }

dpsRTUv2p15419Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 35 is cleared"
	::= { dpsRTUv2 15419 }

dpsRTUv2p14420Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 36 is set"
	::= { dpsRTUv2 14420 }

dpsRTUv2p15420Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 36 is cleared"
	::= { dpsRTUv2 15420 }

dpsRTUv2p14421Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 37 is set"
	::= { dpsRTUv2 14421 }

dpsRTUv2p15421Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 37 is cleared"
	::= { dpsRTUv2 15421 }

dpsRTUv2p14422Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 38 is set"
	::= { dpsRTUv2 14422 }

dpsRTUv2p15422Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 38 is cleared"
	::= { dpsRTUv2 15422 }

dpsRTUv2p14423Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 39 is set"
	::= { dpsRTUv2 14423 }

dpsRTUv2p15423Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 39 is cleared"
	::= { dpsRTUv2 15423 }

dpsRTUv2p14424Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 40 is set"
	::= { dpsRTUv2 14424 }

dpsRTUv2p15424Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 40 is cleared"
	::= { dpsRTUv2 15424 }

dpsRTUv2p14425Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 41 is set"
	::= { dpsRTUv2 14425 }

dpsRTUv2p15425Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 41 is cleared"
	::= { dpsRTUv2 15425 }

dpsRTUv2p14426Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 42 is set"
	::= { dpsRTUv2 14426 }

dpsRTUv2p15426Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 42 is cleared"
	::= { dpsRTUv2 15426 }

dpsRTUv2p14427Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 43 is set"
	::= { dpsRTUv2 14427 }

dpsRTUv2p15427Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 43 is cleared"
	::= { dpsRTUv2 15427 }

dpsRTUv2p14428Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 44 is set"
	::= { dpsRTUv2 14428 }

dpsRTUv2p15428Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 44 is cleared"
	::= { dpsRTUv2 15428 }

dpsRTUv2p14429Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 45 is set"
	::= { dpsRTUv2 14429 }

dpsRTUv2p15429Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 45 is cleared"
	::= { dpsRTUv2 15429 }

dpsRTUv2p14430Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 46 is set"
	::= { dpsRTUv2 14430 }

dpsRTUv2p15430Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 46 is cleared"
	::= { dpsRTUv2 15430 }

dpsRTUv2p14431Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 47 is set"
	::= { dpsRTUv2 14431 }

dpsRTUv2p15431Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 47 is cleared"
	::= { dpsRTUv2 15431 }

dpsRTUv2p14432Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 48 is set"
	::= { dpsRTUv2 14432 }

dpsRTUv2p15432Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 48 is cleared"
	::= { dpsRTUv2 15432 }

dpsRTUv2p14433Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 49 is set"
	::= { dpsRTUv2 14433 }

dpsRTUv2p15433Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 49 is cleared"
	::= { dpsRTUv2 15433 }

dpsRTUv2p14434Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 50 is set"
	::= { dpsRTUv2 14434 }

dpsRTUv2p15434Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 50 is cleared"
	::= { dpsRTUv2 15434 }

dpsRTUv2p14435Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 51 is set"
	::= { dpsRTUv2 14435 }

dpsRTUv2p15435Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 51 is cleared"
	::= { dpsRTUv2 15435 }

dpsRTUv2p14436Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 52 is set"
	::= { dpsRTUv2 14436 }

dpsRTUv2p15436Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 52 is cleared"
	::= { dpsRTUv2 15436 }

dpsRTUv2p14437Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 53 is set"
	::= { dpsRTUv2 14437 }

dpsRTUv2p15437Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 53 is cleared"
	::= { dpsRTUv2 15437 }

dpsRTUv2p14438Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 54 is set"
	::= { dpsRTUv2 14438 }

dpsRTUv2p15438Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 54 is cleared"
	::= { dpsRTUv2 15438 }

dpsRTUv2p14439Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 55 is set"
	::= { dpsRTUv2 14439 }

dpsRTUv2p15439Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 55 is cleared"
	::= { dpsRTUv2 15439 }

dpsRTUv2p14440Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 56 is set"
	::= { dpsRTUv2 14440 }

dpsRTUv2p15440Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 56 is cleared"
	::= { dpsRTUv2 15440 }

dpsRTUv2p14441Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 57 is set"
	::= { dpsRTUv2 14441 }

dpsRTUv2p15441Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 57 is cleared"
	::= { dpsRTUv2 15441 }

dpsRTUv2p14442Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 58 is set"
	::= { dpsRTUv2 14442 }

dpsRTUv2p15442Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 58 is cleared"
	::= { dpsRTUv2 15442 }

dpsRTUv2p14443Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 59 is set"
	::= { dpsRTUv2 14443 }

dpsRTUv2p15443Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 59 is cleared"
	::= { dpsRTUv2 15443 }

dpsRTUv2p14444Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 60 is set"
	::= { dpsRTUv2 14444 }

dpsRTUv2p15444Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 60 is cleared"
	::= { dpsRTUv2 15444 }

dpsRTUv2p14445Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 61 is set"
	::= { dpsRTUv2 14445 }

dpsRTUv2p15445Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 61 is cleared"
	::= { dpsRTUv2 15445 }

dpsRTUv2p14446Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 62 is set"
	::= { dpsRTUv2 14446 }

dpsRTUv2p15446Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 62 is cleared"
	::= { dpsRTUv2 15446 }

dpsRTUv2p14447Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 63 is set"
	::= { dpsRTUv2 14447 }

dpsRTUv2p15447Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 63 is cleared"
	::= { dpsRTUv2 15447 }

dpsRTUv2p14448Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 64 is set"
	::= { dpsRTUv2 14448 }

dpsRTUv2p15448Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 7 point 64 is cleared"
	::= { dpsRTUv2 15448 }

dpsRTUv2p14449Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 1 is set"
	::= { dpsRTUv2 14449 }

dpsRTUv2p15449Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 1 is cleared"
	::= { dpsRTUv2 15449 }

dpsRTUv2p14450Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 2 is set"
	::= { dpsRTUv2 14450 }

dpsRTUv2p15450Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 2 is cleared"
	::= { dpsRTUv2 15450 }

dpsRTUv2p14451Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 3 is set"
	::= { dpsRTUv2 14451 }

dpsRTUv2p15451Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 3 is cleared"
	::= { dpsRTUv2 15451 }

dpsRTUv2p14452Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 4 is set"
	::= { dpsRTUv2 14452 }

dpsRTUv2p15452Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 4 is cleared"
	::= { dpsRTUv2 15452 }

dpsRTUv2p14453Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 5 is set"
	::= { dpsRTUv2 14453 }

dpsRTUv2p15453Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 5 is cleared"
	::= { dpsRTUv2 15453 }

dpsRTUv2p14454Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 6 is set"
	::= { dpsRTUv2 14454 }

dpsRTUv2p15454Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 6 is cleared"
	::= { dpsRTUv2 15454 }

dpsRTUv2p14455Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 7 is set"
	::= { dpsRTUv2 14455 }

dpsRTUv2p15455Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 7 is cleared"
	::= { dpsRTUv2 15455 }

dpsRTUv2p14456Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 8 is set"
	::= { dpsRTUv2 14456 }

dpsRTUv2p15456Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 8 is cleared"
	::= { dpsRTUv2 15456 }

dpsRTUv2p14457Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 9 is set"
	::= { dpsRTUv2 14457 }

dpsRTUv2p15457Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 9 is cleared"
	::= { dpsRTUv2 15457 }

dpsRTUv2p14458Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 10 is set"
	::= { dpsRTUv2 14458 }

dpsRTUv2p15458Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 10 is cleared"
	::= { dpsRTUv2 15458 }

dpsRTUv2p14459Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 11 is set"
	::= { dpsRTUv2 14459 }

dpsRTUv2p15459Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 11 is cleared"
	::= { dpsRTUv2 15459 }

dpsRTUv2p14460Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 12 is set"
	::= { dpsRTUv2 14460 }

dpsRTUv2p15460Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 12 is cleared"
	::= { dpsRTUv2 15460 }

dpsRTUv2p14461Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 13 is set"
	::= { dpsRTUv2 14461 }

dpsRTUv2p15461Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 13 is cleared"
	::= { dpsRTUv2 15461 }

dpsRTUv2p14462Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 14 is set"
	::= { dpsRTUv2 14462 }

dpsRTUv2p15462Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 14 is cleared"
	::= { dpsRTUv2 15462 }

dpsRTUv2p14463Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 15 is set"
	::= { dpsRTUv2 14463 }

dpsRTUv2p15463Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 15 is cleared"
	::= { dpsRTUv2 15463 }

dpsRTUv2p14464Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 16 is set"
	::= { dpsRTUv2 14464 }

dpsRTUv2p15464Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 16 is cleared"
	::= { dpsRTUv2 15464 }

dpsRTUv2p14465Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 17 is set"
	::= { dpsRTUv2 14465 }

dpsRTUv2p15465Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 17 is cleared"
	::= { dpsRTUv2 15465 }

dpsRTUv2p14466Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 18 is set"
	::= { dpsRTUv2 14466 }

dpsRTUv2p15466Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 18 is cleared"
	::= { dpsRTUv2 15466 }

dpsRTUv2p14467Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 19 is set"
	::= { dpsRTUv2 14467 }

dpsRTUv2p15467Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 19 is cleared"
	::= { dpsRTUv2 15467 }

dpsRTUv2p14468Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 20 is set"
	::= { dpsRTUv2 14468 }

dpsRTUv2p15468Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 20 is cleared"
	::= { dpsRTUv2 15468 }

dpsRTUv2p14469Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 21 is set"
	::= { dpsRTUv2 14469 }

dpsRTUv2p15469Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 21 is cleared"
	::= { dpsRTUv2 15469 }

dpsRTUv2p14470Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 22 is set"
	::= { dpsRTUv2 14470 }

dpsRTUv2p15470Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 22 is cleared"
	::= { dpsRTUv2 15470 }

dpsRTUv2p14471Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 23 is set"
	::= { dpsRTUv2 14471 }

dpsRTUv2p15471Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 23 is cleared"
	::= { dpsRTUv2 15471 }

dpsRTUv2p14472Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 24 is set"
	::= { dpsRTUv2 14472 }

dpsRTUv2p15472Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 24 is cleared"
	::= { dpsRTUv2 15472 }

dpsRTUv2p14473Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 25 is set"
	::= { dpsRTUv2 14473 }

dpsRTUv2p15473Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 25 is cleared"
	::= { dpsRTUv2 15473 }

dpsRTUv2p14474Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 26 is set"
	::= { dpsRTUv2 14474 }

dpsRTUv2p15474Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 26 is cleared"
	::= { dpsRTUv2 15474 }

dpsRTUv2p14475Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 27 is set"
	::= { dpsRTUv2 14475 }

dpsRTUv2p15475Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 27 is cleared"
	::= { dpsRTUv2 15475 }

dpsRTUv2p14476Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 28 is set"
	::= { dpsRTUv2 14476 }

dpsRTUv2p15476Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 28 is cleared"
	::= { dpsRTUv2 15476 }

dpsRTUv2p14477Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 29 is set"
	::= { dpsRTUv2 14477 }

dpsRTUv2p15477Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 29 is cleared"
	::= { dpsRTUv2 15477 }

dpsRTUv2p14478Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 30 is set"
	::= { dpsRTUv2 14478 }

dpsRTUv2p15478Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 30 is cleared"
	::= { dpsRTUv2 15478 }

dpsRTUv2p14479Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 31 is set"
	::= { dpsRTUv2 14479 }

dpsRTUv2p15479Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 31 is cleared"
	::= { dpsRTUv2 15479 }

dpsRTUv2p14480Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 32 is set"
	::= { dpsRTUv2 14480 }

dpsRTUv2p15480Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 32 is cleared"
	::= { dpsRTUv2 15480 }

dpsRTUv2p14481Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 33 is set"
	::= { dpsRTUv2 14481 }

dpsRTUv2p15481Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 33 is cleared"
	::= { dpsRTUv2 15481 }

dpsRTUv2p14482Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 34 is set"
	::= { dpsRTUv2 14482 }

dpsRTUv2p15482Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 34 is cleared"
	::= { dpsRTUv2 15482 }

dpsRTUv2p14483Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 35 is set"
	::= { dpsRTUv2 14483 }

dpsRTUv2p15483Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 35 is cleared"
	::= { dpsRTUv2 15483 }

dpsRTUv2p14484Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 36 is set"
	::= { dpsRTUv2 14484 }

dpsRTUv2p15484Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 36 is cleared"
	::= { dpsRTUv2 15484 }

dpsRTUv2p14485Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 37 is set"
	::= { dpsRTUv2 14485 }

dpsRTUv2p15485Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 37 is cleared"
	::= { dpsRTUv2 15485 }

dpsRTUv2p14486Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 38 is set"
	::= { dpsRTUv2 14486 }

dpsRTUv2p15486Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 38 is cleared"
	::= { dpsRTUv2 15486 }

dpsRTUv2p14487Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 39 is set"
	::= { dpsRTUv2 14487 }

dpsRTUv2p15487Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 39 is cleared"
	::= { dpsRTUv2 15487 }

dpsRTUv2p14488Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 40 is set"
	::= { dpsRTUv2 14488 }

dpsRTUv2p15488Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 40 is cleared"
	::= { dpsRTUv2 15488 }

dpsRTUv2p14489Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 41 is set"
	::= { dpsRTUv2 14489 }

dpsRTUv2p15489Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 41 is cleared"
	::= { dpsRTUv2 15489 }

dpsRTUv2p14490Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 42 is set"
	::= { dpsRTUv2 14490 }

dpsRTUv2p15490Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 42 is cleared"
	::= { dpsRTUv2 15490 }

dpsRTUv2p14491Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 43 is set"
	::= { dpsRTUv2 14491 }

dpsRTUv2p15491Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 43 is cleared"
	::= { dpsRTUv2 15491 }

dpsRTUv2p14492Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 44 is set"
	::= { dpsRTUv2 14492 }

dpsRTUv2p15492Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 44 is cleared"
	::= { dpsRTUv2 15492 }

dpsRTUv2p14493Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 45 is set"
	::= { dpsRTUv2 14493 }

dpsRTUv2p15493Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 45 is cleared"
	::= { dpsRTUv2 15493 }

dpsRTUv2p14494Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 46 is set"
	::= { dpsRTUv2 14494 }

dpsRTUv2p15494Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 46 is cleared"
	::= { dpsRTUv2 15494 }

dpsRTUv2p14495Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 47 is set"
	::= { dpsRTUv2 14495 }

dpsRTUv2p15495Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 47 is cleared"
	::= { dpsRTUv2 15495 }

dpsRTUv2p14496Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 48 is set"
	::= { dpsRTUv2 14496 }

dpsRTUv2p15496Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 48 is cleared"
	::= { dpsRTUv2 15496 }

dpsRTUv2p14497Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 49 is set"
	::= { dpsRTUv2 14497 }

dpsRTUv2p15497Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 49 is cleared"
	::= { dpsRTUv2 15497 }

dpsRTUv2p14498Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 50 is set"
	::= { dpsRTUv2 14498 }

dpsRTUv2p15498Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 50 is cleared"
	::= { dpsRTUv2 15498 }

dpsRTUv2p14499Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 51 is set"
	::= { dpsRTUv2 14499 }

dpsRTUv2p15499Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 51 is cleared"
	::= { dpsRTUv2 15499 }

dpsRTUv2p14500Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 52 is set"
	::= { dpsRTUv2 14500 }

dpsRTUv2p15500Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 52 is cleared"
	::= { dpsRTUv2 15500 }

dpsRTUv2p14501Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 53 is set"
	::= { dpsRTUv2 14501 }

dpsRTUv2p15501Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 53 is cleared"
	::= { dpsRTUv2 15501 }

dpsRTUv2p14502Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 54 is set"
	::= { dpsRTUv2 14502 }

dpsRTUv2p15502Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 54 is cleared"
	::= { dpsRTUv2 15502 }

dpsRTUv2p14503Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 55 is set"
	::= { dpsRTUv2 14503 }

dpsRTUv2p15503Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 55 is cleared"
	::= { dpsRTUv2 15503 }

dpsRTUv2p14504Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 56 is set"
	::= { dpsRTUv2 14504 }

dpsRTUv2p15504Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 56 is cleared"
	::= { dpsRTUv2 15504 }

dpsRTUv2p14505Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 57 is set"
	::= { dpsRTUv2 14505 }

dpsRTUv2p15505Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 57 is cleared"
	::= { dpsRTUv2 15505 }

dpsRTUv2p14506Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 58 is set"
	::= { dpsRTUv2 14506 }

dpsRTUv2p15506Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 58 is cleared"
	::= { dpsRTUv2 15506 }

dpsRTUv2p14507Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 59 is set"
	::= { dpsRTUv2 14507 }

dpsRTUv2p15507Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 59 is cleared"
	::= { dpsRTUv2 15507 }

dpsRTUv2p14508Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 60 is set"
	::= { dpsRTUv2 14508 }

dpsRTUv2p15508Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 60 is cleared"
	::= { dpsRTUv2 15508 }

dpsRTUv2p14509Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 61 is set"
	::= { dpsRTUv2 14509 }

dpsRTUv2p15509Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 61 is cleared"
	::= { dpsRTUv2 15509 }

dpsRTUv2p14510Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 62 is set"
	::= { dpsRTUv2 14510 }

dpsRTUv2p15510Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 62 is cleared"
	::= { dpsRTUv2 15510 }

dpsRTUv2p14511Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 63 is set"
	::= { dpsRTUv2 14511 }

dpsRTUv2p15511Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 63 is cleared"
	::= { dpsRTUv2 15511 }

dpsRTUv2p14512Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 64 is set"
	::= { dpsRTUv2 14512 }

dpsRTUv2p15512Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 3 display 8 point 64 is cleared"
	::= { dpsRTUv2 15512 }

dpsRTUv2p16001Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 1 is set"
	::= { dpsRTUv2 16001 }

dpsRTUv2p17001Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 1 is cleared"
	::= { dpsRTUv2 17001 }

dpsRTUv2p16002Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 2 is set"
	::= { dpsRTUv2 16002 }

dpsRTUv2p17002Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 2 is cleared"
	::= { dpsRTUv2 17002 }

dpsRTUv2p16003Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 3 is set"
	::= { dpsRTUv2 16003 }

dpsRTUv2p17003Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 3 is cleared"
	::= { dpsRTUv2 17003 }

dpsRTUv2p16004Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 4 is set"
	::= { dpsRTUv2 16004 }

dpsRTUv2p17004Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 4 is cleared"
	::= { dpsRTUv2 17004 }

dpsRTUv2p16005Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 5 is set"
	::= { dpsRTUv2 16005 }

dpsRTUv2p17005Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 5 is cleared"
	::= { dpsRTUv2 17005 }

dpsRTUv2p16006Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 6 is set"
	::= { dpsRTUv2 16006 }

dpsRTUv2p17006Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 6 is cleared"
	::= { dpsRTUv2 17006 }

dpsRTUv2p16007Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 7 is set"
	::= { dpsRTUv2 16007 }

dpsRTUv2p17007Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 7 is cleared"
	::= { dpsRTUv2 17007 }

dpsRTUv2p16008Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 8 is set"
	::= { dpsRTUv2 16008 }

dpsRTUv2p17008Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 8 is cleared"
	::= { dpsRTUv2 17008 }

dpsRTUv2p16009Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 9 is set"
	::= { dpsRTUv2 16009 }

dpsRTUv2p17009Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 9 is cleared"
	::= { dpsRTUv2 17009 }

dpsRTUv2p16010Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 10 is set"
	::= { dpsRTUv2 16010 }

dpsRTUv2p17010Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 10 is cleared"
	::= { dpsRTUv2 17010 }

dpsRTUv2p16011Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 11 is set"
	::= { dpsRTUv2 16011 }

dpsRTUv2p17011Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 11 is cleared"
	::= { dpsRTUv2 17011 }

dpsRTUv2p16012Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 12 is set"
	::= { dpsRTUv2 16012 }

dpsRTUv2p17012Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 12 is cleared"
	::= { dpsRTUv2 17012 }

dpsRTUv2p16013Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 13 is set"
	::= { dpsRTUv2 16013 }

dpsRTUv2p17013Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 13 is cleared"
	::= { dpsRTUv2 17013 }

dpsRTUv2p16014Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 14 is set"
	::= { dpsRTUv2 16014 }

dpsRTUv2p17014Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 14 is cleared"
	::= { dpsRTUv2 17014 }

dpsRTUv2p16015Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 15 is set"
	::= { dpsRTUv2 16015 }

dpsRTUv2p17015Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 15 is cleared"
	::= { dpsRTUv2 17015 }

dpsRTUv2p16016Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 16 is set"
	::= { dpsRTUv2 16016 }

dpsRTUv2p17016Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 16 is cleared"
	::= { dpsRTUv2 17016 }

dpsRTUv2p16017Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 17 is set"
	::= { dpsRTUv2 16017 }

dpsRTUv2p17017Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 17 is cleared"
	::= { dpsRTUv2 17017 }

dpsRTUv2p16018Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 18 is set"
	::= { dpsRTUv2 16018 }

dpsRTUv2p17018Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 18 is cleared"
	::= { dpsRTUv2 17018 }

dpsRTUv2p16019Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 19 is set"
	::= { dpsRTUv2 16019 }

dpsRTUv2p17019Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 19 is cleared"
	::= { dpsRTUv2 17019 }

dpsRTUv2p16020Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 20 is set"
	::= { dpsRTUv2 16020 }

dpsRTUv2p17020Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 20 is cleared"
	::= { dpsRTUv2 17020 }

dpsRTUv2p16021Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 21 is set"
	::= { dpsRTUv2 16021 }

dpsRTUv2p17021Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 21 is cleared"
	::= { dpsRTUv2 17021 }

dpsRTUv2p16022Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 22 is set"
	::= { dpsRTUv2 16022 }

dpsRTUv2p17022Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 22 is cleared"
	::= { dpsRTUv2 17022 }

dpsRTUv2p16023Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 23 is set"
	::= { dpsRTUv2 16023 }

dpsRTUv2p17023Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 23 is cleared"
	::= { dpsRTUv2 17023 }

dpsRTUv2p16024Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 24 is set"
	::= { dpsRTUv2 16024 }

dpsRTUv2p17024Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 24 is cleared"
	::= { dpsRTUv2 17024 }

dpsRTUv2p16025Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 25 is set"
	::= { dpsRTUv2 16025 }

dpsRTUv2p17025Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 25 is cleared"
	::= { dpsRTUv2 17025 }

dpsRTUv2p16026Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 26 is set"
	::= { dpsRTUv2 16026 }

dpsRTUv2p17026Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 26 is cleared"
	::= { dpsRTUv2 17026 }

dpsRTUv2p16027Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 27 is set"
	::= { dpsRTUv2 16027 }

dpsRTUv2p17027Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 27 is cleared"
	::= { dpsRTUv2 17027 }

dpsRTUv2p16028Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 28 is set"
	::= { dpsRTUv2 16028 }

dpsRTUv2p17028Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 28 is cleared"
	::= { dpsRTUv2 17028 }

dpsRTUv2p16029Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 29 is set"
	::= { dpsRTUv2 16029 }

dpsRTUv2p17029Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 29 is cleared"
	::= { dpsRTUv2 17029 }

dpsRTUv2p16030Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 30 is set"
	::= { dpsRTUv2 16030 }

dpsRTUv2p17030Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 30 is cleared"
	::= { dpsRTUv2 17030 }

dpsRTUv2p16031Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 31 is set"
	::= { dpsRTUv2 16031 }

dpsRTUv2p17031Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 31 is cleared"
	::= { dpsRTUv2 17031 }

dpsRTUv2p16032Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 32 is set"
	::= { dpsRTUv2 16032 }

dpsRTUv2p17032Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 32 is cleared"
	::= { dpsRTUv2 17032 }

dpsRTUv2p16033Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 33 is set"
	::= { dpsRTUv2 16033 }

dpsRTUv2p17033Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 33 is cleared"
	::= { dpsRTUv2 17033 }

dpsRTUv2p16034Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 34 is set"
	::= { dpsRTUv2 16034 }

dpsRTUv2p17034Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 34 is cleared"
	::= { dpsRTUv2 17034 }

dpsRTUv2p16035Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 35 is set"
	::= { dpsRTUv2 16035 }

dpsRTUv2p17035Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 35 is cleared"
	::= { dpsRTUv2 17035 }

dpsRTUv2p16036Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 36 is set"
	::= { dpsRTUv2 16036 }

dpsRTUv2p17036Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 36 is cleared"
	::= { dpsRTUv2 17036 }

dpsRTUv2p16037Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 37 is set"
	::= { dpsRTUv2 16037 }

dpsRTUv2p17037Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 37 is cleared"
	::= { dpsRTUv2 17037 }

dpsRTUv2p16038Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 38 is set"
	::= { dpsRTUv2 16038 }

dpsRTUv2p17038Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 38 is cleared"
	::= { dpsRTUv2 17038 }

dpsRTUv2p16039Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 39 is set"
	::= { dpsRTUv2 16039 }

dpsRTUv2p17039Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 39 is cleared"
	::= { dpsRTUv2 17039 }

dpsRTUv2p16040Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 40 is set"
	::= { dpsRTUv2 16040 }

dpsRTUv2p17040Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 40 is cleared"
	::= { dpsRTUv2 17040 }

dpsRTUv2p16041Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 41 is set"
	::= { dpsRTUv2 16041 }

dpsRTUv2p17041Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 41 is cleared"
	::= { dpsRTUv2 17041 }

dpsRTUv2p16042Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 42 is set"
	::= { dpsRTUv2 16042 }

dpsRTUv2p17042Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 42 is cleared"
	::= { dpsRTUv2 17042 }

dpsRTUv2p16043Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 43 is set"
	::= { dpsRTUv2 16043 }

dpsRTUv2p17043Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 43 is cleared"
	::= { dpsRTUv2 17043 }

dpsRTUv2p16044Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 44 is set"
	::= { dpsRTUv2 16044 }

dpsRTUv2p17044Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 44 is cleared"
	::= { dpsRTUv2 17044 }

dpsRTUv2p16045Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 45 is set"
	::= { dpsRTUv2 16045 }

dpsRTUv2p17045Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 45 is cleared"
	::= { dpsRTUv2 17045 }

dpsRTUv2p16046Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 46 is set"
	::= { dpsRTUv2 16046 }

dpsRTUv2p17046Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 46 is cleared"
	::= { dpsRTUv2 17046 }

dpsRTUv2p16047Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 47 is set"
	::= { dpsRTUv2 16047 }

dpsRTUv2p17047Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 47 is cleared"
	::= { dpsRTUv2 17047 }

dpsRTUv2p16048Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 48 is set"
	::= { dpsRTUv2 16048 }

dpsRTUv2p17048Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 48 is cleared"
	::= { dpsRTUv2 17048 }

dpsRTUv2p16049Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 49 is set"
	::= { dpsRTUv2 16049 }

dpsRTUv2p17049Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 49 is cleared"
	::= { dpsRTUv2 17049 }

dpsRTUv2p16050Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 50 is set"
	::= { dpsRTUv2 16050 }

dpsRTUv2p17050Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 50 is cleared"
	::= { dpsRTUv2 17050 }

dpsRTUv2p16051Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 51 is set"
	::= { dpsRTUv2 16051 }

dpsRTUv2p17051Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 51 is cleared"
	::= { dpsRTUv2 17051 }

dpsRTUv2p16052Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 52 is set"
	::= { dpsRTUv2 16052 }

dpsRTUv2p17052Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 52 is cleared"
	::= { dpsRTUv2 17052 }

dpsRTUv2p16053Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 53 is set"
	::= { dpsRTUv2 16053 }

dpsRTUv2p17053Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 53 is cleared"
	::= { dpsRTUv2 17053 }

dpsRTUv2p16054Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 54 is set"
	::= { dpsRTUv2 16054 }

dpsRTUv2p17054Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 54 is cleared"
	::= { dpsRTUv2 17054 }

dpsRTUv2p16055Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 55 is set"
	::= { dpsRTUv2 16055 }

dpsRTUv2p17055Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 55 is cleared"
	::= { dpsRTUv2 17055 }

dpsRTUv2p16056Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 56 is set"
	::= { dpsRTUv2 16056 }

dpsRTUv2p17056Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 56 is cleared"
	::= { dpsRTUv2 17056 }

dpsRTUv2p16057Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 57 is set"
	::= { dpsRTUv2 16057 }

dpsRTUv2p17057Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 57 is cleared"
	::= { dpsRTUv2 17057 }

dpsRTUv2p16058Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 58 is set"
	::= { dpsRTUv2 16058 }

dpsRTUv2p17058Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 58 is cleared"
	::= { dpsRTUv2 17058 }

dpsRTUv2p16059Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 59 is set"
	::= { dpsRTUv2 16059 }

dpsRTUv2p17059Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 59 is cleared"
	::= { dpsRTUv2 17059 }

dpsRTUv2p16060Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 60 is set"
	::= { dpsRTUv2 16060 }

dpsRTUv2p17060Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 60 is cleared"
	::= { dpsRTUv2 17060 }

dpsRTUv2p16061Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 61 is set"
	::= { dpsRTUv2 16061 }

dpsRTUv2p17061Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 61 is cleared"
	::= { dpsRTUv2 17061 }

dpsRTUv2p16062Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 62 is set"
	::= { dpsRTUv2 16062 }

dpsRTUv2p17062Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 62 is cleared"
	::= { dpsRTUv2 17062 }

dpsRTUv2p16063Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 63 is set"
	::= { dpsRTUv2 16063 }

dpsRTUv2p17063Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 63 is cleared"
	::= { dpsRTUv2 17063 }

dpsRTUv2p16064Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 64 is set"
	::= { dpsRTUv2 16064 }

dpsRTUv2p17064Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 1 point 64 is cleared"
	::= { dpsRTUv2 17064 }

dpsRTUv2p16065Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 1 is set"
	::= { dpsRTUv2 16065 }

dpsRTUv2p17065Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 1 is cleared"
	::= { dpsRTUv2 17065 }

dpsRTUv2p16066Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 2 is set"
	::= { dpsRTUv2 16066 }

dpsRTUv2p17066Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 2 is cleared"
	::= { dpsRTUv2 17066 }

dpsRTUv2p16067Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 3 is set"
	::= { dpsRTUv2 16067 }

dpsRTUv2p17067Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 3 is cleared"
	::= { dpsRTUv2 17067 }

dpsRTUv2p16068Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 4 is set"
	::= { dpsRTUv2 16068 }

dpsRTUv2p17068Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 4 is cleared"
	::= { dpsRTUv2 17068 }

dpsRTUv2p16069Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 5 is set"
	::= { dpsRTUv2 16069 }

dpsRTUv2p17069Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 5 is cleared"
	::= { dpsRTUv2 17069 }

dpsRTUv2p16070Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 6 is set"
	::= { dpsRTUv2 16070 }

dpsRTUv2p17070Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 6 is cleared"
	::= { dpsRTUv2 17070 }

dpsRTUv2p16071Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 7 is set"
	::= { dpsRTUv2 16071 }

dpsRTUv2p17071Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 7 is cleared"
	::= { dpsRTUv2 17071 }

dpsRTUv2p16072Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 8 is set"
	::= { dpsRTUv2 16072 }

dpsRTUv2p17072Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 8 is cleared"
	::= { dpsRTUv2 17072 }

dpsRTUv2p16073Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 9 is set"
	::= { dpsRTUv2 16073 }

dpsRTUv2p17073Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 9 is cleared"
	::= { dpsRTUv2 17073 }

dpsRTUv2p16074Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 10 is set"
	::= { dpsRTUv2 16074 }

dpsRTUv2p17074Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 10 is cleared"
	::= { dpsRTUv2 17074 }

dpsRTUv2p16075Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 11 is set"
	::= { dpsRTUv2 16075 }

dpsRTUv2p17075Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 11 is cleared"
	::= { dpsRTUv2 17075 }

dpsRTUv2p16076Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 12 is set"
	::= { dpsRTUv2 16076 }

dpsRTUv2p17076Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 12 is cleared"
	::= { dpsRTUv2 17076 }

dpsRTUv2p16077Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 13 is set"
	::= { dpsRTUv2 16077 }

dpsRTUv2p17077Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 13 is cleared"
	::= { dpsRTUv2 17077 }

dpsRTUv2p16078Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 14 is set"
	::= { dpsRTUv2 16078 }

dpsRTUv2p17078Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 14 is cleared"
	::= { dpsRTUv2 17078 }

dpsRTUv2p16079Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 15 is set"
	::= { dpsRTUv2 16079 }

dpsRTUv2p17079Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 15 is cleared"
	::= { dpsRTUv2 17079 }

dpsRTUv2p16080Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 16 is set"
	::= { dpsRTUv2 16080 }

dpsRTUv2p17080Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 16 is cleared"
	::= { dpsRTUv2 17080 }

dpsRTUv2p16081Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 17 is set"
	::= { dpsRTUv2 16081 }

dpsRTUv2p17081Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 17 is cleared"
	::= { dpsRTUv2 17081 }

dpsRTUv2p16082Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 18 is set"
	::= { dpsRTUv2 16082 }

dpsRTUv2p17082Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 18 is cleared"
	::= { dpsRTUv2 17082 }

dpsRTUv2p16083Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 19 is set"
	::= { dpsRTUv2 16083 }

dpsRTUv2p17083Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 19 is cleared"
	::= { dpsRTUv2 17083 }

dpsRTUv2p16084Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 20 is set"
	::= { dpsRTUv2 16084 }

dpsRTUv2p17084Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 20 is cleared"
	::= { dpsRTUv2 17084 }

dpsRTUv2p16085Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 21 is set"
	::= { dpsRTUv2 16085 }

dpsRTUv2p17085Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 21 is cleared"
	::= { dpsRTUv2 17085 }

dpsRTUv2p16086Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 22 is set"
	::= { dpsRTUv2 16086 }

dpsRTUv2p17086Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 22 is cleared"
	::= { dpsRTUv2 17086 }

dpsRTUv2p16087Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 23 is set"
	::= { dpsRTUv2 16087 }

dpsRTUv2p17087Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 23 is cleared"
	::= { dpsRTUv2 17087 }

dpsRTUv2p16088Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 24 is set"
	::= { dpsRTUv2 16088 }

dpsRTUv2p17088Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 24 is cleared"
	::= { dpsRTUv2 17088 }

dpsRTUv2p16089Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 25 is set"
	::= { dpsRTUv2 16089 }

dpsRTUv2p17089Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 25 is cleared"
	::= { dpsRTUv2 17089 }

dpsRTUv2p16090Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 26 is set"
	::= { dpsRTUv2 16090 }

dpsRTUv2p17090Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 26 is cleared"
	::= { dpsRTUv2 17090 }

dpsRTUv2p16091Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 27 is set"
	::= { dpsRTUv2 16091 }

dpsRTUv2p17091Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 27 is cleared"
	::= { dpsRTUv2 17091 }

dpsRTUv2p16092Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 28 is set"
	::= { dpsRTUv2 16092 }

dpsRTUv2p17092Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 28 is cleared"
	::= { dpsRTUv2 17092 }

dpsRTUv2p16093Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 29 is set"
	::= { dpsRTUv2 16093 }

dpsRTUv2p17093Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 29 is cleared"
	::= { dpsRTUv2 17093 }

dpsRTUv2p16094Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 30 is set"
	::= { dpsRTUv2 16094 }

dpsRTUv2p17094Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 30 is cleared"
	::= { dpsRTUv2 17094 }

dpsRTUv2p16095Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 31 is set"
	::= { dpsRTUv2 16095 }

dpsRTUv2p17095Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 31 is cleared"
	::= { dpsRTUv2 17095 }

dpsRTUv2p16096Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 32 is set"
	::= { dpsRTUv2 16096 }

dpsRTUv2p17096Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 32 is cleared"
	::= { dpsRTUv2 17096 }

dpsRTUv2p16097Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 33 is set"
	::= { dpsRTUv2 16097 }

dpsRTUv2p17097Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 33 is cleared"
	::= { dpsRTUv2 17097 }

dpsRTUv2p16098Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 34 is set"
	::= { dpsRTUv2 16098 }

dpsRTUv2p17098Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 34 is cleared"
	::= { dpsRTUv2 17098 }

dpsRTUv2p16099Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 35 is set"
	::= { dpsRTUv2 16099 }

dpsRTUv2p17099Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 35 is cleared"
	::= { dpsRTUv2 17099 }

dpsRTUv2p16100Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 36 is set"
	::= { dpsRTUv2 16100 }

dpsRTUv2p17100Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 36 is cleared"
	::= { dpsRTUv2 17100 }

dpsRTUv2p16101Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 37 is set"
	::= { dpsRTUv2 16101 }

dpsRTUv2p17101Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 37 is cleared"
	::= { dpsRTUv2 17101 }

dpsRTUv2p16102Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 38 is set"
	::= { dpsRTUv2 16102 }

dpsRTUv2p17102Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 38 is cleared"
	::= { dpsRTUv2 17102 }

dpsRTUv2p16103Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 39 is set"
	::= { dpsRTUv2 16103 }

dpsRTUv2p17103Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 39 is cleared"
	::= { dpsRTUv2 17103 }

dpsRTUv2p16104Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 40 is set"
	::= { dpsRTUv2 16104 }

dpsRTUv2p17104Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 40 is cleared"
	::= { dpsRTUv2 17104 }

dpsRTUv2p16105Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 41 is set"
	::= { dpsRTUv2 16105 }

dpsRTUv2p17105Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 41 is cleared"
	::= { dpsRTUv2 17105 }

dpsRTUv2p16106Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 42 is set"
	::= { dpsRTUv2 16106 }

dpsRTUv2p17106Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 42 is cleared"
	::= { dpsRTUv2 17106 }

dpsRTUv2p16107Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 43 is set"
	::= { dpsRTUv2 16107 }

dpsRTUv2p17107Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 43 is cleared"
	::= { dpsRTUv2 17107 }

dpsRTUv2p16108Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 44 is set"
	::= { dpsRTUv2 16108 }

dpsRTUv2p17108Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 44 is cleared"
	::= { dpsRTUv2 17108 }

dpsRTUv2p16109Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 45 is set"
	::= { dpsRTUv2 16109 }

dpsRTUv2p17109Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 45 is cleared"
	::= { dpsRTUv2 17109 }

dpsRTUv2p16110Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 46 is set"
	::= { dpsRTUv2 16110 }

dpsRTUv2p17110Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 46 is cleared"
	::= { dpsRTUv2 17110 }

dpsRTUv2p16111Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 47 is set"
	::= { dpsRTUv2 16111 }

dpsRTUv2p17111Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 47 is cleared"
	::= { dpsRTUv2 17111 }

dpsRTUv2p16112Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 48 is set"
	::= { dpsRTUv2 16112 }

dpsRTUv2p17112Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 48 is cleared"
	::= { dpsRTUv2 17112 }

dpsRTUv2p16113Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 49 is set"
	::= { dpsRTUv2 16113 }

dpsRTUv2p17113Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 49 is cleared"
	::= { dpsRTUv2 17113 }

dpsRTUv2p16114Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 50 is set"
	::= { dpsRTUv2 16114 }

dpsRTUv2p17114Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 50 is cleared"
	::= { dpsRTUv2 17114 }

dpsRTUv2p16115Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 51 is set"
	::= { dpsRTUv2 16115 }

dpsRTUv2p17115Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 51 is cleared"
	::= { dpsRTUv2 17115 }

dpsRTUv2p16116Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 52 is set"
	::= { dpsRTUv2 16116 }

dpsRTUv2p17116Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 52 is cleared"
	::= { dpsRTUv2 17116 }

dpsRTUv2p16117Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 53 is set"
	::= { dpsRTUv2 16117 }

dpsRTUv2p17117Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 53 is cleared"
	::= { dpsRTUv2 17117 }

dpsRTUv2p16118Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 54 is set"
	::= { dpsRTUv2 16118 }

dpsRTUv2p17118Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 54 is cleared"
	::= { dpsRTUv2 17118 }

dpsRTUv2p16119Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 55 is set"
	::= { dpsRTUv2 16119 }

dpsRTUv2p17119Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 55 is cleared"
	::= { dpsRTUv2 17119 }

dpsRTUv2p16120Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 56 is set"
	::= { dpsRTUv2 16120 }

dpsRTUv2p17120Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 56 is cleared"
	::= { dpsRTUv2 17120 }

dpsRTUv2p16121Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 57 is set"
	::= { dpsRTUv2 16121 }

dpsRTUv2p17121Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 57 is cleared"
	::= { dpsRTUv2 17121 }

dpsRTUv2p16122Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 58 is set"
	::= { dpsRTUv2 16122 }

dpsRTUv2p17122Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 58 is cleared"
	::= { dpsRTUv2 17122 }

dpsRTUv2p16123Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 59 is set"
	::= { dpsRTUv2 16123 }

dpsRTUv2p17123Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 59 is cleared"
	::= { dpsRTUv2 17123 }

dpsRTUv2p16124Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 60 is set"
	::= { dpsRTUv2 16124 }

dpsRTUv2p17124Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 60 is cleared"
	::= { dpsRTUv2 17124 }

dpsRTUv2p16125Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 61 is set"
	::= { dpsRTUv2 16125 }

dpsRTUv2p17125Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 61 is cleared"
	::= { dpsRTUv2 17125 }

dpsRTUv2p16126Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 62 is set"
	::= { dpsRTUv2 16126 }

dpsRTUv2p17126Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 62 is cleared"
	::= { dpsRTUv2 17126 }

dpsRTUv2p16127Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 63 is set"
	::= { dpsRTUv2 16127 }

dpsRTUv2p17127Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 63 is cleared"
	::= { dpsRTUv2 17127 }

dpsRTUv2p16128Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 64 is set"
	::= { dpsRTUv2 16128 }

dpsRTUv2p17128Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 2 point 64 is cleared"
	::= { dpsRTUv2 17128 }

dpsRTUv2p16129Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 1 is set"
	::= { dpsRTUv2 16129 }

dpsRTUv2p17129Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 1 is cleared"
	::= { dpsRTUv2 17129 }

dpsRTUv2p16130Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 2 is set"
	::= { dpsRTUv2 16130 }

dpsRTUv2p17130Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 2 is cleared"
	::= { dpsRTUv2 17130 }

dpsRTUv2p16131Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 3 is set"
	::= { dpsRTUv2 16131 }

dpsRTUv2p17131Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 3 is cleared"
	::= { dpsRTUv2 17131 }

dpsRTUv2p16132Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 4 is set"
	::= { dpsRTUv2 16132 }

dpsRTUv2p17132Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 4 is cleared"
	::= { dpsRTUv2 17132 }

dpsRTUv2p16133Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 5 is set"
	::= { dpsRTUv2 16133 }

dpsRTUv2p17133Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 5 is cleared"
	::= { dpsRTUv2 17133 }

dpsRTUv2p16134Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 6 is set"
	::= { dpsRTUv2 16134 }

dpsRTUv2p17134Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 6 is cleared"
	::= { dpsRTUv2 17134 }

dpsRTUv2p16135Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 7 is set"
	::= { dpsRTUv2 16135 }

dpsRTUv2p17135Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 7 is cleared"
	::= { dpsRTUv2 17135 }

dpsRTUv2p16136Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 8 is set"
	::= { dpsRTUv2 16136 }

dpsRTUv2p17136Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 8 is cleared"
	::= { dpsRTUv2 17136 }

dpsRTUv2p16137Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 9 is set"
	::= { dpsRTUv2 16137 }

dpsRTUv2p17137Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 9 is cleared"
	::= { dpsRTUv2 17137 }

dpsRTUv2p16138Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 10 is set"
	::= { dpsRTUv2 16138 }

dpsRTUv2p17138Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 10 is cleared"
	::= { dpsRTUv2 17138 }

dpsRTUv2p16139Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 11 is set"
	::= { dpsRTUv2 16139 }

dpsRTUv2p17139Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 11 is cleared"
	::= { dpsRTUv2 17139 }

dpsRTUv2p16140Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 12 is set"
	::= { dpsRTUv2 16140 }

dpsRTUv2p17140Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 12 is cleared"
	::= { dpsRTUv2 17140 }

dpsRTUv2p16141Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 13 is set"
	::= { dpsRTUv2 16141 }

dpsRTUv2p17141Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 13 is cleared"
	::= { dpsRTUv2 17141 }

dpsRTUv2p16142Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 14 is set"
	::= { dpsRTUv2 16142 }

dpsRTUv2p17142Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 14 is cleared"
	::= { dpsRTUv2 17142 }

dpsRTUv2p16143Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 15 is set"
	::= { dpsRTUv2 16143 }

dpsRTUv2p17143Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 15 is cleared"
	::= { dpsRTUv2 17143 }

dpsRTUv2p16144Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 16 is set"
	::= { dpsRTUv2 16144 }

dpsRTUv2p17144Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 16 is cleared"
	::= { dpsRTUv2 17144 }

dpsRTUv2p16145Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 17 is set"
	::= { dpsRTUv2 16145 }

dpsRTUv2p17145Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 17 is cleared"
	::= { dpsRTUv2 17145 }

dpsRTUv2p16146Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 18 is set"
	::= { dpsRTUv2 16146 }

dpsRTUv2p17146Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 18 is cleared"
	::= { dpsRTUv2 17146 }

dpsRTUv2p16147Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 19 is set"
	::= { dpsRTUv2 16147 }

dpsRTUv2p17147Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 19 is cleared"
	::= { dpsRTUv2 17147 }

dpsRTUv2p16148Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 20 is set"
	::= { dpsRTUv2 16148 }

dpsRTUv2p17148Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 20 is cleared"
	::= { dpsRTUv2 17148 }

dpsRTUv2p16149Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 21 is set"
	::= { dpsRTUv2 16149 }

dpsRTUv2p17149Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 21 is cleared"
	::= { dpsRTUv2 17149 }

dpsRTUv2p16150Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 22 is set"
	::= { dpsRTUv2 16150 }

dpsRTUv2p17150Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 22 is cleared"
	::= { dpsRTUv2 17150 }

dpsRTUv2p16151Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 23 is set"
	::= { dpsRTUv2 16151 }

dpsRTUv2p17151Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 23 is cleared"
	::= { dpsRTUv2 17151 }

dpsRTUv2p16152Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 24 is set"
	::= { dpsRTUv2 16152 }

dpsRTUv2p17152Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 24 is cleared"
	::= { dpsRTUv2 17152 }

dpsRTUv2p16153Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 25 is set"
	::= { dpsRTUv2 16153 }

dpsRTUv2p17153Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 25 is cleared"
	::= { dpsRTUv2 17153 }

dpsRTUv2p16154Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 26 is set"
	::= { dpsRTUv2 16154 }

dpsRTUv2p17154Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 26 is cleared"
	::= { dpsRTUv2 17154 }

dpsRTUv2p16155Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 27 is set"
	::= { dpsRTUv2 16155 }

dpsRTUv2p17155Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 27 is cleared"
	::= { dpsRTUv2 17155 }

dpsRTUv2p16156Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 28 is set"
	::= { dpsRTUv2 16156 }

dpsRTUv2p17156Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 28 is cleared"
	::= { dpsRTUv2 17156 }

dpsRTUv2p16157Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 29 is set"
	::= { dpsRTUv2 16157 }

dpsRTUv2p17157Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 29 is cleared"
	::= { dpsRTUv2 17157 }

dpsRTUv2p16158Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 30 is set"
	::= { dpsRTUv2 16158 }

dpsRTUv2p17158Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 30 is cleared"
	::= { dpsRTUv2 17158 }

dpsRTUv2p16159Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 31 is set"
	::= { dpsRTUv2 16159 }

dpsRTUv2p17159Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 31 is cleared"
	::= { dpsRTUv2 17159 }

dpsRTUv2p16160Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 32 is set"
	::= { dpsRTUv2 16160 }

dpsRTUv2p17160Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 32 is cleared"
	::= { dpsRTUv2 17160 }

dpsRTUv2p16161Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 33 is set"
	::= { dpsRTUv2 16161 }

dpsRTUv2p17161Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 33 is cleared"
	::= { dpsRTUv2 17161 }

dpsRTUv2p16162Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 34 is set"
	::= { dpsRTUv2 16162 }

dpsRTUv2p17162Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 34 is cleared"
	::= { dpsRTUv2 17162 }

dpsRTUv2p16163Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 35 is set"
	::= { dpsRTUv2 16163 }

dpsRTUv2p17163Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 35 is cleared"
	::= { dpsRTUv2 17163 }

dpsRTUv2p16164Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 36 is set"
	::= { dpsRTUv2 16164 }

dpsRTUv2p17164Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 36 is cleared"
	::= { dpsRTUv2 17164 }

dpsRTUv2p16165Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 37 is set"
	::= { dpsRTUv2 16165 }

dpsRTUv2p17165Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 37 is cleared"
	::= { dpsRTUv2 17165 }

dpsRTUv2p16166Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 38 is set"
	::= { dpsRTUv2 16166 }

dpsRTUv2p17166Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 38 is cleared"
	::= { dpsRTUv2 17166 }

dpsRTUv2p16167Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 39 is set"
	::= { dpsRTUv2 16167 }

dpsRTUv2p17167Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 39 is cleared"
	::= { dpsRTUv2 17167 }

dpsRTUv2p16168Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 40 is set"
	::= { dpsRTUv2 16168 }

dpsRTUv2p17168Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 40 is cleared"
	::= { dpsRTUv2 17168 }

dpsRTUv2p16169Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 41 is set"
	::= { dpsRTUv2 16169 }

dpsRTUv2p17169Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 41 is cleared"
	::= { dpsRTUv2 17169 }

dpsRTUv2p16170Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 42 is set"
	::= { dpsRTUv2 16170 }

dpsRTUv2p17170Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 42 is cleared"
	::= { dpsRTUv2 17170 }

dpsRTUv2p16171Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 43 is set"
	::= { dpsRTUv2 16171 }

dpsRTUv2p17171Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 43 is cleared"
	::= { dpsRTUv2 17171 }

dpsRTUv2p16172Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 44 is set"
	::= { dpsRTUv2 16172 }

dpsRTUv2p17172Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 44 is cleared"
	::= { dpsRTUv2 17172 }

dpsRTUv2p16173Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 45 is set"
	::= { dpsRTUv2 16173 }

dpsRTUv2p17173Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 45 is cleared"
	::= { dpsRTUv2 17173 }

dpsRTUv2p16174Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 46 is set"
	::= { dpsRTUv2 16174 }

dpsRTUv2p17174Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 46 is cleared"
	::= { dpsRTUv2 17174 }

dpsRTUv2p16175Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 47 is set"
	::= { dpsRTUv2 16175 }

dpsRTUv2p17175Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 47 is cleared"
	::= { dpsRTUv2 17175 }

dpsRTUv2p16176Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 48 is set"
	::= { dpsRTUv2 16176 }

dpsRTUv2p17176Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 48 is cleared"
	::= { dpsRTUv2 17176 }

dpsRTUv2p16177Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 49 is set"
	::= { dpsRTUv2 16177 }

dpsRTUv2p17177Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 49 is cleared"
	::= { dpsRTUv2 17177 }

dpsRTUv2p16178Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 50 is set"
	::= { dpsRTUv2 16178 }

dpsRTUv2p17178Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 50 is cleared"
	::= { dpsRTUv2 17178 }

dpsRTUv2p16179Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 51 is set"
	::= { dpsRTUv2 16179 }

dpsRTUv2p17179Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 51 is cleared"
	::= { dpsRTUv2 17179 }

dpsRTUv2p16180Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 52 is set"
	::= { dpsRTUv2 16180 }

dpsRTUv2p17180Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 52 is cleared"
	::= { dpsRTUv2 17180 }

dpsRTUv2p16181Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 53 is set"
	::= { dpsRTUv2 16181 }

dpsRTUv2p17181Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 53 is cleared"
	::= { dpsRTUv2 17181 }

dpsRTUv2p16182Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 54 is set"
	::= { dpsRTUv2 16182 }

dpsRTUv2p17182Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 54 is cleared"
	::= { dpsRTUv2 17182 }

dpsRTUv2p16183Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 55 is set"
	::= { dpsRTUv2 16183 }

dpsRTUv2p17183Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 55 is cleared"
	::= { dpsRTUv2 17183 }

dpsRTUv2p16184Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 56 is set"
	::= { dpsRTUv2 16184 }

dpsRTUv2p17184Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 56 is cleared"
	::= { dpsRTUv2 17184 }

dpsRTUv2p16185Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 57 is set"
	::= { dpsRTUv2 16185 }

dpsRTUv2p17185Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 57 is cleared"
	::= { dpsRTUv2 17185 }

dpsRTUv2p16186Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 58 is set"
	::= { dpsRTUv2 16186 }

dpsRTUv2p17186Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 58 is cleared"
	::= { dpsRTUv2 17186 }

dpsRTUv2p16187Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 59 is set"
	::= { dpsRTUv2 16187 }

dpsRTUv2p17187Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 59 is cleared"
	::= { dpsRTUv2 17187 }

dpsRTUv2p16188Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 60 is set"
	::= { dpsRTUv2 16188 }

dpsRTUv2p17188Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 60 is cleared"
	::= { dpsRTUv2 17188 }

dpsRTUv2p16189Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 61 is set"
	::= { dpsRTUv2 16189 }

dpsRTUv2p17189Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 61 is cleared"
	::= { dpsRTUv2 17189 }

dpsRTUv2p16190Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 62 is set"
	::= { dpsRTUv2 16190 }

dpsRTUv2p17190Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 62 is cleared"
	::= { dpsRTUv2 17190 }

dpsRTUv2p16191Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 63 is set"
	::= { dpsRTUv2 16191 }

dpsRTUv2p17191Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 63 is cleared"
	::= { dpsRTUv2 17191 }

dpsRTUv2p16192Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 64 is set"
	::= { dpsRTUv2 16192 }

dpsRTUv2p17192Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 3 point 64 is cleared"
	::= { dpsRTUv2 17192 }

dpsRTUv2p16193Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 1 is set"
	::= { dpsRTUv2 16193 }

dpsRTUv2p17193Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 1 is cleared"
	::= { dpsRTUv2 17193 }

dpsRTUv2p16194Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 2 is set"
	::= { dpsRTUv2 16194 }

dpsRTUv2p17194Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 2 is cleared"
	::= { dpsRTUv2 17194 }

dpsRTUv2p16195Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 3 is set"
	::= { dpsRTUv2 16195 }

dpsRTUv2p17195Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 3 is cleared"
	::= { dpsRTUv2 17195 }

dpsRTUv2p16196Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 4 is set"
	::= { dpsRTUv2 16196 }

dpsRTUv2p17196Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 4 is cleared"
	::= { dpsRTUv2 17196 }

dpsRTUv2p16197Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 5 is set"
	::= { dpsRTUv2 16197 }

dpsRTUv2p17197Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 5 is cleared"
	::= { dpsRTUv2 17197 }

dpsRTUv2p16198Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 6 is set"
	::= { dpsRTUv2 16198 }

dpsRTUv2p17198Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 6 is cleared"
	::= { dpsRTUv2 17198 }

dpsRTUv2p16199Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 7 is set"
	::= { dpsRTUv2 16199 }

dpsRTUv2p17199Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 7 is cleared"
	::= { dpsRTUv2 17199 }

dpsRTUv2p16200Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 8 is set"
	::= { dpsRTUv2 16200 }

dpsRTUv2p17200Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 8 is cleared"
	::= { dpsRTUv2 17200 }

dpsRTUv2p16201Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 9 is set"
	::= { dpsRTUv2 16201 }

dpsRTUv2p17201Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 9 is cleared"
	::= { dpsRTUv2 17201 }

dpsRTUv2p16202Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 10 is set"
	::= { dpsRTUv2 16202 }

dpsRTUv2p17202Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 10 is cleared"
	::= { dpsRTUv2 17202 }

dpsRTUv2p16203Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 11 is set"
	::= { dpsRTUv2 16203 }

dpsRTUv2p17203Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 11 is cleared"
	::= { dpsRTUv2 17203 }

dpsRTUv2p16204Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 12 is set"
	::= { dpsRTUv2 16204 }

dpsRTUv2p17204Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 12 is cleared"
	::= { dpsRTUv2 17204 }

dpsRTUv2p16205Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 13 is set"
	::= { dpsRTUv2 16205 }

dpsRTUv2p17205Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 13 is cleared"
	::= { dpsRTUv2 17205 }

dpsRTUv2p16206Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 14 is set"
	::= { dpsRTUv2 16206 }

dpsRTUv2p17206Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 14 is cleared"
	::= { dpsRTUv2 17206 }

dpsRTUv2p16207Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 15 is set"
	::= { dpsRTUv2 16207 }

dpsRTUv2p17207Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 15 is cleared"
	::= { dpsRTUv2 17207 }

dpsRTUv2p16208Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 16 is set"
	::= { dpsRTUv2 16208 }

dpsRTUv2p17208Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 16 is cleared"
	::= { dpsRTUv2 17208 }

dpsRTUv2p16209Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 17 is set"
	::= { dpsRTUv2 16209 }

dpsRTUv2p17209Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 17 is cleared"
	::= { dpsRTUv2 17209 }

dpsRTUv2p16210Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 18 is set"
	::= { dpsRTUv2 16210 }

dpsRTUv2p17210Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 18 is cleared"
	::= { dpsRTUv2 17210 }

dpsRTUv2p16211Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 19 is set"
	::= { dpsRTUv2 16211 }

dpsRTUv2p17211Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 19 is cleared"
	::= { dpsRTUv2 17211 }

dpsRTUv2p16212Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 20 is set"
	::= { dpsRTUv2 16212 }

dpsRTUv2p17212Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 20 is cleared"
	::= { dpsRTUv2 17212 }

dpsRTUv2p16213Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 21 is set"
	::= { dpsRTUv2 16213 }

dpsRTUv2p17213Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 21 is cleared"
	::= { dpsRTUv2 17213 }

dpsRTUv2p16214Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 22 is set"
	::= { dpsRTUv2 16214 }

dpsRTUv2p17214Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 22 is cleared"
	::= { dpsRTUv2 17214 }

dpsRTUv2p16215Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 23 is set"
	::= { dpsRTUv2 16215 }

dpsRTUv2p17215Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 23 is cleared"
	::= { dpsRTUv2 17215 }

dpsRTUv2p16216Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 24 is set"
	::= { dpsRTUv2 16216 }

dpsRTUv2p17216Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 24 is cleared"
	::= { dpsRTUv2 17216 }

dpsRTUv2p16217Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 25 is set"
	::= { dpsRTUv2 16217 }

dpsRTUv2p17217Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 25 is cleared"
	::= { dpsRTUv2 17217 }

dpsRTUv2p16218Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 26 is set"
	::= { dpsRTUv2 16218 }

dpsRTUv2p17218Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 26 is cleared"
	::= { dpsRTUv2 17218 }

dpsRTUv2p16219Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 27 is set"
	::= { dpsRTUv2 16219 }

dpsRTUv2p17219Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 27 is cleared"
	::= { dpsRTUv2 17219 }

dpsRTUv2p16220Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 28 is set"
	::= { dpsRTUv2 16220 }

dpsRTUv2p17220Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 28 is cleared"
	::= { dpsRTUv2 17220 }

dpsRTUv2p16221Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 29 is set"
	::= { dpsRTUv2 16221 }

dpsRTUv2p17221Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 29 is cleared"
	::= { dpsRTUv2 17221 }

dpsRTUv2p16222Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 30 is set"
	::= { dpsRTUv2 16222 }

dpsRTUv2p17222Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 30 is cleared"
	::= { dpsRTUv2 17222 }

dpsRTUv2p16223Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 31 is set"
	::= { dpsRTUv2 16223 }

dpsRTUv2p17223Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 31 is cleared"
	::= { dpsRTUv2 17223 }

dpsRTUv2p16224Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 32 is set"
	::= { dpsRTUv2 16224 }

dpsRTUv2p17224Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 32 is cleared"
	::= { dpsRTUv2 17224 }

dpsRTUv2p16225Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 33 is set"
	::= { dpsRTUv2 16225 }

dpsRTUv2p17225Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 33 is cleared"
	::= { dpsRTUv2 17225 }

dpsRTUv2p16226Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 34 is set"
	::= { dpsRTUv2 16226 }

dpsRTUv2p17226Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 34 is cleared"
	::= { dpsRTUv2 17226 }

dpsRTUv2p16227Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 35 is set"
	::= { dpsRTUv2 16227 }

dpsRTUv2p17227Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 35 is cleared"
	::= { dpsRTUv2 17227 }

dpsRTUv2p16228Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 36 is set"
	::= { dpsRTUv2 16228 }

dpsRTUv2p17228Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 36 is cleared"
	::= { dpsRTUv2 17228 }

dpsRTUv2p16229Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 37 is set"
	::= { dpsRTUv2 16229 }

dpsRTUv2p17229Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 37 is cleared"
	::= { dpsRTUv2 17229 }

dpsRTUv2p16230Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 38 is set"
	::= { dpsRTUv2 16230 }

dpsRTUv2p17230Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 38 is cleared"
	::= { dpsRTUv2 17230 }

dpsRTUv2p16231Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 39 is set"
	::= { dpsRTUv2 16231 }

dpsRTUv2p17231Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 39 is cleared"
	::= { dpsRTUv2 17231 }

dpsRTUv2p16232Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 40 is set"
	::= { dpsRTUv2 16232 }

dpsRTUv2p17232Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 40 is cleared"
	::= { dpsRTUv2 17232 }

dpsRTUv2p16233Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 41 is set"
	::= { dpsRTUv2 16233 }

dpsRTUv2p17233Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 41 is cleared"
	::= { dpsRTUv2 17233 }

dpsRTUv2p16234Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 42 is set"
	::= { dpsRTUv2 16234 }

dpsRTUv2p17234Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 42 is cleared"
	::= { dpsRTUv2 17234 }

dpsRTUv2p16235Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 43 is set"
	::= { dpsRTUv2 16235 }

dpsRTUv2p17235Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 43 is cleared"
	::= { dpsRTUv2 17235 }

dpsRTUv2p16236Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 44 is set"
	::= { dpsRTUv2 16236 }

dpsRTUv2p17236Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 44 is cleared"
	::= { dpsRTUv2 17236 }

dpsRTUv2p16237Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 45 is set"
	::= { dpsRTUv2 16237 }

dpsRTUv2p17237Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 45 is cleared"
	::= { dpsRTUv2 17237 }

dpsRTUv2p16238Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 46 is set"
	::= { dpsRTUv2 16238 }

dpsRTUv2p17238Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 46 is cleared"
	::= { dpsRTUv2 17238 }

dpsRTUv2p16239Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 47 is set"
	::= { dpsRTUv2 16239 }

dpsRTUv2p17239Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 47 is cleared"
	::= { dpsRTUv2 17239 }

dpsRTUv2p16240Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 48 is set"
	::= { dpsRTUv2 16240 }

dpsRTUv2p17240Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 48 is cleared"
	::= { dpsRTUv2 17240 }

dpsRTUv2p16241Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 49 is set"
	::= { dpsRTUv2 16241 }

dpsRTUv2p17241Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 49 is cleared"
	::= { dpsRTUv2 17241 }

dpsRTUv2p16242Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 50 is set"
	::= { dpsRTUv2 16242 }

dpsRTUv2p17242Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 50 is cleared"
	::= { dpsRTUv2 17242 }

dpsRTUv2p16243Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 51 is set"
	::= { dpsRTUv2 16243 }

dpsRTUv2p17243Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 51 is cleared"
	::= { dpsRTUv2 17243 }

dpsRTUv2p16244Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 52 is set"
	::= { dpsRTUv2 16244 }

dpsRTUv2p17244Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 52 is cleared"
	::= { dpsRTUv2 17244 }

dpsRTUv2p16245Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 53 is set"
	::= { dpsRTUv2 16245 }

dpsRTUv2p17245Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 53 is cleared"
	::= { dpsRTUv2 17245 }

dpsRTUv2p16246Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 54 is set"
	::= { dpsRTUv2 16246 }

dpsRTUv2p17246Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 54 is cleared"
	::= { dpsRTUv2 17246 }

dpsRTUv2p16247Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 55 is set"
	::= { dpsRTUv2 16247 }

dpsRTUv2p17247Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 55 is cleared"
	::= { dpsRTUv2 17247 }

dpsRTUv2p16248Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 56 is set"
	::= { dpsRTUv2 16248 }

dpsRTUv2p17248Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 56 is cleared"
	::= { dpsRTUv2 17248 }

dpsRTUv2p16249Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 57 is set"
	::= { dpsRTUv2 16249 }

dpsRTUv2p17249Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 57 is cleared"
	::= { dpsRTUv2 17249 }

dpsRTUv2p16250Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 58 is set"
	::= { dpsRTUv2 16250 }

dpsRTUv2p17250Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 58 is cleared"
	::= { dpsRTUv2 17250 }

dpsRTUv2p16251Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 59 is set"
	::= { dpsRTUv2 16251 }

dpsRTUv2p17251Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 59 is cleared"
	::= { dpsRTUv2 17251 }

dpsRTUv2p16252Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 60 is set"
	::= { dpsRTUv2 16252 }

dpsRTUv2p17252Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 60 is cleared"
	::= { dpsRTUv2 17252 }

dpsRTUv2p16253Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 61 is set"
	::= { dpsRTUv2 16253 }

dpsRTUv2p17253Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 61 is cleared"
	::= { dpsRTUv2 17253 }

dpsRTUv2p16254Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 62 is set"
	::= { dpsRTUv2 16254 }

dpsRTUv2p17254Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 62 is cleared"
	::= { dpsRTUv2 17254 }

dpsRTUv2p16255Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 63 is set"
	::= { dpsRTUv2 16255 }

dpsRTUv2p17255Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 63 is cleared"
	::= { dpsRTUv2 17255 }

dpsRTUv2p16256Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 64 is set"
	::= { dpsRTUv2 16256 }

dpsRTUv2p17256Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 4 point 64 is cleared"
	::= { dpsRTUv2 17256 }

dpsRTUv2p16257Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 1 is set"
	::= { dpsRTUv2 16257 }

dpsRTUv2p17257Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 1 is cleared"
	::= { dpsRTUv2 17257 }

dpsRTUv2p16258Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 2 is set"
	::= { dpsRTUv2 16258 }

dpsRTUv2p17258Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 2 is cleared"
	::= { dpsRTUv2 17258 }

dpsRTUv2p16259Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 3 is set"
	::= { dpsRTUv2 16259 }

dpsRTUv2p17259Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 3 is cleared"
	::= { dpsRTUv2 17259 }

dpsRTUv2p16260Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 4 is set"
	::= { dpsRTUv2 16260 }

dpsRTUv2p17260Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 4 is cleared"
	::= { dpsRTUv2 17260 }

dpsRTUv2p16261Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 5 is set"
	::= { dpsRTUv2 16261 }

dpsRTUv2p17261Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 5 is cleared"
	::= { dpsRTUv2 17261 }

dpsRTUv2p16262Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 6 is set"
	::= { dpsRTUv2 16262 }

dpsRTUv2p17262Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 6 is cleared"
	::= { dpsRTUv2 17262 }

dpsRTUv2p16263Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 7 is set"
	::= { dpsRTUv2 16263 }

dpsRTUv2p17263Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 7 is cleared"
	::= { dpsRTUv2 17263 }

dpsRTUv2p16264Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 8 is set"
	::= { dpsRTUv2 16264 }

dpsRTUv2p17264Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 8 is cleared"
	::= { dpsRTUv2 17264 }

dpsRTUv2p16265Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 9 is set"
	::= { dpsRTUv2 16265 }

dpsRTUv2p17265Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 9 is cleared"
	::= { dpsRTUv2 17265 }

dpsRTUv2p16266Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 10 is set"
	::= { dpsRTUv2 16266 }

dpsRTUv2p17266Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 10 is cleared"
	::= { dpsRTUv2 17266 }

dpsRTUv2p16267Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 11 is set"
	::= { dpsRTUv2 16267 }

dpsRTUv2p17267Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 11 is cleared"
	::= { dpsRTUv2 17267 }

dpsRTUv2p16268Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 12 is set"
	::= { dpsRTUv2 16268 }

dpsRTUv2p17268Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 12 is cleared"
	::= { dpsRTUv2 17268 }

dpsRTUv2p16269Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 13 is set"
	::= { dpsRTUv2 16269 }

dpsRTUv2p17269Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 13 is cleared"
	::= { dpsRTUv2 17269 }

dpsRTUv2p16270Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 14 is set"
	::= { dpsRTUv2 16270 }

dpsRTUv2p17270Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 14 is cleared"
	::= { dpsRTUv2 17270 }

dpsRTUv2p16271Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 15 is set"
	::= { dpsRTUv2 16271 }

dpsRTUv2p17271Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 15 is cleared"
	::= { dpsRTUv2 17271 }

dpsRTUv2p16272Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 16 is set"
	::= { dpsRTUv2 16272 }

dpsRTUv2p17272Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 16 is cleared"
	::= { dpsRTUv2 17272 }

dpsRTUv2p16273Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 17 is set"
	::= { dpsRTUv2 16273 }

dpsRTUv2p17273Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 17 is cleared"
	::= { dpsRTUv2 17273 }

dpsRTUv2p16274Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 18 is set"
	::= { dpsRTUv2 16274 }

dpsRTUv2p17274Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 18 is cleared"
	::= { dpsRTUv2 17274 }

dpsRTUv2p16275Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 19 is set"
	::= { dpsRTUv2 16275 }

dpsRTUv2p17275Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 19 is cleared"
	::= { dpsRTUv2 17275 }

dpsRTUv2p16276Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 20 is set"
	::= { dpsRTUv2 16276 }

dpsRTUv2p17276Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 20 is cleared"
	::= { dpsRTUv2 17276 }

dpsRTUv2p16277Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 21 is set"
	::= { dpsRTUv2 16277 }

dpsRTUv2p17277Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 21 is cleared"
	::= { dpsRTUv2 17277 }

dpsRTUv2p16278Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 22 is set"
	::= { dpsRTUv2 16278 }

dpsRTUv2p17278Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 22 is cleared"
	::= { dpsRTUv2 17278 }

dpsRTUv2p16279Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 23 is set"
	::= { dpsRTUv2 16279 }

dpsRTUv2p17279Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 23 is cleared"
	::= { dpsRTUv2 17279 }

dpsRTUv2p16280Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 24 is set"
	::= { dpsRTUv2 16280 }

dpsRTUv2p17280Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 24 is cleared"
	::= { dpsRTUv2 17280 }

dpsRTUv2p16281Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 25 is set"
	::= { dpsRTUv2 16281 }

dpsRTUv2p17281Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 25 is cleared"
	::= { dpsRTUv2 17281 }

dpsRTUv2p16282Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 26 is set"
	::= { dpsRTUv2 16282 }

dpsRTUv2p17282Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 26 is cleared"
	::= { dpsRTUv2 17282 }

dpsRTUv2p16283Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 27 is set"
	::= { dpsRTUv2 16283 }

dpsRTUv2p17283Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 27 is cleared"
	::= { dpsRTUv2 17283 }

dpsRTUv2p16284Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 28 is set"
	::= { dpsRTUv2 16284 }

dpsRTUv2p17284Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 28 is cleared"
	::= { dpsRTUv2 17284 }

dpsRTUv2p16285Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 29 is set"
	::= { dpsRTUv2 16285 }

dpsRTUv2p17285Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 29 is cleared"
	::= { dpsRTUv2 17285 }

dpsRTUv2p16286Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 30 is set"
	::= { dpsRTUv2 16286 }

dpsRTUv2p17286Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 30 is cleared"
	::= { dpsRTUv2 17286 }

dpsRTUv2p16287Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 31 is set"
	::= { dpsRTUv2 16287 }

dpsRTUv2p17287Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 31 is cleared"
	::= { dpsRTUv2 17287 }

dpsRTUv2p16288Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 32 is set"
	::= { dpsRTUv2 16288 }

dpsRTUv2p17288Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 32 is cleared"
	::= { dpsRTUv2 17288 }

dpsRTUv2p16289Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 33 is set"
	::= { dpsRTUv2 16289 }

dpsRTUv2p17289Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 33 is cleared"
	::= { dpsRTUv2 17289 }

dpsRTUv2p16290Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 34 is set"
	::= { dpsRTUv2 16290 }

dpsRTUv2p17290Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 34 is cleared"
	::= { dpsRTUv2 17290 }

dpsRTUv2p16291Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 35 is set"
	::= { dpsRTUv2 16291 }

dpsRTUv2p17291Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 35 is cleared"
	::= { dpsRTUv2 17291 }

dpsRTUv2p16292Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 36 is set"
	::= { dpsRTUv2 16292 }

dpsRTUv2p17292Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 36 is cleared"
	::= { dpsRTUv2 17292 }

dpsRTUv2p16293Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 37 is set"
	::= { dpsRTUv2 16293 }

dpsRTUv2p17293Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 37 is cleared"
	::= { dpsRTUv2 17293 }

dpsRTUv2p16294Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 38 is set"
	::= { dpsRTUv2 16294 }

dpsRTUv2p17294Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 38 is cleared"
	::= { dpsRTUv2 17294 }

dpsRTUv2p16295Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 39 is set"
	::= { dpsRTUv2 16295 }

dpsRTUv2p17295Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 39 is cleared"
	::= { dpsRTUv2 17295 }

dpsRTUv2p16296Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 40 is set"
	::= { dpsRTUv2 16296 }

dpsRTUv2p17296Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 40 is cleared"
	::= { dpsRTUv2 17296 }

dpsRTUv2p16297Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 41 is set"
	::= { dpsRTUv2 16297 }

dpsRTUv2p17297Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 41 is cleared"
	::= { dpsRTUv2 17297 }

dpsRTUv2p16298Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 42 is set"
	::= { dpsRTUv2 16298 }

dpsRTUv2p17298Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 42 is cleared"
	::= { dpsRTUv2 17298 }

dpsRTUv2p16299Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 43 is set"
	::= { dpsRTUv2 16299 }

dpsRTUv2p17299Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 43 is cleared"
	::= { dpsRTUv2 17299 }

dpsRTUv2p16300Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 44 is set"
	::= { dpsRTUv2 16300 }

dpsRTUv2p17300Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 44 is cleared"
	::= { dpsRTUv2 17300 }

dpsRTUv2p16301Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 45 is set"
	::= { dpsRTUv2 16301 }

dpsRTUv2p17301Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 45 is cleared"
	::= { dpsRTUv2 17301 }

dpsRTUv2p16302Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 46 is set"
	::= { dpsRTUv2 16302 }

dpsRTUv2p17302Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 46 is cleared"
	::= { dpsRTUv2 17302 }

dpsRTUv2p16303Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 47 is set"
	::= { dpsRTUv2 16303 }

dpsRTUv2p17303Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 47 is cleared"
	::= { dpsRTUv2 17303 }

dpsRTUv2p16304Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 48 is set"
	::= { dpsRTUv2 16304 }

dpsRTUv2p17304Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 48 is cleared"
	::= { dpsRTUv2 17304 }

dpsRTUv2p16305Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 49 is set"
	::= { dpsRTUv2 16305 }

dpsRTUv2p17305Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 49 is cleared"
	::= { dpsRTUv2 17305 }

dpsRTUv2p16306Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 50 is set"
	::= { dpsRTUv2 16306 }

dpsRTUv2p17306Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 50 is cleared"
	::= { dpsRTUv2 17306 }

dpsRTUv2p16307Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 51 is set"
	::= { dpsRTUv2 16307 }

dpsRTUv2p17307Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 51 is cleared"
	::= { dpsRTUv2 17307 }

dpsRTUv2p16308Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 52 is set"
	::= { dpsRTUv2 16308 }

dpsRTUv2p17308Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 52 is cleared"
	::= { dpsRTUv2 17308 }

dpsRTUv2p16309Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 53 is set"
	::= { dpsRTUv2 16309 }

dpsRTUv2p17309Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 53 is cleared"
	::= { dpsRTUv2 17309 }

dpsRTUv2p16310Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 54 is set"
	::= { dpsRTUv2 16310 }

dpsRTUv2p17310Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 54 is cleared"
	::= { dpsRTUv2 17310 }

dpsRTUv2p16311Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 55 is set"
	::= { dpsRTUv2 16311 }

dpsRTUv2p17311Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 55 is cleared"
	::= { dpsRTUv2 17311 }

dpsRTUv2p16312Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 56 is set"
	::= { dpsRTUv2 16312 }

dpsRTUv2p17312Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 56 is cleared"
	::= { dpsRTUv2 17312 }

dpsRTUv2p16313Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 57 is set"
	::= { dpsRTUv2 16313 }

dpsRTUv2p17313Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 57 is cleared"
	::= { dpsRTUv2 17313 }

dpsRTUv2p16314Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 58 is set"
	::= { dpsRTUv2 16314 }

dpsRTUv2p17314Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 58 is cleared"
	::= { dpsRTUv2 17314 }

dpsRTUv2p16315Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 59 is set"
	::= { dpsRTUv2 16315 }

dpsRTUv2p17315Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 59 is cleared"
	::= { dpsRTUv2 17315 }

dpsRTUv2p16316Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 60 is set"
	::= { dpsRTUv2 16316 }

dpsRTUv2p17316Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 60 is cleared"
	::= { dpsRTUv2 17316 }

dpsRTUv2p16317Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 61 is set"
	::= { dpsRTUv2 16317 }

dpsRTUv2p17317Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 61 is cleared"
	::= { dpsRTUv2 17317 }

dpsRTUv2p16318Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 62 is set"
	::= { dpsRTUv2 16318 }

dpsRTUv2p17318Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 62 is cleared"
	::= { dpsRTUv2 17318 }

dpsRTUv2p16319Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 63 is set"
	::= { dpsRTUv2 16319 }

dpsRTUv2p17319Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 63 is cleared"
	::= { dpsRTUv2 17319 }

dpsRTUv2p16320Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 64 is set"
	::= { dpsRTUv2 16320 }

dpsRTUv2p17320Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 5 point 64 is cleared"
	::= { dpsRTUv2 17320 }

dpsRTUv2p16321Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 1 is set"
	::= { dpsRTUv2 16321 }

dpsRTUv2p17321Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 1 is cleared"
	::= { dpsRTUv2 17321 }

dpsRTUv2p16322Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 2 is set"
	::= { dpsRTUv2 16322 }

dpsRTUv2p17322Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 2 is cleared"
	::= { dpsRTUv2 17322 }

dpsRTUv2p16323Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 3 is set"
	::= { dpsRTUv2 16323 }

dpsRTUv2p17323Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 3 is cleared"
	::= { dpsRTUv2 17323 }

dpsRTUv2p16324Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 4 is set"
	::= { dpsRTUv2 16324 }

dpsRTUv2p17324Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 4 is cleared"
	::= { dpsRTUv2 17324 }

dpsRTUv2p16325Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 5 is set"
	::= { dpsRTUv2 16325 }

dpsRTUv2p17325Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 5 is cleared"
	::= { dpsRTUv2 17325 }

dpsRTUv2p16326Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 6 is set"
	::= { dpsRTUv2 16326 }

dpsRTUv2p17326Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 6 is cleared"
	::= { dpsRTUv2 17326 }

dpsRTUv2p16327Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 7 is set"
	::= { dpsRTUv2 16327 }

dpsRTUv2p17327Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 7 is cleared"
	::= { dpsRTUv2 17327 }

dpsRTUv2p16328Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 8 is set"
	::= { dpsRTUv2 16328 }

dpsRTUv2p17328Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 8 is cleared"
	::= { dpsRTUv2 17328 }

dpsRTUv2p16329Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 9 is set"
	::= { dpsRTUv2 16329 }

dpsRTUv2p17329Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 9 is cleared"
	::= { dpsRTUv2 17329 }

dpsRTUv2p16330Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 10 is set"
	::= { dpsRTUv2 16330 }

dpsRTUv2p17330Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 10 is cleared"
	::= { dpsRTUv2 17330 }

dpsRTUv2p16331Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 11 is set"
	::= { dpsRTUv2 16331 }

dpsRTUv2p17331Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 11 is cleared"
	::= { dpsRTUv2 17331 }

dpsRTUv2p16332Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 12 is set"
	::= { dpsRTUv2 16332 }

dpsRTUv2p17332Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 12 is cleared"
	::= { dpsRTUv2 17332 }

dpsRTUv2p16333Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 13 is set"
	::= { dpsRTUv2 16333 }

dpsRTUv2p17333Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 13 is cleared"
	::= { dpsRTUv2 17333 }

dpsRTUv2p16334Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 14 is set"
	::= { dpsRTUv2 16334 }

dpsRTUv2p17334Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 14 is cleared"
	::= { dpsRTUv2 17334 }

dpsRTUv2p16335Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 15 is set"
	::= { dpsRTUv2 16335 }

dpsRTUv2p17335Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 15 is cleared"
	::= { dpsRTUv2 17335 }

dpsRTUv2p16336Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 16 is set"
	::= { dpsRTUv2 16336 }

dpsRTUv2p17336Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 16 is cleared"
	::= { dpsRTUv2 17336 }

dpsRTUv2p16337Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 17 is set"
	::= { dpsRTUv2 16337 }

dpsRTUv2p17337Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 17 is cleared"
	::= { dpsRTUv2 17337 }

dpsRTUv2p16338Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 18 is set"
	::= { dpsRTUv2 16338 }

dpsRTUv2p17338Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 18 is cleared"
	::= { dpsRTUv2 17338 }

dpsRTUv2p16339Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 19 is set"
	::= { dpsRTUv2 16339 }

dpsRTUv2p17339Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 19 is cleared"
	::= { dpsRTUv2 17339 }

dpsRTUv2p16340Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 20 is set"
	::= { dpsRTUv2 16340 }

dpsRTUv2p17340Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 20 is cleared"
	::= { dpsRTUv2 17340 }

dpsRTUv2p16341Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 21 is set"
	::= { dpsRTUv2 16341 }

dpsRTUv2p17341Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 21 is cleared"
	::= { dpsRTUv2 17341 }

dpsRTUv2p16342Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 22 is set"
	::= { dpsRTUv2 16342 }

dpsRTUv2p17342Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 22 is cleared"
	::= { dpsRTUv2 17342 }

dpsRTUv2p16343Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 23 is set"
	::= { dpsRTUv2 16343 }

dpsRTUv2p17343Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 23 is cleared"
	::= { dpsRTUv2 17343 }

dpsRTUv2p16344Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 24 is set"
	::= { dpsRTUv2 16344 }

dpsRTUv2p17344Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 24 is cleared"
	::= { dpsRTUv2 17344 }

dpsRTUv2p16345Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 25 is set"
	::= { dpsRTUv2 16345 }

dpsRTUv2p17345Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 25 is cleared"
	::= { dpsRTUv2 17345 }

dpsRTUv2p16346Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 26 is set"
	::= { dpsRTUv2 16346 }

dpsRTUv2p17346Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 26 is cleared"
	::= { dpsRTUv2 17346 }

dpsRTUv2p16347Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 27 is set"
	::= { dpsRTUv2 16347 }

dpsRTUv2p17347Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 27 is cleared"
	::= { dpsRTUv2 17347 }

dpsRTUv2p16348Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 28 is set"
	::= { dpsRTUv2 16348 }

dpsRTUv2p17348Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 28 is cleared"
	::= { dpsRTUv2 17348 }

dpsRTUv2p16349Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 29 is set"
	::= { dpsRTUv2 16349 }

dpsRTUv2p17349Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 29 is cleared"
	::= { dpsRTUv2 17349 }

dpsRTUv2p16350Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 30 is set"
	::= { dpsRTUv2 16350 }

dpsRTUv2p17350Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 30 is cleared"
	::= { dpsRTUv2 17350 }

dpsRTUv2p16351Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 31 is set"
	::= { dpsRTUv2 16351 }

dpsRTUv2p17351Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 31 is cleared"
	::= { dpsRTUv2 17351 }

dpsRTUv2p16352Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 32 is set"
	::= { dpsRTUv2 16352 }

dpsRTUv2p17352Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 32 is cleared"
	::= { dpsRTUv2 17352 }

dpsRTUv2p16353Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 33 is set"
	::= { dpsRTUv2 16353 }

dpsRTUv2p17353Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 33 is cleared"
	::= { dpsRTUv2 17353 }

dpsRTUv2p16354Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 34 is set"
	::= { dpsRTUv2 16354 }

dpsRTUv2p17354Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 34 is cleared"
	::= { dpsRTUv2 17354 }

dpsRTUv2p16355Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 35 is set"
	::= { dpsRTUv2 16355 }

dpsRTUv2p17355Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 35 is cleared"
	::= { dpsRTUv2 17355 }

dpsRTUv2p16356Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 36 is set"
	::= { dpsRTUv2 16356 }

dpsRTUv2p17356Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 36 is cleared"
	::= { dpsRTUv2 17356 }

dpsRTUv2p16357Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 37 is set"
	::= { dpsRTUv2 16357 }

dpsRTUv2p17357Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 37 is cleared"
	::= { dpsRTUv2 17357 }

dpsRTUv2p16358Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 38 is set"
	::= { dpsRTUv2 16358 }

dpsRTUv2p17358Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 38 is cleared"
	::= { dpsRTUv2 17358 }

dpsRTUv2p16359Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 39 is set"
	::= { dpsRTUv2 16359 }

dpsRTUv2p17359Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 39 is cleared"
	::= { dpsRTUv2 17359 }

dpsRTUv2p16360Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 40 is set"
	::= { dpsRTUv2 16360 }

dpsRTUv2p17360Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 40 is cleared"
	::= { dpsRTUv2 17360 }

dpsRTUv2p16361Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 41 is set"
	::= { dpsRTUv2 16361 }

dpsRTUv2p17361Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 41 is cleared"
	::= { dpsRTUv2 17361 }

dpsRTUv2p16362Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 42 is set"
	::= { dpsRTUv2 16362 }

dpsRTUv2p17362Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 42 is cleared"
	::= { dpsRTUv2 17362 }

dpsRTUv2p16363Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 43 is set"
	::= { dpsRTUv2 16363 }

dpsRTUv2p17363Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 43 is cleared"
	::= { dpsRTUv2 17363 }

dpsRTUv2p16364Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 44 is set"
	::= { dpsRTUv2 16364 }

dpsRTUv2p17364Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 44 is cleared"
	::= { dpsRTUv2 17364 }

dpsRTUv2p16365Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 45 is set"
	::= { dpsRTUv2 16365 }

dpsRTUv2p17365Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 45 is cleared"
	::= { dpsRTUv2 17365 }

dpsRTUv2p16366Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 46 is set"
	::= { dpsRTUv2 16366 }

dpsRTUv2p17366Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 46 is cleared"
	::= { dpsRTUv2 17366 }

dpsRTUv2p16367Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 47 is set"
	::= { dpsRTUv2 16367 }

dpsRTUv2p17367Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 47 is cleared"
	::= { dpsRTUv2 17367 }

dpsRTUv2p16368Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 48 is set"
	::= { dpsRTUv2 16368 }

dpsRTUv2p17368Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 48 is cleared"
	::= { dpsRTUv2 17368 }

dpsRTUv2p16369Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 49 is set"
	::= { dpsRTUv2 16369 }

dpsRTUv2p17369Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 49 is cleared"
	::= { dpsRTUv2 17369 }

dpsRTUv2p16370Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 50 is set"
	::= { dpsRTUv2 16370 }

dpsRTUv2p17370Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 50 is cleared"
	::= { dpsRTUv2 17370 }

dpsRTUv2p16371Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 51 is set"
	::= { dpsRTUv2 16371 }

dpsRTUv2p17371Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 51 is cleared"
	::= { dpsRTUv2 17371 }

dpsRTUv2p16372Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 52 is set"
	::= { dpsRTUv2 16372 }

dpsRTUv2p17372Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 52 is cleared"
	::= { dpsRTUv2 17372 }

dpsRTUv2p16373Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 53 is set"
	::= { dpsRTUv2 16373 }

dpsRTUv2p17373Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 53 is cleared"
	::= { dpsRTUv2 17373 }

dpsRTUv2p16374Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 54 is set"
	::= { dpsRTUv2 16374 }

dpsRTUv2p17374Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 54 is cleared"
	::= { dpsRTUv2 17374 }

dpsRTUv2p16375Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 55 is set"
	::= { dpsRTUv2 16375 }

dpsRTUv2p17375Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 55 is cleared"
	::= { dpsRTUv2 17375 }

dpsRTUv2p16376Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 56 is set"
	::= { dpsRTUv2 16376 }

dpsRTUv2p17376Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 56 is cleared"
	::= { dpsRTUv2 17376 }

dpsRTUv2p16377Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 57 is set"
	::= { dpsRTUv2 16377 }

dpsRTUv2p17377Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 57 is cleared"
	::= { dpsRTUv2 17377 }

dpsRTUv2p16378Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 58 is set"
	::= { dpsRTUv2 16378 }

dpsRTUv2p17378Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 58 is cleared"
	::= { dpsRTUv2 17378 }

dpsRTUv2p16379Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 59 is set"
	::= { dpsRTUv2 16379 }

dpsRTUv2p17379Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 59 is cleared"
	::= { dpsRTUv2 17379 }

dpsRTUv2p16380Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 60 is set"
	::= { dpsRTUv2 16380 }

dpsRTUv2p17380Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 60 is cleared"
	::= { dpsRTUv2 17380 }

dpsRTUv2p16381Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 61 is set"
	::= { dpsRTUv2 16381 }

dpsRTUv2p17381Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 61 is cleared"
	::= { dpsRTUv2 17381 }

dpsRTUv2p16382Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 62 is set"
	::= { dpsRTUv2 16382 }

dpsRTUv2p17382Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 62 is cleared"
	::= { dpsRTUv2 17382 }

dpsRTUv2p16383Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 63 is set"
	::= { dpsRTUv2 16383 }

dpsRTUv2p17383Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 63 is cleared"
	::= { dpsRTUv2 17383 }

dpsRTUv2p16384Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 64 is set"
	::= { dpsRTUv2 16384 }

dpsRTUv2p17384Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 6 point 64 is cleared"
	::= { dpsRTUv2 17384 }

dpsRTUv2p16385Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 1 is set"
	::= { dpsRTUv2 16385 }

dpsRTUv2p17385Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 1 is cleared"
	::= { dpsRTUv2 17385 }

dpsRTUv2p16386Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 2 is set"
	::= { dpsRTUv2 16386 }

dpsRTUv2p17386Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 2 is cleared"
	::= { dpsRTUv2 17386 }

dpsRTUv2p16387Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 3 is set"
	::= { dpsRTUv2 16387 }

dpsRTUv2p17387Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 3 is cleared"
	::= { dpsRTUv2 17387 }

dpsRTUv2p16388Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 4 is set"
	::= { dpsRTUv2 16388 }

dpsRTUv2p17388Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 4 is cleared"
	::= { dpsRTUv2 17388 }

dpsRTUv2p16389Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 5 is set"
	::= { dpsRTUv2 16389 }

dpsRTUv2p17389Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 5 is cleared"
	::= { dpsRTUv2 17389 }

dpsRTUv2p16390Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 6 is set"
	::= { dpsRTUv2 16390 }

dpsRTUv2p17390Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 6 is cleared"
	::= { dpsRTUv2 17390 }

dpsRTUv2p16391Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 7 is set"
	::= { dpsRTUv2 16391 }

dpsRTUv2p17391Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 7 is cleared"
	::= { dpsRTUv2 17391 }

dpsRTUv2p16392Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 8 is set"
	::= { dpsRTUv2 16392 }

dpsRTUv2p17392Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 8 is cleared"
	::= { dpsRTUv2 17392 }

dpsRTUv2p16393Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 9 is set"
	::= { dpsRTUv2 16393 }

dpsRTUv2p17393Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 9 is cleared"
	::= { dpsRTUv2 17393 }

dpsRTUv2p16394Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 10 is set"
	::= { dpsRTUv2 16394 }

dpsRTUv2p17394Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 10 is cleared"
	::= { dpsRTUv2 17394 }

dpsRTUv2p16395Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 11 is set"
	::= { dpsRTUv2 16395 }

dpsRTUv2p17395Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 11 is cleared"
	::= { dpsRTUv2 17395 }

dpsRTUv2p16396Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 12 is set"
	::= { dpsRTUv2 16396 }

dpsRTUv2p17396Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 12 is cleared"
	::= { dpsRTUv2 17396 }

dpsRTUv2p16397Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 13 is set"
	::= { dpsRTUv2 16397 }

dpsRTUv2p17397Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 13 is cleared"
	::= { dpsRTUv2 17397 }

dpsRTUv2p16398Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 14 is set"
	::= { dpsRTUv2 16398 }

dpsRTUv2p17398Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 14 is cleared"
	::= { dpsRTUv2 17398 }

dpsRTUv2p16399Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 15 is set"
	::= { dpsRTUv2 16399 }

dpsRTUv2p17399Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 15 is cleared"
	::= { dpsRTUv2 17399 }

dpsRTUv2p16400Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 16 is set"
	::= { dpsRTUv2 16400 }

dpsRTUv2p17400Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 16 is cleared"
	::= { dpsRTUv2 17400 }

dpsRTUv2p16401Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 17 is set"
	::= { dpsRTUv2 16401 }

dpsRTUv2p17401Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 17 is cleared"
	::= { dpsRTUv2 17401 }

dpsRTUv2p16402Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 18 is set"
	::= { dpsRTUv2 16402 }

dpsRTUv2p17402Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 18 is cleared"
	::= { dpsRTUv2 17402 }

dpsRTUv2p16403Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 19 is set"
	::= { dpsRTUv2 16403 }

dpsRTUv2p17403Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 19 is cleared"
	::= { dpsRTUv2 17403 }

dpsRTUv2p16404Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 20 is set"
	::= { dpsRTUv2 16404 }

dpsRTUv2p17404Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 20 is cleared"
	::= { dpsRTUv2 17404 }

dpsRTUv2p16405Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 21 is set"
	::= { dpsRTUv2 16405 }

dpsRTUv2p17405Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 21 is cleared"
	::= { dpsRTUv2 17405 }

dpsRTUv2p16406Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 22 is set"
	::= { dpsRTUv2 16406 }

dpsRTUv2p17406Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 22 is cleared"
	::= { dpsRTUv2 17406 }

dpsRTUv2p16407Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 23 is set"
	::= { dpsRTUv2 16407 }

dpsRTUv2p17407Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 23 is cleared"
	::= { dpsRTUv2 17407 }

dpsRTUv2p16408Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 24 is set"
	::= { dpsRTUv2 16408 }

dpsRTUv2p17408Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 24 is cleared"
	::= { dpsRTUv2 17408 }

dpsRTUv2p16409Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 25 is set"
	::= { dpsRTUv2 16409 }

dpsRTUv2p17409Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 25 is cleared"
	::= { dpsRTUv2 17409 }

dpsRTUv2p16410Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 26 is set"
	::= { dpsRTUv2 16410 }

dpsRTUv2p17410Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 26 is cleared"
	::= { dpsRTUv2 17410 }

dpsRTUv2p16411Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 27 is set"
	::= { dpsRTUv2 16411 }

dpsRTUv2p17411Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 27 is cleared"
	::= { dpsRTUv2 17411 }

dpsRTUv2p16412Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 28 is set"
	::= { dpsRTUv2 16412 }

dpsRTUv2p17412Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 28 is cleared"
	::= { dpsRTUv2 17412 }

dpsRTUv2p16413Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 29 is set"
	::= { dpsRTUv2 16413 }

dpsRTUv2p17413Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 29 is cleared"
	::= { dpsRTUv2 17413 }

dpsRTUv2p16414Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 30 is set"
	::= { dpsRTUv2 16414 }

dpsRTUv2p17414Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 30 is cleared"
	::= { dpsRTUv2 17414 }

dpsRTUv2p16415Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 31 is set"
	::= { dpsRTUv2 16415 }

dpsRTUv2p17415Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 31 is cleared"
	::= { dpsRTUv2 17415 }

dpsRTUv2p16416Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 32 is set"
	::= { dpsRTUv2 16416 }

dpsRTUv2p17416Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 32 is cleared"
	::= { dpsRTUv2 17416 }

dpsRTUv2p16417Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 33 is set"
	::= { dpsRTUv2 16417 }

dpsRTUv2p17417Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 33 is cleared"
	::= { dpsRTUv2 17417 }

dpsRTUv2p16418Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 34 is set"
	::= { dpsRTUv2 16418 }

dpsRTUv2p17418Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 34 is cleared"
	::= { dpsRTUv2 17418 }

dpsRTUv2p16419Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 35 is set"
	::= { dpsRTUv2 16419 }

dpsRTUv2p17419Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 35 is cleared"
	::= { dpsRTUv2 17419 }

dpsRTUv2p16420Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 36 is set"
	::= { dpsRTUv2 16420 }

dpsRTUv2p17420Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 36 is cleared"
	::= { dpsRTUv2 17420 }

dpsRTUv2p16421Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 37 is set"
	::= { dpsRTUv2 16421 }

dpsRTUv2p17421Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 37 is cleared"
	::= { dpsRTUv2 17421 }

dpsRTUv2p16422Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 38 is set"
	::= { dpsRTUv2 16422 }

dpsRTUv2p17422Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 38 is cleared"
	::= { dpsRTUv2 17422 }

dpsRTUv2p16423Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 39 is set"
	::= { dpsRTUv2 16423 }

dpsRTUv2p17423Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 39 is cleared"
	::= { dpsRTUv2 17423 }

dpsRTUv2p16424Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 40 is set"
	::= { dpsRTUv2 16424 }

dpsRTUv2p17424Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 40 is cleared"
	::= { dpsRTUv2 17424 }

dpsRTUv2p16425Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 41 is set"
	::= { dpsRTUv2 16425 }

dpsRTUv2p17425Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 41 is cleared"
	::= { dpsRTUv2 17425 }

dpsRTUv2p16426Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 42 is set"
	::= { dpsRTUv2 16426 }

dpsRTUv2p17426Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 42 is cleared"
	::= { dpsRTUv2 17426 }

dpsRTUv2p16427Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 43 is set"
	::= { dpsRTUv2 16427 }

dpsRTUv2p17427Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 43 is cleared"
	::= { dpsRTUv2 17427 }

dpsRTUv2p16428Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 44 is set"
	::= { dpsRTUv2 16428 }

dpsRTUv2p17428Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 44 is cleared"
	::= { dpsRTUv2 17428 }

dpsRTUv2p16429Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 45 is set"
	::= { dpsRTUv2 16429 }

dpsRTUv2p17429Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 45 is cleared"
	::= { dpsRTUv2 17429 }

dpsRTUv2p16430Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 46 is set"
	::= { dpsRTUv2 16430 }

dpsRTUv2p17430Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 46 is cleared"
	::= { dpsRTUv2 17430 }

dpsRTUv2p16431Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 47 is set"
	::= { dpsRTUv2 16431 }

dpsRTUv2p17431Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 47 is cleared"
	::= { dpsRTUv2 17431 }

dpsRTUv2p16432Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 48 is set"
	::= { dpsRTUv2 16432 }

dpsRTUv2p17432Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 48 is cleared"
	::= { dpsRTUv2 17432 }

dpsRTUv2p16433Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 49 is set"
	::= { dpsRTUv2 16433 }

dpsRTUv2p17433Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 49 is cleared"
	::= { dpsRTUv2 17433 }

dpsRTUv2p16434Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 50 is set"
	::= { dpsRTUv2 16434 }

dpsRTUv2p17434Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 50 is cleared"
	::= { dpsRTUv2 17434 }

dpsRTUv2p16435Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 51 is set"
	::= { dpsRTUv2 16435 }

dpsRTUv2p17435Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 51 is cleared"
	::= { dpsRTUv2 17435 }

dpsRTUv2p16436Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 52 is set"
	::= { dpsRTUv2 16436 }

dpsRTUv2p17436Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 52 is cleared"
	::= { dpsRTUv2 17436 }

dpsRTUv2p16437Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 53 is set"
	::= { dpsRTUv2 16437 }

dpsRTUv2p17437Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 53 is cleared"
	::= { dpsRTUv2 17437 }

dpsRTUv2p16438Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 54 is set"
	::= { dpsRTUv2 16438 }

dpsRTUv2p17438Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 54 is cleared"
	::= { dpsRTUv2 17438 }

dpsRTUv2p16439Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 55 is set"
	::= { dpsRTUv2 16439 }

dpsRTUv2p17439Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 55 is cleared"
	::= { dpsRTUv2 17439 }

dpsRTUv2p16440Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 56 is set"
	::= { dpsRTUv2 16440 }

dpsRTUv2p17440Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 56 is cleared"
	::= { dpsRTUv2 17440 }

dpsRTUv2p16441Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 57 is set"
	::= { dpsRTUv2 16441 }

dpsRTUv2p17441Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 57 is cleared"
	::= { dpsRTUv2 17441 }

dpsRTUv2p16442Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 58 is set"
	::= { dpsRTUv2 16442 }

dpsRTUv2p17442Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 58 is cleared"
	::= { dpsRTUv2 17442 }

dpsRTUv2p16443Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 59 is set"
	::= { dpsRTUv2 16443 }

dpsRTUv2p17443Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 59 is cleared"
	::= { dpsRTUv2 17443 }

dpsRTUv2p16444Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 60 is set"
	::= { dpsRTUv2 16444 }

dpsRTUv2p17444Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 60 is cleared"
	::= { dpsRTUv2 17444 }

dpsRTUv2p16445Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 61 is set"
	::= { dpsRTUv2 16445 }

dpsRTUv2p17445Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 61 is cleared"
	::= { dpsRTUv2 17445 }

dpsRTUv2p16446Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 62 is set"
	::= { dpsRTUv2 16446 }

dpsRTUv2p17446Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 62 is cleared"
	::= { dpsRTUv2 17446 }

dpsRTUv2p16447Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 63 is set"
	::= { dpsRTUv2 16447 }

dpsRTUv2p17447Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 63 is cleared"
	::= { dpsRTUv2 17447 }

dpsRTUv2p16448Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 64 is set"
	::= { dpsRTUv2 16448 }

dpsRTUv2p17448Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 7 point 64 is cleared"
	::= { dpsRTUv2 17448 }

dpsRTUv2p16449Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 1 is set"
	::= { dpsRTUv2 16449 }

dpsRTUv2p17449Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 1 is cleared"
	::= { dpsRTUv2 17449 }

dpsRTUv2p16450Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 2 is set"
	::= { dpsRTUv2 16450 }

dpsRTUv2p17450Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 2 is cleared"
	::= { dpsRTUv2 17450 }

dpsRTUv2p16451Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 3 is set"
	::= { dpsRTUv2 16451 }

dpsRTUv2p17451Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 3 is cleared"
	::= { dpsRTUv2 17451 }

dpsRTUv2p16452Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 4 is set"
	::= { dpsRTUv2 16452 }

dpsRTUv2p17452Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 4 is cleared"
	::= { dpsRTUv2 17452 }

dpsRTUv2p16453Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 5 is set"
	::= { dpsRTUv2 16453 }

dpsRTUv2p17453Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 5 is cleared"
	::= { dpsRTUv2 17453 }

dpsRTUv2p16454Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 6 is set"
	::= { dpsRTUv2 16454 }

dpsRTUv2p17454Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 6 is cleared"
	::= { dpsRTUv2 17454 }

dpsRTUv2p16455Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 7 is set"
	::= { dpsRTUv2 16455 }

dpsRTUv2p17455Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 7 is cleared"
	::= { dpsRTUv2 17455 }

dpsRTUv2p16456Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 8 is set"
	::= { dpsRTUv2 16456 }

dpsRTUv2p17456Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 8 is cleared"
	::= { dpsRTUv2 17456 }

dpsRTUv2p16457Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 9 is set"
	::= { dpsRTUv2 16457 }

dpsRTUv2p17457Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 9 is cleared"
	::= { dpsRTUv2 17457 }

dpsRTUv2p16458Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 10 is set"
	::= { dpsRTUv2 16458 }

dpsRTUv2p17458Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 10 is cleared"
	::= { dpsRTUv2 17458 }

dpsRTUv2p16459Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 11 is set"
	::= { dpsRTUv2 16459 }

dpsRTUv2p17459Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 11 is cleared"
	::= { dpsRTUv2 17459 }

dpsRTUv2p16460Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 12 is set"
	::= { dpsRTUv2 16460 }

dpsRTUv2p17460Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 12 is cleared"
	::= { dpsRTUv2 17460 }

dpsRTUv2p16461Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 13 is set"
	::= { dpsRTUv2 16461 }

dpsRTUv2p17461Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 13 is cleared"
	::= { dpsRTUv2 17461 }

dpsRTUv2p16462Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 14 is set"
	::= { dpsRTUv2 16462 }

dpsRTUv2p17462Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 14 is cleared"
	::= { dpsRTUv2 17462 }

dpsRTUv2p16463Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 15 is set"
	::= { dpsRTUv2 16463 }

dpsRTUv2p17463Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 15 is cleared"
	::= { dpsRTUv2 17463 }

dpsRTUv2p16464Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 16 is set"
	::= { dpsRTUv2 16464 }

dpsRTUv2p17464Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 16 is cleared"
	::= { dpsRTUv2 17464 }

dpsRTUv2p16465Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 17 is set"
	::= { dpsRTUv2 16465 }

dpsRTUv2p17465Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 17 is cleared"
	::= { dpsRTUv2 17465 }

dpsRTUv2p16466Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 18 is set"
	::= { dpsRTUv2 16466 }

dpsRTUv2p17466Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 18 is cleared"
	::= { dpsRTUv2 17466 }

dpsRTUv2p16467Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 19 is set"
	::= { dpsRTUv2 16467 }

dpsRTUv2p17467Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 19 is cleared"
	::= { dpsRTUv2 17467 }

dpsRTUv2p16468Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 20 is set"
	::= { dpsRTUv2 16468 }

dpsRTUv2p17468Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 20 is cleared"
	::= { dpsRTUv2 17468 }

dpsRTUv2p16469Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 21 is set"
	::= { dpsRTUv2 16469 }

dpsRTUv2p17469Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 21 is cleared"
	::= { dpsRTUv2 17469 }

dpsRTUv2p16470Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 22 is set"
	::= { dpsRTUv2 16470 }

dpsRTUv2p17470Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 22 is cleared"
	::= { dpsRTUv2 17470 }

dpsRTUv2p16471Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 23 is set"
	::= { dpsRTUv2 16471 }

dpsRTUv2p17471Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 23 is cleared"
	::= { dpsRTUv2 17471 }

dpsRTUv2p16472Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 24 is set"
	::= { dpsRTUv2 16472 }

dpsRTUv2p17472Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 24 is cleared"
	::= { dpsRTUv2 17472 }

dpsRTUv2p16473Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 25 is set"
	::= { dpsRTUv2 16473 }

dpsRTUv2p17473Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 25 is cleared"
	::= { dpsRTUv2 17473 }

dpsRTUv2p16474Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 26 is set"
	::= { dpsRTUv2 16474 }

dpsRTUv2p17474Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 26 is cleared"
	::= { dpsRTUv2 17474 }

dpsRTUv2p16475Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 27 is set"
	::= { dpsRTUv2 16475 }

dpsRTUv2p17475Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 27 is cleared"
	::= { dpsRTUv2 17475 }

dpsRTUv2p16476Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 28 is set"
	::= { dpsRTUv2 16476 }

dpsRTUv2p17476Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 28 is cleared"
	::= { dpsRTUv2 17476 }

dpsRTUv2p16477Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 29 is set"
	::= { dpsRTUv2 16477 }

dpsRTUv2p17477Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 29 is cleared"
	::= { dpsRTUv2 17477 }

dpsRTUv2p16478Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 30 is set"
	::= { dpsRTUv2 16478 }

dpsRTUv2p17478Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 30 is cleared"
	::= { dpsRTUv2 17478 }

dpsRTUv2p16479Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 31 is set"
	::= { dpsRTUv2 16479 }

dpsRTUv2p17479Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 31 is cleared"
	::= { dpsRTUv2 17479 }

dpsRTUv2p16480Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 32 is set"
	::= { dpsRTUv2 16480 }

dpsRTUv2p17480Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 32 is cleared"
	::= { dpsRTUv2 17480 }

dpsRTUv2p16481Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 33 is set"
	::= { dpsRTUv2 16481 }

dpsRTUv2p17481Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 33 is cleared"
	::= { dpsRTUv2 17481 }

dpsRTUv2p16482Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 34 is set"
	::= { dpsRTUv2 16482 }

dpsRTUv2p17482Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 34 is cleared"
	::= { dpsRTUv2 17482 }

dpsRTUv2p16483Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 35 is set"
	::= { dpsRTUv2 16483 }

dpsRTUv2p17483Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 35 is cleared"
	::= { dpsRTUv2 17483 }

dpsRTUv2p16484Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 36 is set"
	::= { dpsRTUv2 16484 }

dpsRTUv2p17484Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 36 is cleared"
	::= { dpsRTUv2 17484 }

dpsRTUv2p16485Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 37 is set"
	::= { dpsRTUv2 16485 }

dpsRTUv2p17485Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 37 is cleared"
	::= { dpsRTUv2 17485 }

dpsRTUv2p16486Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 38 is set"
	::= { dpsRTUv2 16486 }

dpsRTUv2p17486Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 38 is cleared"
	::= { dpsRTUv2 17486 }

dpsRTUv2p16487Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 39 is set"
	::= { dpsRTUv2 16487 }

dpsRTUv2p17487Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 39 is cleared"
	::= { dpsRTUv2 17487 }

dpsRTUv2p16488Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 40 is set"
	::= { dpsRTUv2 16488 }

dpsRTUv2p17488Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 40 is cleared"
	::= { dpsRTUv2 17488 }

dpsRTUv2p16489Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 41 is set"
	::= { dpsRTUv2 16489 }

dpsRTUv2p17489Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 41 is cleared"
	::= { dpsRTUv2 17489 }

dpsRTUv2p16490Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 42 is set"
	::= { dpsRTUv2 16490 }

dpsRTUv2p17490Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 42 is cleared"
	::= { dpsRTUv2 17490 }

dpsRTUv2p16491Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 43 is set"
	::= { dpsRTUv2 16491 }

dpsRTUv2p17491Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 43 is cleared"
	::= { dpsRTUv2 17491 }

dpsRTUv2p16492Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 44 is set"
	::= { dpsRTUv2 16492 }

dpsRTUv2p17492Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 44 is cleared"
	::= { dpsRTUv2 17492 }

dpsRTUv2p16493Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 45 is set"
	::= { dpsRTUv2 16493 }

dpsRTUv2p17493Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 45 is cleared"
	::= { dpsRTUv2 17493 }

dpsRTUv2p16494Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 46 is set"
	::= { dpsRTUv2 16494 }

dpsRTUv2p17494Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 46 is cleared"
	::= { dpsRTUv2 17494 }

dpsRTUv2p16495Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 47 is set"
	::= { dpsRTUv2 16495 }

dpsRTUv2p17495Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 47 is cleared"
	::= { dpsRTUv2 17495 }

dpsRTUv2p16496Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 48 is set"
	::= { dpsRTUv2 16496 }

dpsRTUv2p17496Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 48 is cleared"
	::= { dpsRTUv2 17496 }

dpsRTUv2p16497Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 49 is set"
	::= { dpsRTUv2 16497 }

dpsRTUv2p17497Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 49 is cleared"
	::= { dpsRTUv2 17497 }

dpsRTUv2p16498Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 50 is set"
	::= { dpsRTUv2 16498 }

dpsRTUv2p17498Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 50 is cleared"
	::= { dpsRTUv2 17498 }

dpsRTUv2p16499Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 51 is set"
	::= { dpsRTUv2 16499 }

dpsRTUv2p17499Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 51 is cleared"
	::= { dpsRTUv2 17499 }

dpsRTUv2p16500Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 52 is set"
	::= { dpsRTUv2 16500 }

dpsRTUv2p17500Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 52 is cleared"
	::= { dpsRTUv2 17500 }

dpsRTUv2p16501Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 53 is set"
	::= { dpsRTUv2 16501 }

dpsRTUv2p17501Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 53 is cleared"
	::= { dpsRTUv2 17501 }

dpsRTUv2p16502Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 54 is set"
	::= { dpsRTUv2 16502 }

dpsRTUv2p17502Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 54 is cleared"
	::= { dpsRTUv2 17502 }

dpsRTUv2p16503Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 55 is set"
	::= { dpsRTUv2 16503 }

dpsRTUv2p17503Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 55 is cleared"
	::= { dpsRTUv2 17503 }

dpsRTUv2p16504Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 56 is set"
	::= { dpsRTUv2 16504 }

dpsRTUv2p17504Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 56 is cleared"
	::= { dpsRTUv2 17504 }

dpsRTUv2p16505Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 57 is set"
	::= { dpsRTUv2 16505 }

dpsRTUv2p17505Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 57 is cleared"
	::= { dpsRTUv2 17505 }

dpsRTUv2p16506Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 58 is set"
	::= { dpsRTUv2 16506 }

dpsRTUv2p17506Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 58 is cleared"
	::= { dpsRTUv2 17506 }

dpsRTUv2p16507Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 59 is set"
	::= { dpsRTUv2 16507 }

dpsRTUv2p17507Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 59 is cleared"
	::= { dpsRTUv2 17507 }

dpsRTUv2p16508Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 60 is set"
	::= { dpsRTUv2 16508 }

dpsRTUv2p17508Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 60 is cleared"
	::= { dpsRTUv2 17508 }

dpsRTUv2p16509Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 61 is set"
	::= { dpsRTUv2 16509 }

dpsRTUv2p17509Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 61 is cleared"
	::= { dpsRTUv2 17509 }

dpsRTUv2p16510Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 62 is set"
	::= { dpsRTUv2 16510 }

dpsRTUv2p17510Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 62 is cleared"
	::= { dpsRTUv2 17510 }

dpsRTUv2p16511Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 63 is set"
	::= { dpsRTUv2 16511 }

dpsRTUv2p17511Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 63 is cleared"
	::= { dpsRTUv2 17511 }

dpsRTUv2p16512Set NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 64 is set"
	::= { dpsRTUv2 16512 }

dpsRTUv2p17512Clr NOTIFICATION-TYPE
	OBJECTS {	sysDescr, sysLocation, dpsRTUv2DateTime,
			dpsRTUv2APort, dpsRTUv2CAddress, dpsRTUv2ADisplay, dpsRTUv2APoint,
			dpsRTUv2APntDesc, dpsRTUv2AState }
	STATUS		current
	DESCRIPTION "Generated when TBOS port 4 display 8 point 64 is cleared"
	::= { dpsRTUv2 17512 }

 END
