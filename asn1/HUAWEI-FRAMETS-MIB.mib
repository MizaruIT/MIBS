-- =================================================================
-- Copyright (C) 2003 by  HUAWEI TECHNOLOGIES. All rights reserved.
--
-- Description:	Demonstrates how to	get	TS usable information from frame
-- Reference:	None
-- Version:		V1.0
-- History:
-- liguanrong, 2004-05-31, MIB first define
-- =================================================================

HUAWEI-FRAMETS-MIB DEFINITIONS ::= BEGIN
IMPORTS
	MODULE-IDENTITY, OBJECT-TYPE
		FROM SNMPv2-SMI

	huaweiUtility
				FROM HUAWEI-MIB;

hwFramets MODULE-IDENTITY
			LAST-UPDATED "0405310900Z"
			ORGANIZATION
				"Huawei	Technologies co.,Ltd."
			CONTACT-INFO
				"Kefa Road,
				 Fx-Net	Dep, Huawei	Technologies Co.,Ltd.
				 Science-Based Industrial Park,
				 Nanshan District,Shenzhen	P.R. China
				 http://www.huawei.com
				 Zip:518057"
	DESCRIPTION	"The HUAWEI-FRAMETS-MIB	demonstrates how to	get	TS usable information from frame"
	::=	{ huaweiUtility	44 }

		hwFrametsMibObjects		  OBJECT IDENTIFIER	 ::= { hwFramets   1 }

  hwFrametsTable OBJECT-TYPE
	SYNTAX		SEQUENCE OF	HwFrametsEntry
	MAX-ACCESS	not-accessible
	STATUS		current
	DESCRIPTION
	  "Frame TS	infomation maintain	table"
	::=	{ hwFrametsMibObjects 1	}

  hwFrametsEntry OBJECT-TYPE
	SYNTAX		HwFrametsEntry
	MAX-ACCESS	not-accessible
	STATUS		current
	DESCRIPTION
	  "Frame TS	maintain table index"
	INDEX
		{
			hwframeIndex
		}
	::=	{ hwFrametsTable 1 }

  HwFrametsEntry ::=
	SEQUENCE
	{
		hwframeIndex		INTEGER,
		hwUsableTs			INTEGER,
		hwPhoneUsableTs		INTEGER,
		hwPstnUser			INTEGER,
		hwIsdnUser			INTEGER
	}

  hwframeIndex OBJECT-TYPE
	SYNTAX		INTEGER
	MAX-ACCESS	not-accessible
	STATUS		current
	DESCRIPTION
		"
			index
			索引字段
		"
	::=	{ hwFrametsEntry 1 }

  hwUsableTs OBJECT-TYPE
	SYNTAX		INTEGER
	MAX-ACCESS	read-only
	STATUS		current
	DESCRIPTION
		"
			All	user usable	TS number of all V5	links
			链路上用户可用时隙数
		"
	::=	{ hwFrametsEntry 2 }

  hwPhoneUsableTs OBJECT-TYPE
	SYNTAX		INTEGER
	MAX-ACCESS	read-only
	STATUS		current
	DESCRIPTION
		"
			All	instant	user usable	TS number now of all V5	links
			链路上即时业务现可用时隙数
		"
	::=	{ hwFrametsEntry 3 }

  hwPstnUser OBJECT-TYPE
	SYNTAX		INTEGER
	MAX-ACCESS	read-only
	STATUS		current
	DESCRIPTION
		"
			PSTN instant user number on	these V5 links
			本链路需承载的PSTN即时用户数
		"
	::=	{ hwFrametsEntry 4 }

  hwIsdnUser OBJECT-TYPE
	SYNTAX		INTEGER
	MAX-ACCESS	read-only
	STATUS		current
	DESCRIPTION
		"
			ISDN instant user number on	these V5 links
			本链路需承载的ISDN即时用户数
		"
	::=	{ hwFrametsEntry 5 }

END
